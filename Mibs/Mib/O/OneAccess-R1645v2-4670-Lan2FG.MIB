OneAccess-R1645v2-4670-Lan2FG DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Lan2FG OBJECT IDENTIFIER ::= {r1645Rootv2 4670}

r1645v2Lan2FGMOProp OBJECT IDENTIFIER ::= {r1645v2Lan2FG 1}

r1645v2Lan2FGMOPropEntry OBJECT IDENTIFIER ::= {r1645v2Lan2FGMOProp 1}

r1645v2Lan2FGMOPropPath OBJECT-TYPE
   SYNTAX      ContainmentPath
   MAX-ACCESS  read-only
   STATUS      current
   DESCRIPTION
      "Textual description of the containment tree from the instance of
       the root object down to the instance of the current object."
   ::= {r1645v2Lan2FGMOPropEntry 3}

r1645v2Lan2FGMOPropRev OBJECT-TYPE
   SYNTAX      ObjectRevision
   MAX-ACCESS  read-only
   STATUS      current
   DESCRIPTION
      "This value corresponds with the revision of the MANAGED OBJECT."
   ::= {r1645v2Lan2FGMOPropEntry 4}



er1645v2Lan2FG OBJECT IDENTIFIER ::= {r1645v2Lan2FG 11}


er1645v2Lan2FGRemark OBJECT-TYPE
   SYNTAX      DisplayString
   MAX-ACCESS  read-write
   STATUS      current
   DESCRIPTION
      "Path: ethernet2.editConf.remark
       Info: intfRemark"
   ::= {er1645v2Lan2FG 321}


er1645v2Lan2FGAdminStatus OBJECT-TYPE
   SYNTAX      INTEGER
               {
               up (1),
               down (2)
               }
   MAX-ACCESS  read-write
   STATUS      current
   DESCRIPTION
      "Path: ethernet2.editConf.adminStatus
       Info: ifAdminStatus

       Possibilities:
               up   (1)
               down   (2)"
   ::= {er1645v2Lan2FG 106}


er1645v2Lan2FGBw OBJECT IDENTIFIER ::= {er1645v2Lan2FG 5}

er1645v2Lan2FGBwSSC OBJECT IDENTIFIER ::= {er1645v2Lan2FGBw 1}

er1645v2Lan2FGBwEntry OBJECT IDENTIFIER ::= {er1645v2Lan2FGBwSSC 1}

er1645v2Lan2FGBwMode OBJECT-TYPE
   SYNTAX      INTEGER
               {
               reshaping (1),
               policing (2),
               policingReshape (3)
               }
   MAX-ACCESS  read-write
   STATUS      current
   DESCRIPTION
      "Path: ethernet2.editConf.bandwidth.mode

       Possibilities:
               reshaping   (1)
               policing   (2)
               policingReshape   (3)"
   ::= {er1645v2Lan2FGBwEntry 3758096384}

er1645v2Lan2FGBwCir OBJECT-TYPE
   SYNTAX      Integer32
   MAX-ACCESS  read-write
   STATUS      current
   DESCRIPTION
      "Path: ethernet2.editConf.bandwidth.cir"
   ::= {er1645v2Lan2FGBwEntry 268435456}

er1645v2Lan2FGBwEir OBJECT-TYPE
   SYNTAX      Integer32
   MAX-ACCESS  read-write
   STATUS      current
   DESCRIPTION
      "Path: ethernet2.editConf.bandwidth.eir"
   ::= {er1645v2Lan2FGBwEntry 1879048192}

er1645v2Lan2FGBwUnit OBJECT-TYPE
   SYNTAX      INTEGER
               {
               bitssec (1),
               percent (2)
               }
   MAX-ACCESS  read-write
   STATUS      current
   DESCRIPTION
      "Path: ethernet2.editConf.bandwidth.unit

       Possibilities:
               bits/sec   (1)
               percent   (2)"
   ::= {er1645v2Lan2FGBwEntry 1342177280}

er1645v2Lan2FGBwTc OBJECT-TYPE
   SYNTAX      INTEGER
               {
               auto (0)
               }
   MAX-ACCESS  read-write
   STATUS      current
   DESCRIPTION
      "Path: ethernet2.editConf.bandwidth.tc

       Possibilities:
               auto   (0)"
   ::= {er1645v2Lan2FGBwEntry 1610612736}

er1645v2Lan2FGBwTcFactor OBJECT-TYPE
   SYNTAX      INTEGER
               {
               ms (10),
               s100us (1)
               }
   MAX-ACCESS  read-write
   STATUS      current
   DESCRIPTION
      "Path: ethernet2.editConf.bandwidth.tcFactor

       Possibilities:
               ms   (10)
               *100us   (1)"
   ::= {er1645v2Lan2FGBwEntry 2147483648}

er1645v2Lan2FGBwCorrType OBJECT-TYPE
   SYNTAX      INTEGER
               {
               noCorrection (0),
               predefined (1),
               manual (2)
               }
   MAX-ACCESS  read-write
   STATUS      current
   DESCRIPTION
      "Path: ethernet2.editConf.bandwidth.correction.type

       Possibilities:
               noCorrection   (0)
               predefined   (1)
               manual   (2)"
   ::= {er1645v2Lan2FGBwEntry 570425344}

er1645v2Lan2FGBwCorrPredefEncapsFrameRelay OBJECT-TYPE
   SYNTAX      DisplayString
   MAX-ACCESS  read-write
   STATUS      current
   DESCRIPTION
      "Path: ethernet2.editConf.bandwidth.correction.predefined.encapsulation.frameRelay"
   ::= {er1645v2Lan2FGBwEntry 608436224}

er1645v2Lan2FGBwCorrPredefEncapsPpp OBJECT-TYPE
   SYNTAX      DisplayString
   MAX-ACCESS  read-write
   STATUS      current
   DESCRIPTION
      "Path: ethernet2.editConf.bandwidth.correction.predefined.encapsulation.ppp"
   ::= {er1645v2Lan2FGBwEntry 608698368}

er1645v2Lan2FGBwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.bandwidth.correction.predefined.encapsulation.atm.higherLayer

       Possibilities:
               rfc2684   (0)
               ppp   (1)
               pppOverEthernet   (2)"
   ::= {er1645v2Lan2FGBwEntry 608993280}

er1645v2Lan2FGBwCorrPredefEncapsAtmMp OBJECT-TYPE
   SYNTAX      INTEGER
               {
               llcEncapsulation (0),
               vcMultiplexing (1)
               }
   MAX-ACCESS  read-write
   STATUS      current
   DESCRIPTION
      "Path: ethernet2.editConf.bandwidth.correction.predefined.encapsulation.atm.multiProtocol

       Possibilities:
               llcEncapsulation   (0)
               vcMultiplexing   (1)"
   ::= {er1645v2Lan2FGBwEntry 609026048}

er1645v2Lan2FGBwCorrPredefEncapsHdlc OBJECT-TYPE
   SYNTAX      DisplayString
   MAX-ACCESS  read-write
   STATUS      current
   DESCRIPTION
      "Path: ethernet2.editConf.bandwidth.correction.predefined.encapsulation.hdlc"
   ::= {er1645v2Lan2FGBwEntry 609222656}

er1645v2Lan2FGBwCorrPredefEncapsEfmFs OBJECT-TYPE
   SYNTAX      Integer32
   MAX-ACCESS  read-write
   STATUS      current
   DESCRIPTION
      "Path: ethernet2.editConf.bandwidth.correction.predefined.encapsulation.efm.fragmentSize"
   ::= {er1645v2Lan2FGBwEntry 609517568}

er1645v2Lan2FGBwCorrPredefEncapsEfmIb OBJECT-TYPE
   SYNTAX      Integer32
   MAX-ACCESS  read-write
   STATUS      current
   DESCRIPTION
      "Path: ethernet2.editConf.bandwidth.correction.predefined.encapsulation.efm.idleBytes"
   ::= {er1645v2Lan2FGBwEntry 609550336}

er1645v2Lan2FGBwCorrPredefMode OBJECT-TYPE
   SYNTAX      INTEGER
               {
               routing (0),
               bridging (1)
               }
   MAX-ACCESS  read-write
   STATUS      current
   DESCRIPTION
      "Path: ethernet2.editConf.bandwidth.correction.predefined.mode

       Possibilities:
               routing   (0)
               bridging   (1)"
   ::= {er1645v2Lan2FGBwEntry 612368384}

er1645v2Lan2FGBwCorrManualOverhead OBJECT-TYPE
   SYNTAX      Integer32
   MAX-ACCESS  read-write
   STATUS      current
   DESCRIPTION
      "Path: ethernet2.editConf.bandwidth.correction.manual.overhead"
   ::= {er1645v2Lan2FGBwEntry 637665280}

er1645v2Lan2FGBwCorrManualFrameData OBJECT-TYPE
   SYNTAX      Counter32
   MAX-ACCESS  read-write
   STATUS      current
   DESCRIPTION
      "Path: ethernet2.editConf.bandwidth.correction.manual.frameData

       32 bit unsigned wrappable counter."
   ::= {er1645v2Lan2FGBwEntry 637796352}

er1645v2Lan2FGBwCorrManualFrameHeader OBJECT-TYPE
   SYNTAX      Counter32
   MAX-ACCESS  read-write
   STATUS      current
   DESCRIPTION
      "Path: ethernet2.editConf.bandwidth.correction.manual.frameHeader

       32 bit unsigned wrappable counter."
   ::= {er1645v2Lan2FGBwEntry 637927424}

er1645v2Lan2FGBwMaxFifoQLen OBJECT-TYPE
   SYNTAX      Integer32
   MAX-ACCESS  read-write
   STATUS      current
   DESCRIPTION
      "Path: ethernet2.editConf.bandwidth.maxFifoQLen"
   ::= {er1645v2Lan2FGBwEntry 805306368}

er1645v2Lan2FGBwDeFlagCir OBJECT-TYPE
   SYNTAX      INTEGER
               {
               allowed (1),
               notAllowed (2)
               }
   MAX-ACCESS  read-write
   STATUS      current
   DESCRIPTION
      "Path: ethernet2.editConf.bandwidth.deFlag.cir

       Possibilities:
               allowed   (1)
               notAllowed   (2)"
   ::= {er1645v2Lan2FGBwEntry 3490709504}

er1645v2Lan2FGBwDeFlagEir OBJECT-TYPE
   SYNTAX      INTEGER
               {
               allowed (1),
               notAllowed (2)
               }
   MAX-ACCESS  read-write
   STATUS      current
   DESCRIPTION
      "Path: ethernet2.editConf.bandwidth.deFlag.eir

       Possibilities:
               allowed   (1)
               notAllowed   (2)"
   ::= {er1645v2Lan2FGBwEntry 3491758080}

er1645v2Lan2FGBwDeFlagViolate OBJECT-TYPE
   SYNTAX      INTEGER
               {
               allowed (1),
               notAllowed (2)
               }
   MAX-ACCESS  read-write
   STATUS      current
   DESCRIPTION
      "Path: ethernet2.editConf.bandwidth.deFlag.violate

       Possibilities:
               allowed   (1)
               notAllowed   (2)"
   ::= {er1645v2Lan2FGBwEntry 3492806656}

er1645v2Lan2FGBwActCirActNone OBJECT-TYPE
   SYNTAX      OCTET STRING
   MAX-ACCESS  read-write
   STATUS      current
   DESCRIPTION
      "Path: ethernet2.editConf.bandwidth.action.cirAction.none"
   ::= {er1645v2Lan2FGBwEntry 4062183424}

er1645v2Lan2FGBwActCirActEthCos1 OBJECT-TYPE
   SYNTAX      INTEGER
               {
               unchanged (256)
               }
   MAX-ACCESS  read-write
   STATUS      current
   DESCRIPTION
      "Path: ethernet2.editConf.bandwidth.action.cirAction.ethernet.cosDepth1

       Possibilities:
               unchanged   (256)"
   ::= {er1645v2Lan2FGBwEntry 4064346112}

er1645v2Lan2FGBwActCirActEthDei1 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth1

       Possibilities:
               unchanged   (255)
               clear   (0)
               set   (1)"
   ::= {er1645v2Lan2FGBwEntry 4065656832}

er1645v2Lan2FGBwActCirActEthCos2 OBJECT-TYPE
   SYNTAX      INTEGER
               {
               unchanged (256)
               }
   MAX-ACCESS  read-write
   STATUS      current
   DESCRIPTION
      "Path: ethernet2.editConf.bandwidth.action.cirAction.ethernet.cosDepth2

       Possibilities:
               unchanged   (256)"
   ::= {er1645v2Lan2FGBwEntry 4064411648}

er1645v2Lan2FGBwActCirActEthDei2 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth2

       Possibilities:
               unchanged   (255)
               clear   (0)
               set   (1)"
   ::= {er1645v2Lan2FGBwEntry 4065722368}

er1645v2Lan2FGBwActCirActEthCos3 OBJECT-TYPE
   SYNTAX      INTEGER
               {
               unchanged (256)
               }
   MAX-ACCESS  read-write
   STATUS      current
   DESCRIPTION
      "Path: ethernet2.editConf.bandwidth.action.cirAction.ethernet.cosDepth3

       Possibilities:
               unchanged   (256)"
   ::= {er1645v2Lan2FGBwEntry 4064477184}

er1645v2Lan2FGBwActCirActEthDei3 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth3

       Possibilities:
               unchanged   (255)
               clear   (0)
               set   (1)"
   ::= {er1645v2Lan2FGBwEntry 4065787904}

er1645v2Lan2FGBwActCirActEthCos4 OBJECT-TYPE
   SYNTAX      INTEGER
               {
               unchanged (256)
               }
   MAX-ACCESS  read-write
   STATUS      current
   DESCRIPTION
      "Path: ethernet2.editConf.bandwidth.action.cirAction.ethernet.cosDepth4

       Possibilities:
               unchanged   (256)"
   ::= {er1645v2Lan2FGBwEntry 4064542720}

er1645v2Lan2FGBwActCirActEthDei4 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth4

       Possibilities:
               unchanged   (255)
               clear   (0)
               set   (1)"
   ::= {er1645v2Lan2FGBwEntry 4065853440}

er1645v2Lan2FGBwActCirActEthCos5 OBJECT-TYPE
   SYNTAX      INTEGER
               {
               unchanged (256)
               }
   MAX-ACCESS  read-write
   STATUS      current
   DESCRIPTION
      "Path: ethernet2.editConf.bandwidth.action.cirAction.ethernet.cosDepth5

       Possibilities:
               unchanged   (256)"
   ::= {er1645v2Lan2FGBwEntry 4064608256}

er1645v2Lan2FGBwActCirActEthDei5 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth5

       Possibilities:
               unchanged   (255)
               clear   (0)
               set   (1)"
   ::= {er1645v2Lan2FGBwEntry 4065918976}

er1645v2Lan2FGBwActCirActEthCos6 OBJECT-TYPE
   SYNTAX      INTEGER
               {
               unchanged (256)
               }
   MAX-ACCESS  read-write
   STATUS      current
   DESCRIPTION
      "Path: ethernet2.editConf.bandwidth.action.cirAction.ethernet.cosDepth6

       Possibilities:
               unchanged   (256)"
   ::= {er1645v2Lan2FGBwEntry 4064673792}

er1645v2Lan2FGBwActCirActEthDei6 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth6

       Possibilities:
               unchanged   (255)
               clear   (0)
               set   (1)"
   ::= {er1645v2Lan2FGBwEntry 4065984512}

er1645v2Lan2FGBwActCirActEthCos7 OBJECT-TYPE
   SYNTAX      INTEGER
               {
               unchanged (256)
               }
   MAX-ACCESS  read-write
   STATUS      current
   DESCRIPTION
      "Path: ethernet2.editConf.bandwidth.action.cirAction.ethernet.cosDepth7

       Possibilities:
               unchanged   (256)"
   ::= {er1645v2Lan2FGBwEntry 4064739328}

er1645v2Lan2FGBwActCirActEthDei7 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth7

       Possibilities:
               unchanged   (255)
               clear   (0)
               set   (1)"
   ::= {er1645v2Lan2FGBwEntry 4066050048}

er1645v2Lan2FGBwActCirActEthCos8 OBJECT-TYPE
   SYNTAX      INTEGER
               {
               unchanged (256)
               }
   MAX-ACCESS  read-write
   STATUS      current
   DESCRIPTION
      "Path: ethernet2.editConf.bandwidth.action.cirAction.ethernet.cosDepth8

       Possibilities:
               unchanged   (256)"
   ::= {er1645v2Lan2FGBwEntry 4064804864}

er1645v2Lan2FGBwActCirActEthDei8 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth8

       Possibilities:
               unchanged   (255)
               clear   (0)
               set   (1)"
   ::= {er1645v2Lan2FGBwEntry 4066115584}

er1645v2Lan2FGBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGBwEntry 4064870400}

er1645v2Lan2FGBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGBwEntry 4064935936}

er1645v2Lan2FGBwActCirActEthDrpLev OBJECT-TYPE
   SYNTAX      INTEGER
               {
               unchanged (0)
               }
   MAX-ACCESS  read-write
   STATUS      current
   DESCRIPTION
      "Path: ethernet2.editConf.bandwidth.action.cirAction.ethernet.dropLevel

       Possibilities:
               unchanged   (0)"
   ::= {er1645v2Lan2FGBwEntry 4065001472}

er1645v2Lan2FGBwActCirActEthDeFlag OBJECT-TYPE
   SYNTAX      INTEGER
               {
               unchanged (255),
               clear (0),
               set (1)
               }
   MAX-ACCESS  read-write
   STATUS      current
   DESCRIPTION
      "Path: ethernet2.editConf.bandwidth.action.cirAction.ethernet.deFlag

       Possibilities:
               unchanged   (255)
               clear   (0)
               set   (1)"
   ::= {er1645v2Lan2FGBwEntry 4065198080}

er1645v2Lan2FGBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGBwEntry 4071161856}

er1645v2Lan2FGBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGBwEntry 4071227392}

er1645v2Lan2FGBwActCirActIpDrpLev OBJECT-TYPE
   SYNTAX      INTEGER
               {
               unchanged (0)
               }
   MAX-ACCESS  read-write
   STATUS      current
   DESCRIPTION
      "Path: ethernet2.editConf.bandwidth.action.cirAction.ip.dropLevel

       Possibilities:
               unchanged   (0)"
   ::= {er1645v2Lan2FGBwEntry 4071292928}

er1645v2Lan2FGBwActCirActIpDeFlag OBJECT-TYPE
   SYNTAX      INTEGER
               {
               unchanged (255),
               clear (0),
               set (1)
               }
   MAX-ACCESS  read-write
   STATUS      current
   DESCRIPTION
      "Path: ethernet2.editConf.bandwidth.action.cirAction.ip.deFlag

       Possibilities:
               unchanged   (255)
               clear   (0)
               set   (1)"
   ::= {er1645v2Lan2FGBwEntry 4071489536}

er1645v2Lan2FGBwActEirActNone OBJECT-TYPE
   SYNTAX      OCTET STRING
   MAX-ACCESS  read-write
   STATUS      current
   DESCRIPTION
      "Path: ethernet2.editConf.bandwidth.action.eirAction.none"
   ::= {er1645v2Lan2FGBwEntry 4095737856}

er1645v2Lan2FGBwActEirActEthCos1 OBJECT-TYPE
   SYNTAX      INTEGER
               {
               unchanged (256)
               }
   MAX-ACCESS  read-write
   STATUS      current
   DESCRIPTION
      "Path: ethernet2.editConf.bandwidth.action.eirAction.ethernet.cosDepth1

       Possibilities:
               unchanged   (256)"
   ::= {er1645v2Lan2FGBwEntry 4097900544}

er1645v2Lan2FGBwActEirActEthDei1 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth1

       Possibilities:
               unchanged   (255)
               clear   (0)
               set   (1)"
   ::= {er1645v2Lan2FGBwEntry 4099211264}

er1645v2Lan2FGBwActEirActEthCos2 OBJECT-TYPE
   SYNTAX      INTEGER
               {
               unchanged (256)
               }
   MAX-ACCESS  read-write
   STATUS      current
   DESCRIPTION
      "Path: ethernet2.editConf.bandwidth.action.eirAction.ethernet.cosDepth2

       Possibilities:
               unchanged   (256)"
   ::= {er1645v2Lan2FGBwEntry 4097966080}

er1645v2Lan2FGBwActEirActEthDei2 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth2

       Possibilities:
               unchanged   (255)
               clear   (0)
               set   (1)"
   ::= {er1645v2Lan2FGBwEntry 4099276800}

er1645v2Lan2FGBwActEirActEthCos3 OBJECT-TYPE
   SYNTAX      INTEGER
               {
               unchanged (256)
               }
   MAX-ACCESS  read-write
   STATUS      current
   DESCRIPTION
      "Path: ethernet2.editConf.bandwidth.action.eirAction.ethernet.cosDepth3

       Possibilities:
               unchanged   (256)"
   ::= {er1645v2Lan2FGBwEntry 4098031616}

er1645v2Lan2FGBwActEirActEthDei3 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth3

       Possibilities:
               unchanged   (255)
               clear   (0)
               set   (1)"
   ::= {er1645v2Lan2FGBwEntry 4099342336}

er1645v2Lan2FGBwActEirActEthCos4 OBJECT-TYPE
   SYNTAX      INTEGER
               {
               unchanged (256)
               }
   MAX-ACCESS  read-write
   STATUS      current
   DESCRIPTION
      "Path: ethernet2.editConf.bandwidth.action.eirAction.ethernet.cosDepth4

       Possibilities:
               unchanged   (256)"
   ::= {er1645v2Lan2FGBwEntry 4098097152}

er1645v2Lan2FGBwActEirActEthDei4 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth4

       Possibilities:
               unchanged   (255)
               clear   (0)
               set   (1)"
   ::= {er1645v2Lan2FGBwEntry 4099407872}

er1645v2Lan2FGBwActEirActEthCos5 OBJECT-TYPE
   SYNTAX      INTEGER
               {
               unchanged (256)
               }
   MAX-ACCESS  read-write
   STATUS      current
   DESCRIPTION
      "Path: ethernet2.editConf.bandwidth.action.eirAction.ethernet.cosDepth5

       Possibilities:
               unchanged   (256)"
   ::= {er1645v2Lan2FGBwEntry 4098162688}

er1645v2Lan2FGBwActEirActEthDei5 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth5

       Possibilities:
               unchanged   (255)
               clear   (0)
               set   (1)"
   ::= {er1645v2Lan2FGBwEntry 4099473408}

er1645v2Lan2FGBwActEirActEthCos6 OBJECT-TYPE
   SYNTAX      INTEGER
               {
               unchanged (256)
               }
   MAX-ACCESS  read-write
   STATUS      current
   DESCRIPTION
      "Path: ethernet2.editConf.bandwidth.action.eirAction.ethernet.cosDepth6

       Possibilities:
               unchanged   (256)"
   ::= {er1645v2Lan2FGBwEntry 4098228224}

er1645v2Lan2FGBwActEirActEthDei6 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth6

       Possibilities:
               unchanged   (255)
               clear   (0)
               set   (1)"
   ::= {er1645v2Lan2FGBwEntry 4099538944}

er1645v2Lan2FGBwActEirActEthCos7 OBJECT-TYPE
   SYNTAX      INTEGER
               {
               unchanged (256)
               }
   MAX-ACCESS  read-write
   STATUS      current
   DESCRIPTION
      "Path: ethernet2.editConf.bandwidth.action.eirAction.ethernet.cosDepth7

       Possibilities:
               unchanged   (256)"
   ::= {er1645v2Lan2FGBwEntry 4098293760}

er1645v2Lan2FGBwActEirActEthDei7 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth7

       Possibilities:
               unchanged   (255)
               clear   (0)
               set   (1)"
   ::= {er1645v2Lan2FGBwEntry 4099604480}

er1645v2Lan2FGBwActEirActEthCos8 OBJECT-TYPE
   SYNTAX      INTEGER
               {
               unchanged (256)
               }
   MAX-ACCESS  read-write
   STATUS      current
   DESCRIPTION
      "Path: ethernet2.editConf.bandwidth.action.eirAction.ethernet.cosDepth8

       Possibilities:
               unchanged   (256)"
   ::= {er1645v2Lan2FGBwEntry 4098359296}

er1645v2Lan2FGBwActEirActEthDei8 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth8

       Possibilities:
               unchanged   (255)
               clear   (0)
               set   (1)"
   ::= {er1645v2Lan2FGBwEntry 4099670016}

er1645v2Lan2FGBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGBwEntry 4098424832}

er1645v2Lan2FGBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGBwEntry 4098490368}

er1645v2Lan2FGBwActEirActEthDrpLev OBJECT-TYPE
   SYNTAX      INTEGER
               {
               unchanged (0)
               }
   MAX-ACCESS  read-write
   STATUS      current
   DESCRIPTION
      "Path: ethernet2.editConf.bandwidth.action.eirAction.ethernet.dropLevel

       Possibilities:
               unchanged   (0)"
   ::= {er1645v2Lan2FGBwEntry 4098555904}

er1645v2Lan2FGBwActEirActEthDeFlag OBJECT-TYPE
   SYNTAX      INTEGER
               {
               unchanged (255),
               clear (0),
               set (1)
               }
   MAX-ACCESS  read-write
   STATUS      current
   DESCRIPTION
      "Path: ethernet2.editConf.bandwidth.action.eirAction.ethernet.deFlag

       Possibilities:
               unchanged   (255)
               clear   (0)
               set   (1)"
   ::= {er1645v2Lan2FGBwEntry 4098752512}

er1645v2Lan2FGBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGBwEntry 4104716288}

er1645v2Lan2FGBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGBwEntry 4104781824}

er1645v2Lan2FGBwActEirActIpDrpLev OBJECT-TYPE
   SYNTAX      INTEGER
               {
               unchanged (0)
               }
   MAX-ACCESS  read-write
   STATUS      current
   DESCRIPTION
      "Path: ethernet2.editConf.bandwidth.action.eirAction.ip.dropLevel

       Possibilities:
               unchanged   (0)"
   ::= {er1645v2Lan2FGBwEntry 4104847360}

er1645v2Lan2FGBwActEirActIpDeFlag OBJECT-TYPE
   SYNTAX      INTEGER
               {
               unchanged (255),
               clear (0),
               set (1)
               }
   MAX-ACCESS  read-write
   STATUS      current
   DESCRIPTION
      "Path: ethernet2.editConf.bandwidth.action.eirAction.ip.deFlag

       Possibilities:
               unchanged   (255)
               clear   (0)
               set   (1)"
   ::= {er1645v2Lan2FGBwEntry 4105043968}

er1645v2Lan2FGBwActViolActNone OBJECT-TYPE
   SYNTAX      OCTET STRING
   MAX-ACCESS  read-write
   STATUS      current
   DESCRIPTION
      "Path: ethernet2.editConf.bandwidth.action.violateAction.none"
   ::= {er1645v2Lan2FGBwEntry 4129292288}

er1645v2Lan2FGBwActViolActDrop OBJECT-TYPE
   SYNTAX      OCTET STRING
   MAX-ACCESS  read-write
   STATUS      current
   DESCRIPTION
      "Path: ethernet2.editConf.bandwidth.action.violateAction.drop"
   ::= {er1645v2Lan2FGBwEntry 4133486592}

er1645v2Lan2FGBwActViolActEthCos1 OBJECT-TYPE
   SYNTAX      INTEGER
               {
               unchanged (256)
               }
   MAX-ACCESS  read-write
   STATUS      current
   DESCRIPTION
      "Path: ethernet2.editConf.bandwidth.action.violateAction.ethernet.cosDepth1

       Possibilities:
               unchanged   (256)"
   ::= {er1645v2Lan2FGBwEntry 4131454976}

er1645v2Lan2FGBwActViolActEthDei1 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth1

       Possibilities:
               unchanged   (255)
               clear   (0)
               set   (1)"
   ::= {er1645v2Lan2FGBwEntry 4132765696}

er1645v2Lan2FGBwActViolActEthCos2 OBJECT-TYPE
   SYNTAX      INTEGER
               {
               unchanged (256)
               }
   MAX-ACCESS  read-write
   STATUS      current
   DESCRIPTION
      "Path: ethernet2.editConf.bandwidth.action.violateAction.ethernet.cosDepth2

       Possibilities:
               unchanged   (256)"
   ::= {er1645v2Lan2FGBwEntry 4131520512}

er1645v2Lan2FGBwActViolActEthDei2 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth2

       Possibilities:
               unchanged   (255)
               clear   (0)
               set   (1)"
   ::= {er1645v2Lan2FGBwEntry 4132831232}

er1645v2Lan2FGBwActViolActEthCos3 OBJECT-TYPE
   SYNTAX      INTEGER
               {
               unchanged (256)
               }
   MAX-ACCESS  read-write
   STATUS      current
   DESCRIPTION
      "Path: ethernet2.editConf.bandwidth.action.violateAction.ethernet.cosDepth3

       Possibilities:
               unchanged   (256)"
   ::= {er1645v2Lan2FGBwEntry 4131586048}

er1645v2Lan2FGBwActViolActEthDei3 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth3

       Possibilities:
               unchanged   (255)
               clear   (0)
               set   (1)"
   ::= {er1645v2Lan2FGBwEntry 4132896768}

er1645v2Lan2FGBwActViolActEthCos4 OBJECT-TYPE
   SYNTAX      INTEGER
               {
               unchanged (256)
               }
   MAX-ACCESS  read-write
   STATUS      current
   DESCRIPTION
      "Path: ethernet2.editConf.bandwidth.action.violateAction.ethernet.cosDepth4

       Possibilities:
               unchanged   (256)"
   ::= {er1645v2Lan2FGBwEntry 4131651584}

er1645v2Lan2FGBwActViolActEthDei4 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth4

       Possibilities:
               unchanged   (255)
               clear   (0)
               set   (1)"
   ::= {er1645v2Lan2FGBwEntry 4132962304}

er1645v2Lan2FGBwActViolActEthCos5 OBJECT-TYPE
   SYNTAX      INTEGER
               {
               unchanged (256)
               }
   MAX-ACCESS  read-write
   STATUS      current
   DESCRIPTION
      "Path: ethernet2.editConf.bandwidth.action.violateAction.ethernet.cosDepth5

       Possibilities:
               unchanged   (256)"
   ::= {er1645v2Lan2FGBwEntry 4131717120}

er1645v2Lan2FGBwActViolActEthDei5 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth5

       Possibilities:
               unchanged   (255)
               clear   (0)
               set   (1)"
   ::= {er1645v2Lan2FGBwEntry 4133027840}

er1645v2Lan2FGBwActViolActEthCos6 OBJECT-TYPE
   SYNTAX      INTEGER
               {
               unchanged (256)
               }
   MAX-ACCESS  read-write
   STATUS      current
   DESCRIPTION
      "Path: ethernet2.editConf.bandwidth.action.violateAction.ethernet.cosDepth6

       Possibilities:
               unchanged   (256)"
   ::= {er1645v2Lan2FGBwEntry 4131782656}

er1645v2Lan2FGBwActViolActEthDei6 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth6

       Possibilities:
               unchanged   (255)
               clear   (0)
               set   (1)"
   ::= {er1645v2Lan2FGBwEntry 4133093376}

er1645v2Lan2FGBwActViolActEthCos7 OBJECT-TYPE
   SYNTAX      INTEGER
               {
               unchanged (256)
               }
   MAX-ACCESS  read-write
   STATUS      current
   DESCRIPTION
      "Path: ethernet2.editConf.bandwidth.action.violateAction.ethernet.cosDepth7

       Possibilities:
               unchanged   (256)"
   ::= {er1645v2Lan2FGBwEntry 4131848192}

er1645v2Lan2FGBwActViolActEthDei7 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth7

       Possibilities:
               unchanged   (255)
               clear   (0)
               set   (1)"
   ::= {er1645v2Lan2FGBwEntry 4133158912}

er1645v2Lan2FGBwActViolActEthCos8 OBJECT-TYPE
   SYNTAX      INTEGER
               {
               unchanged (256)
               }
   MAX-ACCESS  read-write
   STATUS      current
   DESCRIPTION
      "Path: ethernet2.editConf.bandwidth.action.violateAction.ethernet.cosDepth8

       Possibilities:
               unchanged   (256)"
   ::= {er1645v2Lan2FGBwEntry 4131913728}

er1645v2Lan2FGBwActViolActEthDei8 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth8

       Possibilities:
               unchanged   (255)
               clear   (0)
               set   (1)"
   ::= {er1645v2Lan2FGBwEntry 4133224448}

er1645v2Lan2FGBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGBwEntry 4131979264}

er1645v2Lan2FGBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGBwEntry 4132044800}

er1645v2Lan2FGBwActViolActEthDrpLev OBJECT-TYPE
   SYNTAX      INTEGER
               {
               unchanged (0)
               }
   MAX-ACCESS  read-write
   STATUS      current
   DESCRIPTION
      "Path: ethernet2.editConf.bandwidth.action.violateAction.ethernet.dropLevel

       Possibilities:
               unchanged   (0)"
   ::= {er1645v2Lan2FGBwEntry 4132110336}

er1645v2Lan2FGBwActViolActEthDeFlag OBJECT-TYPE
   SYNTAX      INTEGER
               {
               unchanged (255),
               clear (0),
               set (1)
               }
   MAX-ACCESS  read-write
   STATUS      current
   DESCRIPTION
      "Path: ethernet2.editConf.bandwidth.action.violateAction.ethernet.deFlag

       Possibilities:
               unchanged   (255)
               clear   (0)
               set   (1)"
   ::= {er1645v2Lan2FGBwEntry 4132306944}

er1645v2Lan2FGBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGBwEntry 4138270720}

er1645v2Lan2FGBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGBwEntry 4138336256}

er1645v2Lan2FGBwActViolActIpDrpLev OBJECT-TYPE
   SYNTAX      INTEGER
               {
               unchanged (0)
               }
   MAX-ACCESS  read-write
   STATUS      current
   DESCRIPTION
      "Path: ethernet2.editConf.bandwidth.action.violateAction.ip.dropLevel

       Possibilities:
               unchanged   (0)"
   ::= {er1645v2Lan2FGBwEntry 4138401792}

er1645v2Lan2FGBwActViolActIpDeFlag OBJECT-TYPE
   SYNTAX      INTEGER
               {
               unchanged (255),
               clear (0),
               set (1)
               }
   MAX-ACCESS  read-write
   STATUS      current
   DESCRIPTION
      "Path: ethernet2.editConf.bandwidth.action.violateAction.ip.deFlag

       Possibilities:
               unchanged   (255)
               clear   (0)
               set   (1)"
   ::= {er1645v2Lan2FGBwEntry 4138598400}


er1645v2Lan2FGIbw OBJECT IDENTIFIER ::= {er1645v2Lan2FG 13}

er1645v2Lan2FGIbwSSC OBJECT IDENTIFIER ::= {er1645v2Lan2FGIbw 1}

er1645v2Lan2FGIbwEntry OBJECT IDENTIFIER ::= {er1645v2Lan2FGIbwSSC 1}

er1645v2Lan2FGIbwMode OBJECT-TYPE
   SYNTAX      INTEGER
               {
               reshaping (1),
               policing (2)
               }
   MAX-ACCESS  read-write
   STATUS      current
   DESCRIPTION
      "Path: ethernet2.editConf.inboundBandwidth.mode

       Possibilities:
               reshaping   (1)
               policing   (2)"
   ::= {er1645v2Lan2FGIbwEntry 3758096384}

er1645v2Lan2FGIbwCir OBJECT-TYPE
   SYNTAX      Integer32
   MAX-ACCESS  read-write
   STATUS      current
   DESCRIPTION
      "Path: ethernet2.editConf.inboundBandwidth.cir"
   ::= {er1645v2Lan2FGIbwEntry 268435456}

er1645v2Lan2FGIbwEir OBJECT-TYPE
   SYNTAX      Integer32
   MAX-ACCESS  read-write
   STATUS      current
   DESCRIPTION
      "Path: ethernet2.editConf.inboundBandwidth.eir"
   ::= {er1645v2Lan2FGIbwEntry 1879048192}

er1645v2Lan2FGIbwUnit OBJECT-TYPE
   SYNTAX      INTEGER
               {
               bitssec (1),
               percent (2)
               }
   MAX-ACCESS  read-write
   STATUS      current
   DESCRIPTION
      "Path: ethernet2.editConf.inboundBandwidth.unit

       Possibilities:
               bits/sec   (1)
               percent   (2)"
   ::= {er1645v2Lan2FGIbwEntry 1342177280}

er1645v2Lan2FGIbwTc OBJECT-TYPE
   SYNTAX      INTEGER
               {
               auto (0)
               }
   MAX-ACCESS  read-write
   STATUS      current
   DESCRIPTION
      "Path: ethernet2.editConf.inboundBandwidth.tc

       Possibilities:
               auto   (0)"
   ::= {er1645v2Lan2FGIbwEntry 1610612736}

er1645v2Lan2FGIbwTcFactor OBJECT-TYPE
   SYNTAX      INTEGER
               {
               ms (10),
               s100us (1)
               }
   MAX-ACCESS  read-write
   STATUS      current
   DESCRIPTION
      "Path: ethernet2.editConf.inboundBandwidth.tcFactor

       Possibilities:
               ms   (10)
               *100us   (1)"
   ::= {er1645v2Lan2FGIbwEntry 2147483648}

er1645v2Lan2FGIbwCorrType OBJECT-TYPE
   SYNTAX      INTEGER
               {
               noCorrection (0),
               predefined (1),
               manual (2)
               }
   MAX-ACCESS  read-write
   STATUS      current
   DESCRIPTION
      "Path: ethernet2.editConf.inboundBandwidth.correction.type

       Possibilities:
               noCorrection   (0)
               predefined   (1)
               manual   (2)"
   ::= {er1645v2Lan2FGIbwEntry 570425344}

er1645v2Lan2FGIbwCorrPredefEncapsFrameRelay OBJECT-TYPE
   SYNTAX      DisplayString
   MAX-ACCESS  read-write
   STATUS      current
   DESCRIPTION
      "Path: ethernet2.editConf.inboundBandwidth.correction.predefined.encapsulation.frameRelay"
   ::= {er1645v2Lan2FGIbwEntry 608436224}

er1645v2Lan2FGIbwCorrPredefEncapsPpp OBJECT-TYPE
   SYNTAX      DisplayString
   MAX-ACCESS  read-write
   STATUS      current
   DESCRIPTION
      "Path: ethernet2.editConf.inboundBandwidth.correction.predefined.encapsulation.ppp"
   ::= {er1645v2Lan2FGIbwEntry 608698368}

er1645v2Lan2FGIbwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.inboundBandwidth.correction.predefined.encapsulation.atm.higherLayer

       Possibilities:
               rfc2684   (0)
               ppp   (1)
               pppOverEthernet   (2)"
   ::= {er1645v2Lan2FGIbwEntry 608993280}

er1645v2Lan2FGIbwCorrPredefEncapsAtmMp OBJECT-TYPE
   SYNTAX      INTEGER
               {
               llcEncapsulation (0),
               vcMultiplexing (1)
               }
   MAX-ACCESS  read-write
   STATUS      current
   DESCRIPTION
      "Path: ethernet2.editConf.inboundBandwidth.correction.predefined.encapsulation.atm.multiProtocol

       Possibilities:
               llcEncapsulation   (0)
               vcMultiplexing   (1)"
   ::= {er1645v2Lan2FGIbwEntry 609026048}

er1645v2Lan2FGIbwCorrPredefEncapsHdlc OBJECT-TYPE
   SYNTAX      DisplayString
   MAX-ACCESS  read-write
   STATUS      current
   DESCRIPTION
      "Path: ethernet2.editConf.inboundBandwidth.correction.predefined.encapsulation.hdlc"
   ::= {er1645v2Lan2FGIbwEntry 609222656}

er1645v2Lan2FGIbwCorrPredefEncapsEfmFs OBJECT-TYPE
   SYNTAX      Integer32
   MAX-ACCESS  read-write
   STATUS      current
   DESCRIPTION
      "Path: ethernet2.editConf.inboundBandwidth.correction.predefined.encapsulation.efm.fragmentSize"
   ::= {er1645v2Lan2FGIbwEntry 609517568}

er1645v2Lan2FGIbwCorrPredefEncapsEfmIb OBJECT-TYPE
   SYNTAX      Integer32
   MAX-ACCESS  read-write
   STATUS      current
   DESCRIPTION
      "Path: ethernet2.editConf.inboundBandwidth.correction.predefined.encapsulation.efm.idleBytes"
   ::= {er1645v2Lan2FGIbwEntry 609550336}

er1645v2Lan2FGIbwCorrPredefMode OBJECT-TYPE
   SYNTAX      INTEGER
               {
               routing (0),
               bridging (1)
               }
   MAX-ACCESS  read-write
   STATUS      current
   DESCRIPTION
      "Path: ethernet2.editConf.inboundBandwidth.correction.predefined.mode

       Possibilities:
               routing   (0)
               bridging   (1)"
   ::= {er1645v2Lan2FGIbwEntry 612368384}

er1645v2Lan2FGIbwCorrManualOverhead OBJECT-TYPE
   SYNTAX      Integer32
   MAX-ACCESS  read-write
   STATUS      current
   DESCRIPTION
      "Path: ethernet2.editConf.inboundBandwidth.correction.manual.overhead"
   ::= {er1645v2Lan2FGIbwEntry 637665280}

er1645v2Lan2FGIbwCorrManualFrameData OBJECT-TYPE
   SYNTAX      Counter32
   MAX-ACCESS  read-write
   STATUS      current
   DESCRIPTION
      "Path: ethernet2.editConf.inboundBandwidth.correction.manual.frameData

       32 bit unsigned wrappable counter."
   ::= {er1645v2Lan2FGIbwEntry 637796352}

er1645v2Lan2FGIbwCorrManualFrameHeader OBJECT-TYPE
   SYNTAX      Counter32
   MAX-ACCESS  read-write
   STATUS      current
   DESCRIPTION
      "Path: ethernet2.editConf.inboundBandwidth.correction.manual.frameHeader

       32 bit unsigned wrappable counter."
   ::= {er1645v2Lan2FGIbwEntry 637927424}

er1645v2Lan2FGIbwMaxFifoQLen OBJECT-TYPE
   SYNTAX      Integer32
   MAX-ACCESS  read-write
   STATUS      current
   DESCRIPTION
      "Path: ethernet2.editConf.inboundBandwidth.maxFifoQLen"
   ::= {er1645v2Lan2FGIbwEntry 805306368}

er1645v2Lan2FGIbwPriorityPolicy OBJECT-TYPE
   SYNTAX      DisplayString
   MAX-ACCESS  read-write
   STATUS      current
   DESCRIPTION
      "Path: ethernet2.editConf.inboundBandwidth.priorityPolicy"
   ::= {er1645v2Lan2FGIbwEntry 1073741824}

er1645v2Lan2FGIbwDeFlagCir OBJECT-TYPE
   SYNTAX      INTEGER
               {
               allowed (1),
               notAllowed (2)
               }
   MAX-ACCESS  read-write
   STATUS      current
   DESCRIPTION
      "Path: ethernet2.editConf.inboundBandwidth.deFlag.cir

       Possibilities:
               allowed   (1)
               notAllowed   (2)"
   ::= {er1645v2Lan2FGIbwEntry 3490709504}

er1645v2Lan2FGIbwDeFlagEir OBJECT-TYPE
   SYNTAX      INTEGER
               {
               allowed (1),
               notAllowed (2)
               }
   MAX-ACCESS  read-write
   STATUS      current
   DESCRIPTION
      "Path: ethernet2.editConf.inboundBandwidth.deFlag.eir

       Possibilities:
               allowed   (1)
               notAllowed   (2)"
   ::= {er1645v2Lan2FGIbwEntry 3491758080}

er1645v2Lan2FGIbwDeFlagViolate OBJECT-TYPE
   SYNTAX      INTEGER
               {
               allowed (1),
               notAllowed (2)
               }
   MAX-ACCESS  read-write
   STATUS      current
   DESCRIPTION
      "Path: ethernet2.editConf.inboundBandwidth.deFlag.violate

       Possibilities:
               allowed   (1)
               notAllowed   (2)"
   ::= {er1645v2Lan2FGIbwEntry 3492806656}

er1645v2Lan2FGIbwActCirActNone OBJECT-TYPE
   SYNTAX      OCTET STRING
   MAX-ACCESS  read-write
   STATUS      current
   DESCRIPTION
      "Path: ethernet2.editConf.inboundBandwidth.action.cirAction.none"
   ::= {er1645v2Lan2FGIbwEntry 4062183424}

er1645v2Lan2FGIbwActCirActEthCos1 OBJECT-TYPE
   SYNTAX      INTEGER
               {
               unchanged (256)
               }
   MAX-ACCESS  read-write
   STATUS      current
   DESCRIPTION
      "Path: ethernet2.editConf.inboundBandwidth.action.cirAction.ethernet.cosDepth1

       Possibilities:
               unchanged   (256)"
   ::= {er1645v2Lan2FGIbwEntry 4064346112}

er1645v2Lan2FGIbwActCirActEthDei1 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth1

       Possibilities:
               unchanged   (255)
               clear   (0)
               set   (1)"
   ::= {er1645v2Lan2FGIbwEntry 4065656832}

er1645v2Lan2FGIbwActCirActEthCos2 OBJECT-TYPE
   SYNTAX      INTEGER
               {
               unchanged (256)
               }
   MAX-ACCESS  read-write
   STATUS      current
   DESCRIPTION
      "Path: ethernet2.editConf.inboundBandwidth.action.cirAction.ethernet.cosDepth2

       Possibilities:
               unchanged   (256)"
   ::= {er1645v2Lan2FGIbwEntry 4064411648}

er1645v2Lan2FGIbwActCirActEthDei2 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth2

       Possibilities:
               unchanged   (255)
               clear   (0)
               set   (1)"
   ::= {er1645v2Lan2FGIbwEntry 4065722368}

er1645v2Lan2FGIbwActCirActEthCos3 OBJECT-TYPE
   SYNTAX      INTEGER
               {
               unchanged (256)
               }
   MAX-ACCESS  read-write
   STATUS      current
   DESCRIPTION
      "Path: ethernet2.editConf.inboundBandwidth.action.cirAction.ethernet.cosDepth3

       Possibilities:
               unchanged   (256)"
   ::= {er1645v2Lan2FGIbwEntry 4064477184}

er1645v2Lan2FGIbwActCirActEthDei3 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth3

       Possibilities:
               unchanged   (255)
               clear   (0)
               set   (1)"
   ::= {er1645v2Lan2FGIbwEntry 4065787904}

er1645v2Lan2FGIbwActCirActEthCos4 OBJECT-TYPE
   SYNTAX      INTEGER
               {
               unchanged (256)
               }
   MAX-ACCESS  read-write
   STATUS      current
   DESCRIPTION
      "Path: ethernet2.editConf.inboundBandwidth.action.cirAction.ethernet.cosDepth4

       Possibilities:
               unchanged   (256)"
   ::= {er1645v2Lan2FGIbwEntry 4064542720}

er1645v2Lan2FGIbwActCirActEthDei4 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth4

       Possibilities:
               unchanged   (255)
               clear   (0)
               set   (1)"
   ::= {er1645v2Lan2FGIbwEntry 4065853440}

er1645v2Lan2FGIbwActCirActEthCos5 OBJECT-TYPE
   SYNTAX      INTEGER
               {
               unchanged (256)
               }
   MAX-ACCESS  read-write
   STATUS      current
   DESCRIPTION
      "Path: ethernet2.editConf.inboundBandwidth.action.cirAction.ethernet.cosDepth5

       Possibilities:
               unchanged   (256)"
   ::= {er1645v2Lan2FGIbwEntry 4064608256}

er1645v2Lan2FGIbwActCirActEthDei5 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth5

       Possibilities:
               unchanged   (255)
               clear   (0)
               set   (1)"
   ::= {er1645v2Lan2FGIbwEntry 4065918976}

er1645v2Lan2FGIbwActCirActEthCos6 OBJECT-TYPE
   SYNTAX      INTEGER
               {
               unchanged (256)
               }
   MAX-ACCESS  read-write
   STATUS      current
   DESCRIPTION
      "Path: ethernet2.editConf.inboundBandwidth.action.cirAction.ethernet.cosDepth6

       Possibilities:
               unchanged   (256)"
   ::= {er1645v2Lan2FGIbwEntry 4064673792}

er1645v2Lan2FGIbwActCirActEthDei6 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth6

       Possibilities:
               unchanged   (255)
               clear   (0)
               set   (1)"
   ::= {er1645v2Lan2FGIbwEntry 4065984512}

er1645v2Lan2FGIbwActCirActEthCos7 OBJECT-TYPE
   SYNTAX      INTEGER
               {
               unchanged (256)
               }
   MAX-ACCESS  read-write
   STATUS      current
   DESCRIPTION
      "Path: ethernet2.editConf.inboundBandwidth.action.cirAction.ethernet.cosDepth7

       Possibilities:
               unchanged   (256)"
   ::= {er1645v2Lan2FGIbwEntry 4064739328}

er1645v2Lan2FGIbwActCirActEthDei7 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth7

       Possibilities:
               unchanged   (255)
               clear   (0)
               set   (1)"
   ::= {er1645v2Lan2FGIbwEntry 4066050048}

er1645v2Lan2FGIbwActCirActEthCos8 OBJECT-TYPE
   SYNTAX      INTEGER
               {
               unchanged (256)
               }
   MAX-ACCESS  read-write
   STATUS      current
   DESCRIPTION
      "Path: ethernet2.editConf.inboundBandwidth.action.cirAction.ethernet.cosDepth8

       Possibilities:
               unchanged   (256)"
   ::= {er1645v2Lan2FGIbwEntry 4064804864}

er1645v2Lan2FGIbwActCirActEthDei8 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth8

       Possibilities:
               unchanged   (255)
               clear   (0)
               set   (1)"
   ::= {er1645v2Lan2FGIbwEntry 4066115584}

er1645v2Lan2FGIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGIbwEntry 4064870400}

er1645v2Lan2FGIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGIbwEntry 4064935936}

er1645v2Lan2FGIbwActCirActEthDrpLev OBJECT-TYPE
   SYNTAX      INTEGER
               {
               unchanged (0)
               }
   MAX-ACCESS  read-write
   STATUS      current
   DESCRIPTION
      "Path: ethernet2.editConf.inboundBandwidth.action.cirAction.ethernet.dropLevel

       Possibilities:
               unchanged   (0)"
   ::= {er1645v2Lan2FGIbwEntry 4065001472}

er1645v2Lan2FGIbwActCirActEthDeFlag OBJECT-TYPE
   SYNTAX      INTEGER
               {
               unchanged (255),
               clear (0),
               set (1)
               }
   MAX-ACCESS  read-write
   STATUS      current
   DESCRIPTION
      "Path: ethernet2.editConf.inboundBandwidth.action.cirAction.ethernet.deFlag

       Possibilities:
               unchanged   (255)
               clear   (0)
               set   (1)"
   ::= {er1645v2Lan2FGIbwEntry 4065198080}

er1645v2Lan2FGIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGIbwEntry 4071161856}

er1645v2Lan2FGIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGIbwEntry 4071227392}

er1645v2Lan2FGIbwActCirActIpDrpLev OBJECT-TYPE
   SYNTAX      INTEGER
               {
               unchanged (0)
               }
   MAX-ACCESS  read-write
   STATUS      current
   DESCRIPTION
      "Path: ethernet2.editConf.inboundBandwidth.action.cirAction.ip.dropLevel

       Possibilities:
               unchanged   (0)"
   ::= {er1645v2Lan2FGIbwEntry 4071292928}

er1645v2Lan2FGIbwActCirActIpDeFlag OBJECT-TYPE
   SYNTAX      INTEGER
               {
               unchanged (255),
               clear (0),
               set (1)
               }
   MAX-ACCESS  read-write
   STATUS      current
   DESCRIPTION
      "Path: ethernet2.editConf.inboundBandwidth.action.cirAction.ip.deFlag

       Possibilities:
               unchanged   (255)
               clear   (0)
               set   (1)"
   ::= {er1645v2Lan2FGIbwEntry 4071489536}

er1645v2Lan2FGIbwActEirActNone OBJECT-TYPE
   SYNTAX      OCTET STRING
   MAX-ACCESS  read-write
   STATUS      current
   DESCRIPTION
      "Path: ethernet2.editConf.inboundBandwidth.action.eirAction.none"
   ::= {er1645v2Lan2FGIbwEntry 4095737856}

er1645v2Lan2FGIbwActEirActEthCos1 OBJECT-TYPE
   SYNTAX      INTEGER
               {
               unchanged (256)
               }
   MAX-ACCESS  read-write
   STATUS      current
   DESCRIPTION
      "Path: ethernet2.editConf.inboundBandwidth.action.eirAction.ethernet.cosDepth1

       Possibilities:
               unchanged   (256)"
   ::= {er1645v2Lan2FGIbwEntry 4097900544}

er1645v2Lan2FGIbwActEirActEthDei1 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth1

       Possibilities:
               unchanged   (255)
               clear   (0)
               set   (1)"
   ::= {er1645v2Lan2FGIbwEntry 4099211264}

er1645v2Lan2FGIbwActEirActEthCos2 OBJECT-TYPE
   SYNTAX      INTEGER
               {
               unchanged (256)
               }
   MAX-ACCESS  read-write
   STATUS      current
   DESCRIPTION
      "Path: ethernet2.editConf.inboundBandwidth.action.eirAction.ethernet.cosDepth2

       Possibilities:
               unchanged   (256)"
   ::= {er1645v2Lan2FGIbwEntry 4097966080}

er1645v2Lan2FGIbwActEirActEthDei2 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth2

       Possibilities:
               unchanged   (255)
               clear   (0)
               set   (1)"
   ::= {er1645v2Lan2FGIbwEntry 4099276800}

er1645v2Lan2FGIbwActEirActEthCos3 OBJECT-TYPE
   SYNTAX      INTEGER
               {
               unchanged (256)
               }
   MAX-ACCESS  read-write
   STATUS      current
   DESCRIPTION
      "Path: ethernet2.editConf.inboundBandwidth.action.eirAction.ethernet.cosDepth3

       Possibilities:
               unchanged   (256)"
   ::= {er1645v2Lan2FGIbwEntry 4098031616}

er1645v2Lan2FGIbwActEirActEthDei3 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth3

       Possibilities:
               unchanged   (255)
               clear   (0)
               set   (1)"
   ::= {er1645v2Lan2FGIbwEntry 4099342336}

er1645v2Lan2FGIbwActEirActEthCos4 OBJECT-TYPE
   SYNTAX      INTEGER
               {
               unchanged (256)
               }
   MAX-ACCESS  read-write
   STATUS      current
   DESCRIPTION
      "Path: ethernet2.editConf.inboundBandwidth.action.eirAction.ethernet.cosDepth4

       Possibilities:
               unchanged   (256)"
   ::= {er1645v2Lan2FGIbwEntry 4098097152}

er1645v2Lan2FGIbwActEirActEthDei4 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth4

       Possibilities:
               unchanged   (255)
               clear   (0)
               set   (1)"
   ::= {er1645v2Lan2FGIbwEntry 4099407872}

er1645v2Lan2FGIbwActEirActEthCos5 OBJECT-TYPE
   SYNTAX      INTEGER
               {
               unchanged (256)
               }
   MAX-ACCESS  read-write
   STATUS      current
   DESCRIPTION
      "Path: ethernet2.editConf.inboundBandwidth.action.eirAction.ethernet.cosDepth5

       Possibilities:
               unchanged   (256)"
   ::= {er1645v2Lan2FGIbwEntry 4098162688}

er1645v2Lan2FGIbwActEirActEthDei5 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth5

       Possibilities:
               unchanged   (255)
               clear   (0)
               set   (1)"
   ::= {er1645v2Lan2FGIbwEntry 4099473408}

er1645v2Lan2FGIbwActEirActEthCos6 OBJECT-TYPE
   SYNTAX      INTEGER
               {
               unchanged (256)
               }
   MAX-ACCESS  read-write
   STATUS      current
   DESCRIPTION
      "Path: ethernet2.editConf.inboundBandwidth.action.eirAction.ethernet.cosDepth6

       Possibilities:
               unchanged   (256)"
   ::= {er1645v2Lan2FGIbwEntry 4098228224}

er1645v2Lan2FGIbwActEirActEthDei6 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth6

       Possibilities:
               unchanged   (255)
               clear   (0)
               set   (1)"
   ::= {er1645v2Lan2FGIbwEntry 4099538944}

er1645v2Lan2FGIbwActEirActEthCos7 OBJECT-TYPE
   SYNTAX      INTEGER
               {
               unchanged (256)
               }
   MAX-ACCESS  read-write
   STATUS      current
   DESCRIPTION
      "Path: ethernet2.editConf.inboundBandwidth.action.eirAction.ethernet.cosDepth7

       Possibilities:
               unchanged   (256)"
   ::= {er1645v2Lan2FGIbwEntry 4098293760}

er1645v2Lan2FGIbwActEirActEthDei7 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth7

       Possibilities:
               unchanged   (255)
               clear   (0)
               set   (1)"
   ::= {er1645v2Lan2FGIbwEntry 4099604480}

er1645v2Lan2FGIbwActEirActEthCos8 OBJECT-TYPE
   SYNTAX      INTEGER
               {
               unchanged (256)
               }
   MAX-ACCESS  read-write
   STATUS      current
   DESCRIPTION
      "Path: ethernet2.editConf.inboundBandwidth.action.eirAction.ethernet.cosDepth8

       Possibilities:
               unchanged   (256)"
   ::= {er1645v2Lan2FGIbwEntry 4098359296}

er1645v2Lan2FGIbwActEirActEthDei8 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth8

       Possibilities:
               unchanged   (255)
               clear   (0)
               set   (1)"
   ::= {er1645v2Lan2FGIbwEntry 4099670016}

er1645v2Lan2FGIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGIbwEntry 4098424832}

er1645v2Lan2FGIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGIbwEntry 4098490368}

er1645v2Lan2FGIbwActEirActEthDrpLev OBJECT-TYPE
   SYNTAX      INTEGER
               {
               unchanged (0)
               }
   MAX-ACCESS  read-write
   STATUS      current
   DESCRIPTION
      "Path: ethernet2.editConf.inboundBandwidth.action.eirAction.ethernet.dropLevel

       Possibilities:
               unchanged   (0)"
   ::= {er1645v2Lan2FGIbwEntry 4098555904}

er1645v2Lan2FGIbwActEirActEthDeFlag OBJECT-TYPE
   SYNTAX      INTEGER
               {
               unchanged (255),
               clear (0),
               set (1)
               }
   MAX-ACCESS  read-write
   STATUS      current
   DESCRIPTION
      "Path: ethernet2.editConf.inboundBandwidth.action.eirAction.ethernet.deFlag

       Possibilities:
               unchanged   (255)
               clear   (0)
               set   (1)"
   ::= {er1645v2Lan2FGIbwEntry 4098752512}

er1645v2Lan2FGIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGIbwEntry 4104716288}

er1645v2Lan2FGIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGIbwEntry 4104781824}

er1645v2Lan2FGIbwActEirActIpDrpLev OBJECT-TYPE
   SYNTAX      INTEGER
               {
               unchanged (0)
               }
   MAX-ACCESS  read-write
   STATUS      current
   DESCRIPTION
      "Path: ethernet2.editConf.inboundBandwidth.action.eirAction.ip.dropLevel

       Possibilities:
               unchanged   (0)"
   ::= {er1645v2Lan2FGIbwEntry 4104847360}

er1645v2Lan2FGIbwActEirActIpDeFlag OBJECT-TYPE
   SYNTAX      INTEGER
               {
               unchanged (255),
               clear (0),
               set (1)
               }
   MAX-ACCESS  read-write
   STATUS      current
   DESCRIPTION
      "Path: ethernet2.editConf.inboundBandwidth.action.eirAction.ip.deFlag

       Possibilities:
               unchanged   (255)
               clear   (0)
               set   (1)"
   ::= {er1645v2Lan2FGIbwEntry 4105043968}

er1645v2Lan2FGIbwActViolActNone OBJECT-TYPE
   SYNTAX      OCTET STRING
   MAX-ACCESS  read-write
   STATUS      current
   DESCRIPTION
      "Path: ethernet2.editConf.inboundBandwidth.action.violateAction.none"
   ::= {er1645v2Lan2FGIbwEntry 4129292288}

er1645v2Lan2FGIbwActViolActDrop OBJECT-TYPE
   SYNTAX      OCTET STRING
   MAX-ACCESS  read-write
   STATUS      current
   DESCRIPTION
      "Path: ethernet2.editConf.inboundBandwidth.action.violateAction.drop"
   ::= {er1645v2Lan2FGIbwEntry 4133486592}

er1645v2Lan2FGIbwActViolActEthCos1 OBJECT-TYPE
   SYNTAX      INTEGER
               {
               unchanged (256)
               }
   MAX-ACCESS  read-write
   STATUS      current
   DESCRIPTION
      "Path: ethernet2.editConf.inboundBandwidth.action.violateAction.ethernet.cosDepth1

       Possibilities:
               unchanged   (256)"
   ::= {er1645v2Lan2FGIbwEntry 4131454976}

er1645v2Lan2FGIbwActViolActEthDei1 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth1

       Possibilities:
               unchanged   (255)
               clear   (0)
               set   (1)"
   ::= {er1645v2Lan2FGIbwEntry 4132765696}

er1645v2Lan2FGIbwActViolActEthCos2 OBJECT-TYPE
   SYNTAX      INTEGER
               {
               unchanged (256)
               }
   MAX-ACCESS  read-write
   STATUS      current
   DESCRIPTION
      "Path: ethernet2.editConf.inboundBandwidth.action.violateAction.ethernet.cosDepth2

       Possibilities:
               unchanged   (256)"
   ::= {er1645v2Lan2FGIbwEntry 4131520512}

er1645v2Lan2FGIbwActViolActEthDei2 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth2

       Possibilities:
               unchanged   (255)
               clear   (0)
               set   (1)"
   ::= {er1645v2Lan2FGIbwEntry 4132831232}

er1645v2Lan2FGIbwActViolActEthCos3 OBJECT-TYPE
   SYNTAX      INTEGER
               {
               unchanged (256)
               }
   MAX-ACCESS  read-write
   STATUS      current
   DESCRIPTION
      "Path: ethernet2.editConf.inboundBandwidth.action.violateAction.ethernet.cosDepth3

       Possibilities:
               unchanged   (256)"
   ::= {er1645v2Lan2FGIbwEntry 4131586048}

er1645v2Lan2FGIbwActViolActEthDei3 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth3

       Possibilities:
               unchanged   (255)
               clear   (0)
               set   (1)"
   ::= {er1645v2Lan2FGIbwEntry 4132896768}

er1645v2Lan2FGIbwActViolActEthCos4 OBJECT-TYPE
   SYNTAX      INTEGER
               {
               unchanged (256)
               }
   MAX-ACCESS  read-write
   STATUS      current
   DESCRIPTION
      "Path: ethernet2.editConf.inboundBandwidth.action.violateAction.ethernet.cosDepth4

       Possibilities:
               unchanged   (256)"
   ::= {er1645v2Lan2FGIbwEntry 4131651584}

er1645v2Lan2FGIbwActViolActEthDei4 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth4

       Possibilities:
               unchanged   (255)
               clear   (0)
               set   (1)"
   ::= {er1645v2Lan2FGIbwEntry 4132962304}

er1645v2Lan2FGIbwActViolActEthCos5 OBJECT-TYPE
   SYNTAX      INTEGER
               {
               unchanged (256)
               }
   MAX-ACCESS  read-write
   STATUS      current
   DESCRIPTION
      "Path: ethernet2.editConf.inboundBandwidth.action.violateAction.ethernet.cosDepth5

       Possibilities:
               unchanged   (256)"
   ::= {er1645v2Lan2FGIbwEntry 4131717120}

er1645v2Lan2FGIbwActViolActEthDei5 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth5

       Possibilities:
               unchanged   (255)
               clear   (0)
               set   (1)"
   ::= {er1645v2Lan2FGIbwEntry 4133027840}

er1645v2Lan2FGIbwActViolActEthCos6 OBJECT-TYPE
   SYNTAX      INTEGER
               {
               unchanged (256)
               }
   MAX-ACCESS  read-write
   STATUS      current
   DESCRIPTION
      "Path: ethernet2.editConf.inboundBandwidth.action.violateAction.ethernet.cosDepth6

       Possibilities:
               unchanged   (256)"
   ::= {er1645v2Lan2FGIbwEntry 4131782656}

er1645v2Lan2FGIbwActViolActEthDei6 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth6

       Possibilities:
               unchanged   (255)
               clear   (0)
               set   (1)"
   ::= {er1645v2Lan2FGIbwEntry 4133093376}

er1645v2Lan2FGIbwActViolActEthCos7 OBJECT-TYPE
   SYNTAX      INTEGER
               {
               unchanged (256)
               }
   MAX-ACCESS  read-write
   STATUS      current
   DESCRIPTION
      "Path: ethernet2.editConf.inboundBandwidth.action.violateAction.ethernet.cosDepth7

       Possibilities:
               unchanged   (256)"
   ::= {er1645v2Lan2FGIbwEntry 4131848192}

er1645v2Lan2FGIbwActViolActEthDei7 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth7

       Possibilities:
               unchanged   (255)
               clear   (0)
               set   (1)"
   ::= {er1645v2Lan2FGIbwEntry 4133158912}

er1645v2Lan2FGIbwActViolActEthCos8 OBJECT-TYPE
   SYNTAX      INTEGER
               {
               unchanged (256)
               }
   MAX-ACCESS  read-write
   STATUS      current
   DESCRIPTION
      "Path: ethernet2.editConf.inboundBandwidth.action.violateAction.ethernet.cosDepth8

       Possibilities:
               unchanged   (256)"
   ::= {er1645v2Lan2FGIbwEntry 4131913728}

er1645v2Lan2FGIbwActViolActEthDei8 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth8

       Possibilities:
               unchanged   (255)
               clear   (0)
               set   (1)"
   ::= {er1645v2Lan2FGIbwEntry 4133224448}

er1645v2Lan2FGIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGIbwEntry 4131979264}

er1645v2Lan2FGIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGIbwEntry 4132044800}

er1645v2Lan2FGIbwActViolActEthDrpLev OBJECT-TYPE
   SYNTAX      INTEGER
               {
               unchanged (0)
               }
   MAX-ACCESS  read-write
   STATUS      current
   DESCRIPTION
      "Path: ethernet2.editConf.inboundBandwidth.action.violateAction.ethernet.dropLevel

       Possibilities:
               unchanged   (0)"
   ::= {er1645v2Lan2FGIbwEntry 4132110336}

er1645v2Lan2FGIbwActViolActEthDeFlag OBJECT-TYPE
   SYNTAX      INTEGER
               {
               unchanged (255),
               clear (0),
               set (1)
               }
   MAX-ACCESS  read-write
   STATUS      current
   DESCRIPTION
      "Path: ethernet2.editConf.inboundBandwidth.action.violateAction.ethernet.deFlag

       Possibilities:
               unchanged   (255)
               clear   (0)
               set   (1)"
   ::= {er1645v2Lan2FGIbwEntry 4132306944}

er1645v2Lan2FGIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGIbwEntry 4138270720}

er1645v2Lan2FGIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGIbwEntry 4138336256}

er1645v2Lan2FGIbwActViolActIpDrpLev OBJECT-TYPE
   SYNTAX      INTEGER
               {
               unchanged (0)
               }
   MAX-ACCESS  read-write
   STATUS      current
   DESCRIPTION
      "Path: ethernet2.editConf.inboundBandwidth.action.violateAction.ip.dropLevel

       Possibilities:
               unchanged   (0)"
   ::= {er1645v2Lan2FGIbwEntry 4138401792}

er1645v2Lan2FGIbwActViolActIpDeFlag OBJECT-TYPE
   SYNTAX      INTEGER
               {
               unchanged (255),
               clear (0),
               set (1)
               }
   MAX-ACCESS  read-write
   STATUS      current
   DESCRIPTION
      "Path: ethernet2.editConf.inboundBandwidth.action.violateAction.ip.deFlag

       Possibilities:
               unchanged   (255)
               clear   (0)
               set   (1)"
   ::= {er1645v2Lan2FGIbwEntry 4138598400}

er1645v2Lan2FGIbwSubInterfacesExcluded OBJECT-TYPE
   SYNTAX      INTEGER
               {
               s (1)
               }
   MAX-ACCESS  read-write
   STATUS      current
   DESCRIPTION
      "Path: ethernet2.editConf.inboundBandwidth.subInterfaces.excluded

       Possibilities:
                  (1)"
   ::= {er1645v2Lan2FGIbwEntry 2416967680}

er1645v2Lan2FGIbwSubInterfacesIncludedInAccessList OBJECT-TYPE
   SYNTAX      DisplayString
   MAX-ACCESS  read-write
   STATUS      current
   DESCRIPTION
      "Path: ethernet2.editConf.inboundBandwidth.subInterfaces.included.inAccessList"
   ::= {er1645v2Lan2FGIbwEntry 2418020352}


er1645v2Lan2FGPriorityPolicy OBJECT-TYPE
   SYNTAX      DisplayString
   MAX-ACCESS  read-write
   STATUS      current
   DESCRIPTION
      "Path: ethernet2.editConf.priorityPolicy
       Info: Preferred Policy"
   ::= {er1645v2Lan2FG 39}


er1645v2Lan2FGMru OBJECT-TYPE
   SYNTAX      Integer32
   MAX-ACCESS  read-write
   STATUS      current
   DESCRIPTION
      "Path: ethernet2.editConf.mru"
   ::= {er1645v2Lan2FG 43}


er1645v2Lan2FGDelayOptimisation OBJECT-TYPE
   SYNTAX      INTEGER
               {
               disabled (0),
               enabled (1)
               }
   MAX-ACCESS  read-write
   STATUS      current
   DESCRIPTION
      "Path: ethernet2.editConf.delayOptimisation
       Info: optimise delay

       Possibilities:
               disabled   (0)
               enabled   (1)"
   ::= {er1645v2Lan2FG 80}


er1645v2Lan2FGAlarmMask OBJECT-TYPE
   SYNTAX      Integer32
   MAX-ACCESS  read-write
   STATUS      current
   DESCRIPTION
      "Path: ethernet2.editConf.alarmMask
       Info: ifAlarmMask

       Bit meanings:
               bit 0 = linkDown,
               bit 9 = pppoEDown"
   ::= {er1645v2Lan2FG 135}


er1645v2Lan2FGAlarmLev OBJECT IDENTIFIER ::= {er1645v2Lan2FG 170}

er1645v2Lan2FGAlarmLevSSC OBJECT IDENTIFIER ::= {er1645v2Lan2FGAlarmLev 1}

er1645v2Lan2FGAlarmLevEntry OBJECT IDENTIFIER ::= {er1645v2Lan2FGAlarmLevSSC 1}

er1645v2Lan2FGAlarmLevLinkDown OBJECT-TYPE
   SYNTAX      Integer32
   MAX-ACCESS  read-write
   STATUS      current
   DESCRIPTION
      "Path: ethernet2.editConf.alarmLevel.linkDown"
   ::= {er1645v2Lan2FGAlarmLevEntry 16777216}

er1645v2Lan2FGAlarmLevPppoEDown OBJECT-TYPE
   SYNTAX      Integer32
   MAX-ACCESS  read-write
   STATUS      current
   DESCRIPTION
      "Path: ethernet2.editConf.alarmLevel.pppoEDown"
   ::= {er1645v2Lan2FGAlarmLevEntry 167772160}


er1645v2Lan2FGArp OBJECT IDENTIFIER ::= {er1645v2Lan2FG 19}

er1645v2Lan2FGArpSSC OBJECT IDENTIFIER ::= {er1645v2Lan2FGArp 1}

er1645v2Lan2FGArpEntry OBJECT IDENTIFIER ::= {er1645v2Lan2FGArpSSC 1}

er1645v2Lan2FGArpTimeOut OBJECT-TYPE
   SYNTAX      TimeTicks
   MAX-ACCESS  read-write
   STATUS      current
   DESCRIPTION
      "Path: ethernet2.editConf.arp.timeOut

       Time in centi-second."
   ::= {er1645v2Lan2FGArpEntry 201326592}

er1645v2Lan2FGArpProxyArp OBJECT-TYPE
   SYNTAX      INTEGER
               {
               disabled (0),
               enabled (1)
               }
   MAX-ACCESS  read-write
   STATUS      current
   DESCRIPTION
      "Path: ethernet2.editConf.arp.proxyArp

       Possibilities:
               disabled   (0)
               enabled   (1)"
   ::= {er1645v2Lan2FGArpEntry 838860800}

er1645v2Lan2FGArpStaticArp OBJECT-TYPE
   SYNTAX      SEQUENCE OF Er1645v2Lan2FGArpStaticArpEntry
   MAX-ACCESS  not-accessible
   STATUS      current
   DESCRIPTION
      ""
   ::= {er1645v2Lan2FGArp 50331648}

er1645v2Lan2FGArpStaticArpEntry OBJECT-TYPE
   SYNTAX      Er1645v2Lan2FGArpStaticArpEntry
   MAX-ACCESS  not-accessible
   STATUS      current
   DESCRIPTION
      ""
   INDEX      { er1645v2Lan2FGArpStaticArpTableIx }
   ::= {er1645v2Lan2FGArpStaticArp 1}

Er1645v2Lan2FGArpStaticArpEntry ::=
   SEQUENCE
      {
      er1645v2Lan2FGArpStaticArpActions
         VariableLengthTableActions,
      er1645v2Lan2FGArpStaticArpTableIx
         TableIndex,
      er1645v2Lan2FGArpStaticArpMacAddress
         OCTET STRING,
      er1645v2Lan2FGArpStaticArpIpAddress
         IpAddress
      }

er1645v2Lan2FGArpStaticArpActions OBJECT-TYPE
   SYNTAX      VariableLengthTableActions
   MAX-ACCESS  read-write
   STATUS      current
   DESCRIPTION
      "By way of this field, some manipulations
       on this table may be performed."
   ::= {er1645v2Lan2FGArpStaticArpEntry 2}

er1645v2Lan2FGArpStaticArpTableIx OBJECT-TYPE
   SYNTAX      TableIndex
   MAX-ACCESS  not-accessible
   STATUS      current
   DESCRIPTION
      ""
   ::= {er1645v2Lan2FGArpStaticArpEntry 11}

er1645v2Lan2FGArpStaticArpMacAddress OBJECT-TYPE
   SYNTAX      OCTET STRING
   MAX-ACCESS  read-write
   STATUS      current
   DESCRIPTION
      "Path: ethernet2.editConf.arp.staticArp.macAddress

       MAC address."
   ::= {er1645v2Lan2FGArpStaticArpEntry 16777216}

er1645v2Lan2FGArpStaticArpIpAddress OBJECT-TYPE
   SYNTAX      IpAddress
   MAX-ACCESS  read-write
   STATUS      current
   DESCRIPTION
      "Path: ethernet2.editConf.arp.staticArp.ipAddress"
   ::= {er1645v2Lan2FGArpStaticArpEntry 33554432}


er1645v2Lan2FGBrC OBJECT IDENTIFIER ::= {er1645v2Lan2FG 27}

er1645v2Lan2FGBrCSSC OBJECT IDENTIFIER ::= {er1645v2Lan2FGBrC 1}

er1645v2Lan2FGBrCEntry OBJECT IDENTIFIER ::= {er1645v2Lan2FGBrCSSC 1}

er1645v2Lan2FGBrCAccessList OBJECT-TYPE
   SYNTAX      DisplayString
   MAX-ACCESS  read-write
   STATUS      current
   DESCRIPTION
      "Path: ethernet2.editConf.bridging.accessList"
   ::= {er1645v2Lan2FGBrCEntry 83886080}

er1645v2Lan2FGBrCInAccessList OBJECT-TYPE
   SYNTAX      DisplayString
   MAX-ACCESS  read-write
   STATUS      current
   DESCRIPTION
      "Path: ethernet2.editConf.bridging.inAccessList"
   ::= {er1645v2Lan2FGBrCEntry 251658240}

er1645v2Lan2FGBrCTp OBJECT-TYPE
   SYNTAX      DisplayString
   MAX-ACCESS  read-write
   STATUS      current
   DESCRIPTION
      "Path: ethernet2.editConf.bridging.trafficPolicy"
   ::= {er1645v2Lan2FGBrCEntry 100663296}

er1645v2Lan2FGBrCBridgeGroup OBJECT-TYPE
   SYNTAX      DisplayString
   MAX-ACCESS  read-write
   STATUS      current
   DESCRIPTION
      "Path: ethernet2.editConf.bridging.bridgeGroup"
   ::= {er1645v2Lan2FGBrCEntry 117440512}

er1645v2Lan2FGBrCLimBC OBJECT-TYPE
   SYNTAX      INTEGER
               {
               disabled (0),
               enabled (1)
               }
   MAX-ACCESS  read-write
   STATUS      current
   DESCRIPTION
      "Path: ethernet2.editConf.bridging.limitBroadcasts

       Possibilities:
               disabled   (0)
               enabled   (1)"
   ::= {er1645v2Lan2FGBrCEntry 134217728}

er1645v2Lan2FGBrCPrivateMode OBJECT-TYPE
   SYNTAX      INTEGER
               {
               disabled (0),
               enabled (1)
               }
   MAX-ACCESS  read-write
   STATUS      current
   DESCRIPTION
      "Path: ethernet2.editConf.bridging.privateMode

       Possibilities:
               disabled   (0)
               enabled   (1)"
   ::= {er1645v2Lan2FGBrCEntry 419430400}

er1645v2Lan2FGBrCLearning OBJECT-TYPE
   SYNTAX      INTEGER
               {
               disabled (0),
               enabled (1)
               }
   MAX-ACCESS  read-write
   STATUS      current
   DESCRIPTION
      "Path: ethernet2.editConf.bridging.learning

       Possibilities:
               disabled   (0)
               enabled   (1)"
   ::= {er1645v2Lan2FGBrCEntry 201326592}

er1645v2Lan2FGBrCMaxCacheSize OBJECT-TYPE
   SYNTAX      INTEGER
               {
               unlimited (0)
               }
   MAX-ACCESS  read-write
   STATUS      current
   DESCRIPTION
      "Path: ethernet2.editConf.bridging.maxCacheSize

       Possibilities:
               unlimited   (0)"
   ::= {er1645v2Lan2FGBrCEntry 218103808}

er1645v2Lan2FGBrCRelearnDropOnRelearn OBJECT-TYPE
   SYNTAX      INTEGER
               {
               disabled (0),
               enabled (1)
               }
   MAX-ACCESS  read-write
   STATUS      current
   DESCRIPTION
      "Path: ethernet2.editConf.bridging.relearn.dropOnRelearn

       Possibilities:
               disabled   (0)
               enabled   (1)"
   ::= {er1645v2Lan2FGBrCEntry 234946560}

er1645v2Lan2FGBrCRelearnShutdownThreshold OBJECT-TYPE
   SYNTAX      Integer32
   MAX-ACCESS  read-write
   STATUS      current
   DESCRIPTION
      "Path: ethernet2.editConf.bridging.relearn.shutdownThreshold"
   ::= {er1645v2Lan2FGBrCEntry 235012096}

er1645v2Lan2FGBrCRelearnShutdownTime OBJECT-TYPE
   SYNTAX      TimeTicks
   MAX-ACCESS  read-write
   STATUS      current
   DESCRIPTION
      "Path: ethernet2.editConf.bridging.relearn.shutdownTime

       Time in centi-second."
   ::= {er1645v2Lan2FGBrCEntry 235077632}

er1645v2Lan2FGBrCRelearnLoopDetection OBJECT-TYPE
   SYNTAX      INTEGER
               {
               disabled (0),
               passive (1),
               active (2)
               }
   MAX-ACCESS  read-write
   STATUS      current
   DESCRIPTION
      "Path: ethernet2.editConf.bridging.relearn.loopDetection

       Possibilities:
               disabled   (0)
               passive   (1)
               active   (2)"
   ::= {er1645v2Lan2FGBrCEntry 235143168}

er1645v2Lan2FGBrCRelearnLoopDetectionInterval OBJECT-TYPE
   SYNTAX      TimeTicks
   MAX-ACCESS  read-write
   STATUS      current
   DESCRIPTION
      "Path: ethernet2.editConf.bridging.relearn.loopDetectionInterval

       Time in centi-second."
   ::= {er1645v2Lan2FGBrCEntry 235208704}

er1645v2Lan2FGBrCVlanMemberShip OBJECT-TYPE
   SYNTAX      INTEGER
               {
               all (0),
               none (1),
               grouped (2)
               }
   MAX-ACCESS  read-write
   STATUS      current
   DESCRIPTION
      "Path: ethernet2.editConf.bridging.vlanMemberShip

       Possibilities:
               all   (0)
               none   (1)
               grouped   (2)"
   ::= {er1645v2Lan2FGBrCEntry 318767104}

er1645v2Lan2FGBrCDot1adType OBJECT-TYPE
   SYNTAX      INTEGER
               {
               slOPTg (0),
               cPort (4),
               sPort (1),
               nni (2)
               }
   MAX-ACCESS  read-write
   STATUS      current
   DESCRIPTION
      "Path: ethernet2.editConf.bridging.dot1ad.type

       Possibilities:
               <OPT>   (0)
               cPort   (4)
               sPort   (1)
               nni   (2)"
   ::= {er1645v2Lan2FGBrCEntry 503382016}

er1645v2Lan2FGBrCPriority OBJECT-TYPE
   SYNTAX      Integer32
   MAX-ACCESS  read-write
   STATUS      current
   DESCRIPTION
      "Path: ethernet2.editConf.bridging.priority"
   ::= {er1645v2Lan2FGBrCEntry 33554432}

er1645v2Lan2FGBrCPathCost OBJECT-TYPE
   SYNTAX      Integer32
   MAX-ACCESS  read-write
   STATUS      current
   DESCRIPTION
      "Path: ethernet2.editConf.bridging.pathCost"
   ::= {er1645v2Lan2FGBrCEntry 50331648}

er1645v2Lan2FGBrCInternalPathCost OBJECT-TYPE
   SYNTAX      Integer32
   MAX-ACCESS  read-write
   STATUS      current
   DESCRIPTION
      "Path: ethernet2.editConf.bridging.internalPathCost"
   ::= {er1645v2Lan2FGBrCEntry 301989888}

er1645v2Lan2FGBrCTCD OBJECT-TYPE
   SYNTAX      INTEGER
               {
               disabled (0),
               enabled (1)
               }
   MAX-ACCESS  read-write
   STATUS      current
   DESCRIPTION
      "Path: ethernet2.editConf.bridging.topologyChangeDetection

       Possibilities:
               disabled   (0)
               enabled   (1)"
   ::= {er1645v2Lan2FGBrCEntry 67108864}

er1645v2Lan2FGBrCRestrictedRole OBJECT-TYPE
   SYNTAX      INTEGER
               {
               disabled (0),
               enabled (1)
               }
   MAX-ACCESS  read-write
   STATUS      current
   DESCRIPTION
      "Path: ethernet2.editConf.bridging.restrictedRole

       Possibilities:
               disabled   (0)
               enabled   (1)"
   ::= {er1645v2Lan2FGBrCEntry 335544320}

er1645v2Lan2FGBrCAdminEdge OBJECT-TYPE
   SYNTAX      INTEGER
               {
               disabled (0),
               enabled (1)
               }
   MAX-ACCESS  read-write
   STATUS      current
   DESCRIPTION
      "Path: ethernet2.editConf.bridging.adminEdge

       Possibilities:
               disabled   (0)
               enabled   (1)"
   ::= {er1645v2Lan2FGBrCEntry 268435456}

er1645v2Lan2FGBrCMgmtInline OBJECT-TYPE
   SYNTAX      INTEGER
               {
               disabled (0),
               enabled (1)
               }
   MAX-ACCESS  read-write
   STATUS      current
   DESCRIPTION
      "Path: ethernet2.editConf.bridging.mgmtInline

       Possibilities:
               disabled   (0)
               enabled   (1)"
   ::= {er1645v2Lan2FGBrCEntry 369098752}

er1645v2Lan2FGBrCL2ptMode OBJECT-TYPE
   SYNTAX      INTEGER
               {
               disabled (0),
               enabled (1)
               }
   MAX-ACCESS  read-write
   STATUS      current
   DESCRIPTION
      "Path: ethernet2.editConf.bridging.l2ProtTunnel.mode

       Possibilities:
               disabled   (0)
               enabled   (1)"
   ::= {er1645v2Lan2FGBrCEntry 403701760}

er1645v2Lan2FGBrCL2ptProtocols OBJECT-TYPE
   SYNTAX      Integer32
   MAX-ACCESS  read-write
   STATUS      current
   DESCRIPTION
      "Path: ethernet2.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan2FGBrCEntry 404750336}

er1645v2Lan2FGBrCL2ptDestMac OBJECT-TYPE
   SYNTAX      OCTET STRING
   MAX-ACCESS  read-write
   STATUS      current
   DESCRIPTION
      "Path: ethernet2.editConf.bridging.l2ProtTunnel.destinationMac

       MAC address."
   ::= {er1645v2Lan2FGBrCEntry 405798912}

er1645v2Lan2FGBrCL2ptCos OBJECT-TYPE
   SYNTAX      INTEGER
               {
               unchanged (255)
               }
   MAX-ACCESS  read-write
   STATUS      current
   DESCRIPTION
      "Path: ethernet2.editConf.bridging.l2ProtTunnel.cos

       Possibilities:
               unchanged   (255)"
   ::= {er1645v2Lan2FGBrCEntry 406847488}

er1645v2Lan2FGBrCL2ptDropThrStp OBJECT-TYPE
   SYNTAX      INTEGER
               {
               unlimited (0)
               }
   UNITS       "packets/sec"
   MAX-ACCESS  read-write
   STATUS      current
   DESCRIPTION
      "Path: ethernet2.editConf.bridging.l2ProtTunnel.dropThresholds.stp

       unit name = packets/sec

       Possibilities:
               unlimited   (0)"
   ::= {er1645v2Lan2FGBrCEntry 407900160}

er1645v2Lan2FGBrCL2ptDropThrLldp OBJECT-TYPE
   SYNTAX      INTEGER
               {
               unlimited (0)
               }
   UNITS       "packets/sec"
   MAX-ACCESS  read-write
   STATUS      current
   DESCRIPTION
      "Path: ethernet2.editConf.bridging.l2ProtTunnel.dropThresholds.lldp

       unit name = packets/sec

       Possibilities:
               unlimited   (0)"
   ::= {er1645v2Lan2FGBrCEntry 407904256}

er1645v2Lan2FGBrCL2ptDropThrOam OBJECT-TYPE
   SYNTAX      INTEGER
               {
               unlimited (0)
               }
   UNITS       "packets/sec"
   MAX-ACCESS  read-write
   STATUS      current
   DESCRIPTION
      "Path: ethernet2.editConf.bridging.l2ProtTunnel.dropThresholds.oam

       unit name = packets/sec

       Possibilities:
               unlimited   (0)"
   ::= {er1645v2Lan2FGBrCEntry 407908352}

er1645v2Lan2FGBrCL2ptDropThrCdp OBJECT-TYPE
   SYNTAX      INTEGER
               {
               unlimited (0)
               }
   UNITS       "packets/sec"
   MAX-ACCESS  read-write
   STATUS      current
   DESCRIPTION
      "Path: ethernet2.editConf.bridging.l2ProtTunnel.dropThresholds.cdp

       unit name = packets/sec

       Possibilities:
               unlimited   (0)"
   ::= {er1645v2Lan2FGBrCEntry 407912448}

er1645v2Lan2FGBrCL2ptDropThrVtp OBJECT-TYPE
   SYNTAX      INTEGER
               {
               unlimited (0)
               }
   UNITS       "packets/sec"
   MAX-ACCESS  read-write
   STATUS      current
   DESCRIPTION
      "Path: ethernet2.editConf.bridging.l2ProtTunnel.dropThresholds.vtp

       unit name = packets/sec

       Possibilities:
               unlimited   (0)"
   ::= {er1645v2Lan2FGBrCEntry 407916544}

er1645v2Lan2FGBrCL2ptDropThrLacp OBJECT-TYPE
   SYNTAX      INTEGER
               {
               unlimited (0)
               }
   UNITS       "packets/sec"
   MAX-ACCESS  read-write
   STATUS      current
   DESCRIPTION
      "Path: ethernet2.editConf.bridging.l2ProtTunnel.dropThresholds.lacp

       unit name = packets/sec

       Possibilities:
               unlimited   (0)"
   ::= {er1645v2Lan2FGBrCEntry 407920640}

er1645v2Lan2FGBrCL2ptDropThrEfmOam OBJECT-TYPE
   SYNTAX      INTEGER
               {
               unlimited (0)
               }
   UNITS       "packets/sec"
   MAX-ACCESS  read-write
   STATUS      current
   DESCRIPTION
      "Path: ethernet2.editConf.bridging.l2ProtTunnel.dropThresholds.efmOam

       unit name = packets/sec

       Possibilities:
               unlimited   (0)"
   ::= {er1645v2Lan2FGBrCEntry 407924736}

er1645v2Lan2FGBrCL2ptDropThrPvst OBJECT-TYPE
   SYNTAX      INTEGER
               {
               unlimited (0)
               }
   UNITS       "packets/sec"
   MAX-ACCESS  read-write
   STATUS      current
   DESCRIPTION
      "Path: ethernet2.editConf.bridging.l2ProtTunnel.dropThresholds.pvst

       unit name = packets/sec

       Possibilities:
               unlimited   (0)"
   ::= {er1645v2Lan2FGBrCEntry 407928832}

er1645v2Lan2FGBrCL2ptDropThrMmrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.mmrp

       unit name = packets/sec

       Possibilities:
               unlimited   (0)"
   ::= {er1645v2Lan2FGBrCEntry 407932928}

er1645v2Lan2FGBrCL2ptDropThrMvrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.mvrp

       unit name = packets/sec

       Possibilities:
               unlimited   (0)"
   ::= {er1645v2Lan2FGBrCEntry 407937024}

er1645v2Lan2FGBrCL2ptDropThrGvrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.gvrp

       unit name = packets/sec

       Possibilities:
               unlimited   (0)"
   ::= {er1645v2Lan2FGBrCEntry 407941120}

er1645v2Lan2FGBrCL2ptDropThrGmrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.gmrp

       unit name = packets/sec

       Possibilities:
               unlimited   (0)"
   ::= {er1645v2Lan2FGBrCEntry 407945216}

er1645v2Lan2FGBrCL2ptDropThrDtp OBJECT-TYPE
   SYNTAX      INTEGER
               {
               unlimited (0)
               }
   UNITS       "packets/sec"
   MAX-ACCESS  read-write
   STATUS      current
   DESCRIPTION
      "Path: ethernet2.editConf.bridging.l2ProtTunnel.dropThresholds.dtp

       unit name = packets/sec

       Possibilities:
               unlimited   (0)"
   ::= {er1645v2Lan2FGBrCEntry 407949312}

er1645v2Lan2FGBrCL2ptDropThrPagp OBJECT-TYPE
   SYNTAX      INTEGER
               {
               unlimited (0)
               }
   UNITS       "packets/sec"
   MAX-ACCESS  read-write
   STATUS      current
   DESCRIPTION
      "Path: ethernet2.editConf.bridging.l2ProtTunnel.dropThresholds.pagp

       unit name = packets/sec

       Possibilities:
               unlimited   (0)"
   ::= {er1645v2Lan2FGBrCEntry 407953408}

er1645v2Lan2FGBrCL2ptDropThrUdld OBJECT-TYPE
   SYNTAX      INTEGER
               {
               unlimited (0)
               }
   UNITS       "packets/sec"
   MAX-ACCESS  read-write
   STATUS      current
   DESCRIPTION
      "Path: ethernet2.editConf.bridging.l2ProtTunnel.dropThresholds.udld

       unit name = packets/sec

       Possibilities:
               unlimited   (0)"
   ::= {er1645v2Lan2FGBrCEntry 407957504}


er1645v2Lan2FGVlanTagging OBJECT IDENTIFIER ::= {er1645v2Lan2FG 14}

er1645v2Lan2FGVlanTaggingSSC OBJECT IDENTIFIER ::= {er1645v2Lan2FGVlanTagging 1}

er1645v2Lan2FGVlanTaggingEntry OBJECT IDENTIFIER ::= {er1645v2Lan2FGVlanTaggingSSC 1}

er1645v2Lan2FGVlanTaggingUntaggedAction OBJECT-TYPE
   SYNTAX      INTEGER
               {
               discard (0),
               accept (1),
               tag (2)
               }
   MAX-ACCESS  read-write
   STATUS      current
   DESCRIPTION
      "Path: ethernet2.editConf.vlanTagging.untagged.action

       Possibilities:
               discard   (0)
               accept   (1)
               tag   (2)"
   ::= {er1645v2Lan2FGVlanTaggingEntry 671088640}

er1645v2Lan2FGVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.untagged.tagInfo.tpid

       Possibilities:
               dot1Q   (33024)
               dot1ad   (34984)
               0x9100   (37120)
               0x9200   (37376)
               0x9300   (37632)"
   ::= {er1645v2Lan2FGVlanTaggingEntry 746586112}

er1645v2Lan2FGVlanTaggingUntaggedTagInfoVid OBJECT-TYPE
   SYNTAX      Integer32
   MAX-ACCESS  read-write
   STATUS      current
   DESCRIPTION
      "Path: ethernet2.editConf.vlanTagging.untagged.tagInfo.vid"
   ::= {er1645v2Lan2FGVlanTaggingEntry 754974720}

er1645v2Lan2FGVlanTaggingUnknownVlansAction OBJECT-TYPE
   SYNTAX      INTEGER
               {
               discard (0),
               accept (1),
               tag (2)
               }
   MAX-ACCESS  read-write
   STATUS      current
   DESCRIPTION
      "Path: ethernet2.editConf.vlanTagging.unknownVlans.action

       Possibilities:
               discard   (0)
               accept   (1)
               tag   (2)"
   ::= {er1645v2Lan2FGVlanTaggingEntry 1744830464}

er1645v2Lan2FGVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.unknownVlans.tagInfo.tpid

       Possibilities:
               dot1Q   (33024)
               dot1ad   (34984)
               0x9100   (37120)
               0x9200   (37376)
               0x9300   (37632)"
   ::= {er1645v2Lan2FGVlanTaggingEntry 1820327936}

er1645v2Lan2FGVlanTaggingUnknownVlansTagInfoVid OBJECT-TYPE
   SYNTAX      Integer32
   MAX-ACCESS  read-write
   STATUS      current
   DESCRIPTION
      "Path: ethernet2.editConf.vlanTagging.unknownVlans.tagInfo.vid"
   ::= {er1645v2Lan2FGVlanTaggingEntry 1828716544}

er1645v2Lan2FGVlanTaggingVlans OBJECT-TYPE
   SYNTAX      SEQUENCE OF Er1645v2Lan2FGVlanTaggingVlansEntry
   MAX-ACCESS  not-accessible
   STATUS      current
   DESCRIPTION
      ""
   ::= {er1645v2Lan2FGVlanTagging 1073741824}

er1645v2Lan2FGVlanTaggingVlansEntry OBJECT-TYPE
   SYNTAX      Er1645v2Lan2FGVlanTaggingVlansEntry
   MAX-ACCESS  not-accessible
   STATUS      current
   DESCRIPTION
      ""
   INDEX      { er1645v2Lan2FGVlanTaggingVlansTableIx }
   ::= {er1645v2Lan2FGVlanTaggingVlans 1}

Er1645v2Lan2FGVlanTaggingVlansEntry ::=
   SEQUENCE
      {
      er1645v2Lan2FGVlanTaggingVlansActions
         VariableLengthTableActions,
      er1645v2Lan2FGVlanTaggingVlansTableIx
         TableIndex,
      er1645v2Lan2FGVlanTaggingVlansVid
         Integer32,
      er1645v2Lan2FGVlanTaggingVlansEndVid
         Integer32,
      er1645v2Lan2FGVlanTaggingVlansAction
         INTEGER,
      er1645v2Lan2FGVlanTaggingVlansTagInfoTpid
         INTEGER,
      er1645v2Lan2FGVlanTaggingVlansTagInfoVid
         Integer32
      }

er1645v2Lan2FGVlanTaggingVlansActions OBJECT-TYPE
   SYNTAX      VariableLengthTableActions
   MAX-ACCESS  read-write
   STATUS      current
   DESCRIPTION
      "By way of this field, some manipulations
       on this table may be performed."
   ::= {er1645v2Lan2FGVlanTaggingVlansEntry 2}

er1645v2Lan2FGVlanTaggingVlansTableIx OBJECT-TYPE
   SYNTAX      TableIndex
   MAX-ACCESS  not-accessible
   STATUS      current
   DESCRIPTION
      ""
   ::= {er1645v2Lan2FGVlanTaggingVlansEntry 11}

er1645v2Lan2FGVlanTaggingVlansVid OBJECT-TYPE
   SYNTAX      Integer32
   MAX-ACCESS  read-write
   STATUS      current
   DESCRIPTION
      "Path: ethernet2.editConf.vlanTagging.vlans.vid"
   ::= {er1645v2Lan2FGVlanTaggingVlansEntry 536870912}

er1645v2Lan2FGVlanTaggingVlansEndVid OBJECT-TYPE
   SYNTAX      Integer32
   MAX-ACCESS  read-write
   STATUS      current
   DESCRIPTION
      "Path: ethernet2.editConf.vlanTagging.vlans.endVid"
   ::= {er1645v2Lan2FGVlanTaggingVlansEntry 2147483648}

er1645v2Lan2FGVlanTaggingVlansAction OBJECT-TYPE
   SYNTAX      INTEGER
               {
               discard (0),
               accept (1),
               tag (2)
               }
   MAX-ACCESS  read-write
   STATUS      current
   DESCRIPTION
      "Path: ethernet2.editConf.vlanTagging.vlans.action

       Possibilities:
               discard   (0)
               accept   (1)
               tag   (2)"
   ::= {er1645v2Lan2FGVlanTaggingVlansEntry 1073741824}

er1645v2Lan2FGVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.vlans.tagInfo.tpid

       Possibilities:
               dot1Q   (33024)
               dot1ad   (34984)
               0x9100   (37120)
               0x9200   (37376)
               0x9300   (37632)"
   ::= {er1645v2Lan2FGVlanTaggingVlansEntry 1677721600}

er1645v2Lan2FGVlanTaggingVlansTagInfoVid OBJECT-TYPE
   SYNTAX      Integer32
   MAX-ACCESS  read-write
   STATUS      current
   DESCRIPTION
      "Path: ethernet2.editConf.vlanTagging.vlans.tagInfo.vid"
   ::= {er1645v2Lan2FGVlanTaggingVlansEntry 1744830464}


er1645v2Lan2FGOam OBJECT IDENTIFIER ::= {er1645v2Lan2FG 900}

er1645v2Lan2FGOamSSC OBJECT IDENTIFIER ::= {er1645v2Lan2FGOam 1}

er1645v2Lan2FGOamEntry OBJECT IDENTIFIER ::= {er1645v2Lan2FGOamSSC 1}

er1645v2Lan2FGOamMode OBJECT-TYPE
   SYNTAX      INTEGER
               {
               disabled (0),
               passive (3),
               active (2)
               }
   MAX-ACCESS  read-write
   STATUS      current
   DESCRIPTION
      "Path: ethernet2.editConf.oam.mode

       Possibilities:
               disabled   (0)
               passive   (3)
               active   (2)"
   ::= {er1645v2Lan2FGOamEntry 16777216}

er1645v2Lan2FGOamLpbkLocalParAction OBJECT-TYPE
   SYNTAX      INTEGER
               {
               discard (0),
               forward (1)
               }
   MAX-ACCESS  read-write
   STATUS      current
   DESCRIPTION
      "Path: ethernet2.editConf.oam.loopbackLocalParserAction

       Possibilities:
               discard   (0)
               forward   (1)"
   ::= {er1645v2Lan2FGOamEntry 33554432}

er1645v2Lan2FGOamLpbkSwapMacAddr OBJECT-TYPE
   SYNTAX      INTEGER
               {
               disabled (0),
               enabled (1)
               }
   MAX-ACCESS  read-write
   STATUS      current
   DESCRIPTION
      "Path: ethernet2.editConf.oam.loopbackSwapMacAddresses

       Possibilities:
               disabled   (0)
               enabled   (1)"
   ::= {er1645v2Lan2FGOamEntry 50331648}

er1645v2Lan2FGOamLoopbackIgnoreRx OBJECT-TYPE
   SYNTAX      INTEGER
               {
               no (0),
               yes (1)
               }
   MAX-ACCESS  read-write
   STATUS      current
   DESCRIPTION
      "Path: ethernet2.editConf.oam.loopbackIgnoreRx

       Possibilities:
               no   (0)
               yes   (1)"
   ::= {er1645v2Lan2FGOamEntry 67108864}

er1645v2Lan2FGOamEventsErroredSymbolEnabled OBJECT-TYPE
   SYNTAX      INTEGER
               {
               no (0),
               yes (1)
               }
   MAX-ACCESS  read-write
   STATUS      current
   DESCRIPTION
      "Path: ethernet2.editConf.oam.events.erroredSymbol.enabled

       Possibilities:
               no   (0)
               yes   (1)"
   ::= {er1645v2Lan2FGOamEntry 83951872}

er1645v2Lan2FGOamEventsErroredSymbolWindowHi OBJECT-TYPE
   SYNTAX      INTEGER
               {
               default (0)
               }
   UNITS       "symbols"
   MAX-ACCESS  read-write
   STATUS      current
   DESCRIPTION
      "Path: ethernet2.editConf.oam.events.erroredSymbol.windowHi

       unit name = symbols

       Possibilities:
               default   (0)"
   ::= {er1645v2Lan2FGOamEntry 83952128}

er1645v2Lan2FGOamEventsErroredSymbolWindowLo OBJECT-TYPE
   SYNTAX      INTEGER
               {
               default (0)
               }
   UNITS       "symbols"
   MAX-ACCESS  read-write
   STATUS      current
   DESCRIPTION
      "Path: ethernet2.editConf.oam.events.erroredSymbol.windowLo

       unit name = symbols

       Possibilities:
               default   (0)"
   ::= {er1645v2Lan2FGOamEntry 83952384}

er1645v2Lan2FGOamEventsErroredSymbolThresholdHi OBJECT-TYPE
   SYNTAX      Integer32
   UNITS       "symbols"
   MAX-ACCESS  read-write
   STATUS      current
   DESCRIPTION
      "Path: ethernet2.editConf.oam.events.erroredSymbol.thresholdHi

       unit name = symbols"
   ::= {er1645v2Lan2FGOamEntry 83952640}

er1645v2Lan2FGOamEventsErroredSymbolThresholdLo OBJECT-TYPE
   SYNTAX      Integer32
   UNITS       "symbols"
   MAX-ACCESS  read-write
   STATUS      current
   DESCRIPTION
      "Path: ethernet2.editConf.oam.events.erroredSymbol.thresholdLo

       unit name = symbols"
   ::= {er1645v2Lan2FGOamEntry 83952896}

er1645v2Lan2FGOamEventsErroredFramePeriodEnabled OBJECT-TYPE
   SYNTAX      INTEGER
               {
               no (0),
               yes (1)
               }
   MAX-ACCESS  read-write
   STATUS      current
   DESCRIPTION
      "Path: ethernet2.editConf.oam.events.erroredFramePeriod.enabled

       Possibilities:
               no   (0)
               yes   (1)"
   ::= {er1645v2Lan2FGOamEntry 84017408}

er1645v2Lan2FGOamEventsErroredFramePeriodWindow OBJECT-TYPE
   SYNTAX      INTEGER
               {
               default (0)
               }
   UNITS       "frames"
   MAX-ACCESS  read-write
   STATUS      current
   DESCRIPTION
      "Path: ethernet2.editConf.oam.events.erroredFramePeriod.window

       unit name = frames

       Possibilities:
               default   (0)"
   ::= {er1645v2Lan2FGOamEntry 84017664}

er1645v2Lan2FGOamEventsErroredFramePeriodThreshold OBJECT-TYPE
   SYNTAX      Integer32
   UNITS       "frames"
   MAX-ACCESS  read-write
   STATUS      current
   DESCRIPTION
      "Path: ethernet2.editConf.oam.events.erroredFramePeriod.threshold

       unit name = frames"
   ::= {er1645v2Lan2FGOamEntry 84017920}

er1645v2Lan2FGOamEventsErroredFrameEnabled OBJECT-TYPE
   SYNTAX      INTEGER
               {
               no (0),
               yes (1)
               }
   MAX-ACCESS  read-write
   STATUS      current
   DESCRIPTION
      "Path: ethernet2.editConf.oam.events.erroredFrame.enabled

       Possibilities:
               no   (0)
               yes   (1)"
   ::= {er1645v2Lan2FGOamEntry 84082944}

er1645v2Lan2FGOamEventsErroredFrameWindow OBJECT-TYPE
   SYNTAX      Integer32
   UNITS       "100msec"
   MAX-ACCESS  read-write
   STATUS      current
   DESCRIPTION
      "Path: ethernet2.editConf.oam.events.erroredFrame.window

       unit name = 100msec"
   ::= {er1645v2Lan2FGOamEntry 84083200}

er1645v2Lan2FGOamEventsErroredFrameThreshold OBJECT-TYPE
   SYNTAX      Integer32
   UNITS       "frames"
   MAX-ACCESS  read-write
   STATUS      current
   DESCRIPTION
      "Path: ethernet2.editConf.oam.events.erroredFrame.threshold

       unit name = frames"
   ::= {er1645v2Lan2FGOamEntry 84083456}

er1645v2Lan2FGOamEventsErroredFrameSecondsEnabled OBJECT-TYPE
   SYNTAX      INTEGER
               {
               no (0),
               yes (1)
               }
   MAX-ACCESS  read-write
   STATUS      current
   DESCRIPTION
      "Path: ethernet2.editConf.oam.events.erroredFrameSeconds.enabled

       Possibilities:
               no   (0)
               yes   (1)"
   ::= {er1645v2Lan2FGOamEntry 84148480}

er1645v2Lan2FGOamEventsErroredFrameSecondsWindow OBJECT-TYPE
   SYNTAX      Integer32
   UNITS       "100msec"
   MAX-ACCESS  read-write
   STATUS      current
   DESCRIPTION
      "Path: ethernet2.editConf.oam.events.erroredFrameSeconds.window

       unit name = 100msec"
   ::= {er1645v2Lan2FGOamEntry 84148736}

er1645v2Lan2FGOamEventsErroredFrameSecondsThreshold OBJECT-TYPE
   SYNTAX      Integer32
   UNITS       "frames"
   MAX-ACCESS  read-write
   STATUS      current
   DESCRIPTION
      "Path: ethernet2.editConf.oam.events.erroredFrameSeconds.threshold

       unit name = frames"
   ::= {er1645v2Lan2FGOamEntry 84148992}

er1645v2Lan2FGOamEventsDyingGasp OBJECT-TYPE
   SYNTAX      INTEGER
               {
               disabled (0),
               enabled (1)
               }
   MAX-ACCESS  read-write
   STATUS      current
   DESCRIPTION
      "Path: ethernet2.editConf.oam.events.dyingGasp

       Possibilities:
               disabled   (0)
               enabled   (1)"
   ::= {er1645v2Lan2FGOamEntry 84213760}

er1645v2Lan2FGOamEventsCriticalEvent OBJECT-TYPE
   SYNTAX      INTEGER
               {
               disabled (0),
               enabled (1)
               }
   MAX-ACCESS  read-write
   STATUS      current
   DESCRIPTION
      "Path: ethernet2.editConf.oam.events.criticalEvent

       Possibilities:
               disabled   (0)
               enabled   (1)"
   ::= {er1645v2Lan2FGOamEntry 84279296}


er1645v2Lan2FGLst OBJECT IDENTIFIER ::= {er1645v2Lan2FG 12}

er1645v2Lan2FGLstSSC OBJECT IDENTIFIER ::= {er1645v2Lan2FGLst 1}

er1645v2Lan2FGLstEntry OBJECT IDENTIFIER ::= {er1645v2Lan2FGLstSSC 1}

er1645v2Lan2FGLstTrackedInterface OBJECT-TYPE
   SYNTAX      DisplayString
   MAX-ACCESS  read-write
   STATUS      current
   DESCRIPTION
      "Path: ethernet2.editConf.linkStateTracking.trackedInterface"
   ::= {er1645v2Lan2FGLstEntry 16777216}


er1645v2Lan2FGDot1x OBJECT IDENTIFIER ::= {er1645v2Lan2FG 191}

er1645v2Lan2FGDot1xSSC OBJECT IDENTIFIER ::= {er1645v2Lan2FGDot1x 1}

er1645v2Lan2FGDot1xEntry OBJECT IDENTIFIER ::= {er1645v2Lan2FGDot1xSSC 1}

er1645v2Lan2FGDot1xMode OBJECT-TYPE
   SYNTAX      INTEGER
               {
               inactive (0),
               auto (1)
               }
   MAX-ACCESS  read-write
   STATUS      current
   DESCRIPTION
      "Path: ethernet2.editConf.dot1x.mode

       Possibilities:
               inactive   (0)
               auto   (1)"
   ::= {er1645v2Lan2FGDot1xEntry 16777216}

er1645v2Lan2FGDot1xMaxHosts OBJECT-TYPE
   SYNTAX      Integer32
   MAX-ACCESS  read-write
   STATUS      current
   DESCRIPTION
      "Path: ethernet2.editConf.dot1x.maxHosts"
   ::= {er1645v2Lan2FGDot1xEntry 33554432}

er1645v2Lan2FGDot1xReAuthentication OBJECT-TYPE
   SYNTAX      INTEGER
               {
               disabled (0),
               enabled (1)
               }
   MAX-ACCESS  read-write
   STATUS      current
   DESCRIPTION
      "Path: ethernet2.editConf.dot1x.reAuthentication

       Possibilities:
               disabled   (0)
               enabled   (1)"
   ::= {er1645v2Lan2FGDot1xEntry 50331648}

er1645v2Lan2FGDot1xReAuthPeriod OBJECT-TYPE
   SYNTAX      TimeTicks
   MAX-ACCESS  read-write
   STATUS      current
   DESCRIPTION
      "Path: ethernet2.editConf.dot1x.reAuthPeriod

       Time in centi-second."
   ::= {er1645v2Lan2FGDot1xEntry 67108864}

er1645v2Lan2FGDot1xQuietPeriod OBJECT-TYPE
   SYNTAX      TimeTicks
   MAX-ACCESS  read-write
   STATUS      current
   DESCRIPTION
      "Path: ethernet2.editConf.dot1x.quietPeriod

       Time in centi-second."
   ::= {er1645v2Lan2FGDot1xEntry 83886080}

er1645v2Lan2FGDot1xSupplTimeout OBJECT-TYPE
   SYNTAX      TimeTicks
   MAX-ACCESS  read-write
   STATUS      current
   DESCRIPTION
      "Path: ethernet2.editConf.dot1x.supplTimeout

       Time in centi-second."
   ::= {er1645v2Lan2FGDot1xEntry 100663296}

er1645v2Lan2FGDot1xServerTimeout OBJECT-TYPE
   SYNTAX      TimeTicks
   MAX-ACCESS  read-write
   STATUS      current
   DESCRIPTION
      "Path: ethernet2.editConf.dot1x.serverTimeout

       Time in centi-second."
   ::= {er1645v2Lan2FGDot1xEntry 117440512}

er1645v2Lan2FGDot1xMaxReqCount OBJECT-TYPE
   SYNTAX      Integer32
   MAX-ACCESS  read-write
   STATUS      current
   DESCRIPTION
      "Path: ethernet2.editConf.dot1x.maxReqCount"
   ::= {er1645v2Lan2FGDot1xEntry 134217728}


er1645v2Lan2FGMode OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: ethernet2.editConf.mode
       Info: routing and/or bridging or ipV6 or multilink selection

       Possibilities:
               bridging   (0)
               routing   (1)
               routingAndBridging   (2)
               ipV6   (3)
               ipV6/ipV4   (4)
               multilink   (5)"
   ::= {er1645v2Lan2FG 29}


er1645v2Lan2FGIpV6 OBJECT IDENTIFIER ::= {er1645v2Lan2FG 15}

er1645v2Lan2FGIpV6SSC OBJECT IDENTIFIER ::= {er1645v2Lan2FGIpV6 1}

er1645v2Lan2FGIpV6Entry OBJECT IDENTIFIER ::= {er1645v2Lan2FGIpV6SSC 1}

er1645v2Lan2FGIpV6VrfRouter OBJECT-TYPE
   SYNTAX      DisplayString
   MAX-ACCESS  read-write
   STATUS      current
   DESCRIPTION
      "Path: ethernet2.editConf.ipV6.vrfRouter"
   ::= {er1645v2Lan2FGIpV6Entry 16777216}

er1645v2Lan2FGIpV6AddrAutoConfigNrDupAddrDetects OBJECT-TYPE
   SYNTAX      Integer32
   MAX-ACCESS  read-write
   STATUS      current
   DESCRIPTION
      "Path: ethernet2.editConf.ipV6.addrAutoConfig.nrDupAddrDetects"
   ::= {er1645v2Lan2FGIpV6Entry 67174400}

er1645v2Lan2FGIpV6AddrAutoConfigAcceptRa OBJECT-TYPE
   SYNTAX      INTEGER
               {
               disabled (0),
               enabled (1)
               }
   MAX-ACCESS  read-write
   STATUS      current
   DESCRIPTION
      "Path: ethernet2.editConf.ipV6.addrAutoConfig.acceptRa

       Possibilities:
               disabled   (0)
               enabled   (1)"
   ::= {er1645v2Lan2FGIpV6Entry 67239936}

er1645v2Lan2FGIpV6AddrAutoConfigAcceptRaRdnss OBJECT-TYPE
   SYNTAX      INTEGER
               {
               disabled (0),
               enabled (1)
               }
   MAX-ACCESS  read-write
   STATUS      current
   DESCRIPTION
      "Path: ethernet2.editConf.ipV6.addrAutoConfig.acceptRaRdnss

       Possibilities:
               disabled   (0)
               enabled   (1)"
   ::= {er1645v2Lan2FGIpV6Entry 67305472}

er1645v2Lan2FGIpV6AddrAutoConfigAcceptRaDnssl OBJECT-TYPE
   SYNTAX      INTEGER
               {
               disabled (0),
               enabled (1)
               }
   MAX-ACCESS  read-write
   STATUS      current
   DESCRIPTION
      "Path: ethernet2.editConf.ipV6.addrAutoConfig.acceptRaDnssl

       Possibilities:
               disabled   (0)
               enabled   (1)"
   ::= {er1645v2Lan2FGIpV6Entry 67371008}

er1645v2Lan2FGIpV6DefaultRoute OBJECT-TYPE
   SYNTAX      INTEGER
               {
               disabled (0),
               enabled (1)
               }
   MAX-ACCESS  read-write
   STATUS      current
   DESCRIPTION
      "Path: ethernet2.editConf.ipV6.defaultRoute

       Possibilities:
               disabled   (0)
               enabled   (1)"
   ::= {er1645v2Lan2FGIpV6Entry 83886080}

er1645v2Lan2FGIpV6RaSend OBJECT-TYPE
   SYNTAX      INTEGER
               {
               disabled (0),
               enabled (1)
               }
   MAX-ACCESS  read-write
   STATUS      current
   DESCRIPTION
      "Path: ethernet2.editConf.ipV6.ra.send

       Possibilities:
               disabled   (0)
               enabled   (1)"
   ::= {er1645v2Lan2FGIpV6Entry 100728832}

er1645v2Lan2FGIpV6RaMinInterval OBJECT-TYPE
   SYNTAX      TimeTicks
   MAX-ACCESS  read-write
   STATUS      current
   DESCRIPTION
      "Path: ethernet2.editConf.ipV6.ra.minInterval

       Time in centi-second."
   ::= {er1645v2Lan2FGIpV6Entry 100794368}

er1645v2Lan2FGIpV6RaMaxInterval OBJECT-TYPE
   SYNTAX      TimeTicks
   MAX-ACCESS  read-write
   STATUS      current
   DESCRIPTION
      "Path: ethernet2.editConf.ipV6.ra.maxInterval

       Time in centi-second."
   ::= {er1645v2Lan2FGIpV6Entry 100859904}

er1645v2Lan2FGIpV6RaManagedFlag OBJECT-TYPE
   SYNTAX      INTEGER
               {
               disabled (0),
               enabled (1)
               }
   MAX-ACCESS  read-write
   STATUS      current
   DESCRIPTION
      "Path: ethernet2.editConf.ipV6.ra.managedFlag

       Possibilities:
               disabled   (0)
               enabled   (1)"
   ::= {er1645v2Lan2FGIpV6Entry 100925440}

er1645v2Lan2FGIpV6RaOtherConfFlag OBJECT-TYPE
   SYNTAX      INTEGER
               {
               disabled (0),
               enabled (1)
               }
   MAX-ACCESS  read-write
   STATUS      current
   DESCRIPTION
      "Path: ethernet2.editConf.ipV6.ra.otherConfFlag

       Possibilities:
               disabled   (0)
               enabled   (1)"
   ::= {er1645v2Lan2FGIpV6Entry 100990976}

er1645v2Lan2FGIpV6RaLinkMtu OBJECT-TYPE
   SYNTAX      Integer32
   MAX-ACCESS  read-write
   STATUS      current
   DESCRIPTION
      "Path: ethernet2.editConf.ipV6.ra.linkMtu"
   ::= {er1645v2Lan2FGIpV6Entry 101056512}

er1645v2Lan2FGIpV6RaReachableTime OBJECT-TYPE
   SYNTAX      TimeTicks
   MAX-ACCESS  read-write
   STATUS      current
   DESCRIPTION
      "Path: ethernet2.editConf.ipV6.ra.reachableTime

       Time in centi-second."
   ::= {er1645v2Lan2FGIpV6Entry 101122048}

er1645v2Lan2FGIpV6RaRetransmitTime OBJECT-TYPE
   SYNTAX      TimeTicks
   MAX-ACCESS  read-write
   STATUS      current
   DESCRIPTION
      "Path: ethernet2.editConf.ipV6.ra.retransmitTime

       Time in centi-second."
   ::= {er1645v2Lan2FGIpV6Entry 101187584}

er1645v2Lan2FGIpV6RaHopLimit OBJECT-TYPE
   SYNTAX      Integer32
   MAX-ACCESS  read-write
   STATUS      current
   DESCRIPTION
      "Path: ethernet2.editConf.ipV6.ra.hopLimit"
   ::= {er1645v2Lan2FGIpV6Entry 101253120}

er1645v2Lan2FGIpV6RaDefaultLifeTime OBJECT-TYPE
   SYNTAX      TimeTicks
   MAX-ACCESS  read-write
   STATUS      current
   DESCRIPTION
      "Path: ethernet2.editConf.ipV6.ra.defaultLifeTime

       Time in centi-second."
   ::= {er1645v2Lan2FGIpV6Entry 101318656}

er1645v2Lan2FGIpV6RaDnsOptionsRdnssLifeTime OBJECT-TYPE
   SYNTAX      TimeTicks
   MAX-ACCESS  read-write
   STATUS      current
   DESCRIPTION
      "Path: ethernet2.editConf.ipV6.ra.dnsOptions.rdnss.lifeTime

       Time in centi-second."
   ::= {er1645v2Lan2FGIpV6Entry 101393408}

er1645v2Lan2FGIpV6RaDnsOptionsRdnssImportServers OBJECT-TYPE
   SYNTAX      INTEGER
               {
               disabled (0),
               enabled (1)
               }
   MAX-ACCESS  read-write
   STATUS      current
   DESCRIPTION
      "Path: ethernet2.editConf.ipV6.ra.dnsOptions.rdnss.importServers

       Possibilities:
               disabled   (0)
               enabled   (1)"
   ::= {er1645v2Lan2FGIpV6Entry 101395456}

er1645v2Lan2FGIpV6RaDnsOptionsDnsslLifeTime OBJECT-TYPE
   SYNTAX      TimeTicks
   MAX-ACCESS  read-write
   STATUS      current
   DESCRIPTION
      "Path: ethernet2.editConf.ipV6.ra.dnsOptions.dnssl.lifeTime

       Time in centi-second."
   ::= {er1645v2Lan2FGIpV6Entry 101401600}

er1645v2Lan2FGIpV6RaDnsOptionsDnsslImportDomains OBJECT-TYPE
   SYNTAX      INTEGER
               {
               disabled (0),
               enabled (1)
               }
   MAX-ACCESS  read-write
   STATUS      current
   DESCRIPTION
      "Path: ethernet2.editConf.ipV6.ra.dnsOptions.dnssl.importDomains

       Possibilities:
               disabled   (0)
               enabled   (1)"
   ::= {er1645v2Lan2FGIpV6Entry 101403648}

er1645v2Lan2FGIpV6RsSend OBJECT-TYPE
   SYNTAX      INTEGER
               {
               disabled (0),
               enabled (1)
               }
   MAX-ACCESS  read-write
   STATUS      current
   DESCRIPTION
      "Path: ethernet2.editConf.ipV6.rs.send

       Possibilities:
               disabled   (0)
               enabled   (1)"
   ::= {er1645v2Lan2FGIpV6Entry 335609856}

er1645v2Lan2FGIpV6RsMaxRandomDelay OBJECT-TYPE
   SYNTAX      TimeTicks
   MAX-ACCESS  read-write
   STATUS      current
   DESCRIPTION
      "Path: ethernet2.editConf.ipV6.rs.maxRandomDelay

       Time in centi-second."
   ::= {er1645v2Lan2FGIpV6Entry 335675392}

er1645v2Lan2FGIpV6RsInterval OBJECT-TYPE
   SYNTAX      TimeTicks
   MAX-ACCESS  read-write
   STATUS      current
   DESCRIPTION
      "Path: ethernet2.editConf.ipV6.rs.interval

       Time in centi-second."
   ::= {er1645v2Lan2FGIpV6Entry 335740928}

er1645v2Lan2FGIpV6RsMaxSolicitations OBJECT-TYPE
   SYNTAX      Integer32
   MAX-ACCESS  read-write
   STATUS      current
   DESCRIPTION
      "Path: ethernet2.editConf.ipV6.rs.maxSolicitations"
   ::= {er1645v2Lan2FGIpV6Entry 335806464}

er1645v2Lan2FGIpV6TrafficPolicyInbound OBJECT-TYPE
   SYNTAX      DisplayString
   MAX-ACCESS  read-write
   STATUS      current
   DESCRIPTION
      "Path: ethernet2.editConf.ipV6.trafficPolicy.inbound"
   ::= {er1645v2Lan2FGIpV6Entry 184614912}

er1645v2Lan2FGIpV6TrafficPolicyOutbound OBJECT-TYPE
   SYNTAX      DisplayString
   MAX-ACCESS  read-write
   STATUS      current
   DESCRIPTION
      "Path: ethernet2.editConf.ipV6.trafficPolicy.outbound"
   ::= {er1645v2Lan2FGIpV6Entry 184680448}

er1645v2Lan2FGIpV6FirewallZone OBJECT-TYPE
   SYNTAX      DisplayString
   MAX-ACCESS  read-write
   STATUS      current
   DESCRIPTION
      "Path: ethernet2.editConf.ipV6.firewall.zone"
   ::= {er1645v2Lan2FGIpV6Entry 201392128}

er1645v2Lan2FGIpV6DhcpClientAddrAC OBJECT-TYPE
   SYNTAX      INTEGER
               {
               disabled (0),
               enabled (1)
               }
   MAX-ACCESS  read-write
   STATUS      current
   DESCRIPTION
      "Path: ethernet2.editConf.ipV6.dhcp.client.addrAutoConfig

       Possibilities:
               disabled   (0)
               enabled   (1)"
   ::= {er1645v2Lan2FGIpV6Entry 170131456}

er1645v2Lan2FGIpV6DhcpClientPrDelMode OBJECT-TYPE
   SYNTAX      INTEGER
               {
               disabled (0),
               enabled (1)
               }
   MAX-ACCESS  read-write
   STATUS      current
   DESCRIPTION
      "Path: ethernet2.editConf.ipV6.dhcp.client.pd.mode

       Possibilities:
               disabled   (0)
               enabled   (1)"
   ::= {er1645v2Lan2FGIpV6Entry 170394624}

er1645v2Lan2FGIpV6DhcpClientPrDelPool OBJECT-TYPE
   SYNTAX      DisplayString
   MAX-ACCESS  read-write
   STATUS      current
   DESCRIPTION
      "Path: ethernet2.editConf.ipV6.dhcp.client.pd.pool"
   ::= {er1645v2Lan2FGIpV6Entry 170395648}

er1645v2Lan2FGIpV6DhcpClientPrDelPdExclOpt OBJECT-TYPE
   SYNTAX      INTEGER
               {
               disabled (0),
               enabled (1)
               }
   MAX-ACCESS  read-write
   STATUS      current
   DESCRIPTION
      "Path: ethernet2.editConf.ipV6.dhcp.client.pd.pdExclOpt

       Possibilities:
               disabled   (0)
               enabled   (1)"
   ::= {er1645v2Lan2FGIpV6Entry 170396672}

er1645v2Lan2FGIpV6DhcpClientDnsServerPref OBJECT-TYPE
   SYNTAX      Integer32
   MAX-ACCESS  read-write
   STATUS      current
   DESCRIPTION
      "Path: ethernet2.editConf.ipV6.dhcp.client.dns.serverPref"
   ::= {er1645v2Lan2FGIpV6Entry 170918912}

er1645v2Lan2FGIpV6DhcpClientRapidCommit OBJECT-TYPE
   SYNTAX      INTEGER
               {
               disabled (0),
               enabled (1)
               }
   MAX-ACCESS  read-write
   STATUS      current
   DESCRIPTION
      "Path: ethernet2.editConf.ipV6.dhcp.client.rapidCommit

       Possibilities:
               disabled   (0)
               enabled   (1)"
   ::= {er1645v2Lan2FGIpV6Entry 170655744}

er1645v2Lan2FGIpV6DhcpClientTimersSolTimeOut OBJECT-TYPE
   SYNTAX      TimeTicks
   MAX-ACCESS  read-write
   STATUS      current
   DESCRIPTION
      "Path: ethernet2.editConf.ipV6.dhcp.client.timers.solTimeOut

       Time in centi-second."
   ::= {er1645v2Lan2FGIpV6Entry 171181056}

er1645v2Lan2FGIpV6DhcpClientTimersSolMaxRt OBJECT-TYPE
   SYNTAX      TimeTicks
   MAX-ACCESS  read-write
   STATUS      current
   DESCRIPTION
      "Path: ethernet2.editConf.ipV6.dhcp.client.timers.solMaxRt

       Time in centi-second."
   ::= {er1645v2Lan2FGIpV6Entry 171182080}

er1645v2Lan2FGIpV6DhcpClientTimersInfoRefresh OBJECT-TYPE
   SYNTAX      TimeTicks
   MAX-ACCESS  read-write
   STATUS      current
   DESCRIPTION
      "Path: ethernet2.editConf.ipV6.dhcp.client.timers.infoRefresh

       Time in centi-second."
   ::= {er1645v2Lan2FGIpV6Entry 171183104}

er1645v2Lan2FGIpV6DhcpServerMode OBJECT-TYPE
   SYNTAX      INTEGER
               {
               disabled (0),
               enabled (1)
               }
   MAX-ACCESS  read-write
   STATUS      current
   DESCRIPTION
      "Path: ethernet2.editConf.ipV6.dhcp.server.mode

       Possibilities:
               disabled   (0)
               enabled   (1)"
   ::= {er1645v2Lan2FGIpV6Entry 172228608}

er1645v2Lan2FGIpV6DhcpServerPreference OBJECT-TYPE
   SYNTAX      Integer32
   MAX-ACCESS  read-write
   STATUS      current
   DESCRIPTION
      "Path: ethernet2.editConf.ipV6.dhcp.server.preference"
   ::= {er1645v2Lan2FGIpV6Entry 172490752}

er1645v2Lan2FGIpV6DhcpServerPool OBJECT-TYPE
   SYNTAX      DisplayString
   MAX-ACCESS  read-write
   STATUS      current
   DESCRIPTION
      "Path: ethernet2.editConf.ipV6.dhcp.server.pool"
   ::= {er1645v2Lan2FGIpV6Entry 172752896}

er1645v2Lan2FGIpV6DhcpServerRapidCommit OBJECT-TYPE
   SYNTAX      INTEGER
               {
               disabled (0),
               enabled (1)
               }
   MAX-ACCESS  read-write
   STATUS      current
   DESCRIPTION
      "Path: ethernet2.editConf.ipV6.dhcp.server.rapidCommit

       Possibilities:
               disabled   (0)
               enabled   (1)"
   ::= {er1645v2Lan2FGIpV6Entry 173015040}

er1645v2Lan2FGIpV6DhcpServerTimersInfoRefresh OBJECT-TYPE
   SYNTAX      TimeTicks
   MAX-ACCESS  read-write
   STATUS      current
   DESCRIPTION
      "Path: ethernet2.editConf.ipV6.dhcp.server.timers.infoRefresh

       Time in centi-second."
   ::= {er1645v2Lan2FGIpV6Entry 173278208}

er1645v2Lan2FGIpV6DhcpRelayMode OBJECT-TYPE
   SYNTAX      INTEGER
               {
               disabled (0),
               enabled (1)
               }
   MAX-ACCESS  read-write
   STATUS      current
   DESCRIPTION
      "Path: ethernet2.editConf.ipV6.dhcp.relay.mode

       Possibilities:
               disabled   (0)
               enabled   (1)"
   ::= {er1645v2Lan2FGIpV6Entry 174071808}

er1645v2Lan2FGIpV6SendRedirect OBJECT-TYPE
   SYNTAX      INTEGER
               {
               disabled (0),
               enabled (1)
               }
   MAX-ACCESS  read-write
   STATUS      current
   DESCRIPTION
      "Path: ethernet2.editConf.ipV6.sendRedirect

       Possibilities:
               disabled   (0)
               enabled   (1)"
   ::= {er1645v2Lan2FGIpV6Entry 117440512}

er1645v2Lan2FGIpV6LinkMtu OBJECT-TYPE
   SYNTAX      Integer32
   MAX-ACCESS  read-write
   STATUS      current
   DESCRIPTION
      "Path: ethernet2.editConf.ipV6.linkMtu"
   ::= {er1645v2Lan2FGIpV6Entry 134217728}

er1645v2Lan2FGIpV6InterfaceId OBJECT-TYPE
   SYNTAX      OCTET STRING
   MAX-ACCESS  read-write
   STATUS      current
   DESCRIPTION
      "Path: ethernet2.editConf.ipV6.interfaceId"
   ::= {er1645v2Lan2FGIpV6Entry 150994944}

er1645v2Lan2FGIpV6MF OBJECT-TYPE
   SYNTAX      Integer32
   MAX-ACCESS  read-write
   STATUS      current
   DESCRIPTION
      "Path: ethernet2.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2FGIpV6Entry 285212672}

er1645v2Lan2FGIpV6IcmpMessagesNoRoute OBJECT-TYPE
   SYNTAX      INTEGER
               {
               disabled (0),
               enabled (1)
               }
   MAX-ACCESS  read-write
   STATUS      current
   DESCRIPTION
      "Path: ethernet2.editConf.ipV6.icmpMessages.noRoute

       Possibilities:
               disabled   (0)
               enabled   (1)"
   ::= {er1645v2Lan2FGIpV6Entry 302055424}

er1645v2Lan2FGIpV6IcmpMessagesBeyondScope OBJECT-TYPE
   SYNTAX      INTEGER
               {
               disabled (0),
               enabled (1)
               }
   MAX-ACCESS  read-write
   STATUS      current
   DESCRIPTION
      "Path: ethernet2.editConf.ipV6.icmpMessages.beyondScope

       Possibilities:
               disabled   (0)
               enabled   (1)"
   ::= {er1645v2Lan2FGIpV6Entry 302186496}

er1645v2Lan2FGIpV6IcmpMessagesAddressUnreachable OBJECT-TYPE
   SYNTAX      INTEGER
               {
               disabled (0),
               enabled (1)
               }
   MAX-ACCESS  read-write
   STATUS      current
   DESCRIPTION
      "Path: ethernet2.editConf.ipV6.icmpMessages.addressUnreachable

       Possibilities:
               disabled   (0)
               enabled   (1)"
   ::= {er1645v2Lan2FGIpV6Entry 302252032}

er1645v2Lan2FGIpV6IcmpMessagesPortUnreachable OBJECT-TYPE
   SYNTAX      INTEGER
               {
               disabled (0),
               enabled (1)
               }
   MAX-ACCESS  read-write
   STATUS      current
   DESCRIPTION
      "Path: ethernet2.editConf.ipV6.icmpMessages.portUnreachable

       Possibilities:
               disabled   (0)
               enabled   (1)"
   ::= {er1645v2Lan2FGIpV6Entry 302317568}

er1645v2Lan2FGIpV6IcmpMessagesPacketTooBig OBJECT-TYPE
   SYNTAX      INTEGER
               {
               disabled (0),
               enabled (1)
               }
   MAX-ACCESS  read-write
   STATUS      current
   DESCRIPTION
      "Path: ethernet2.editConf.ipV6.icmpMessages.packetTooBig

       Possibilities:
               disabled   (0)
               enabled   (1)"
   ::= {er1645v2Lan2FGIpV6Entry 302645248}

er1645v2Lan2FGIpV6IcmpMessagesHopLimitExceeded OBJECT-TYPE
   SYNTAX      INTEGER
               {
               disabled (0),
               enabled (1)
               }
   MAX-ACCESS  read-write
   STATUS      current
   DESCRIPTION
      "Path: ethernet2.editConf.ipV6.icmpMessages.hopLimitExceeded

       Possibilities:
               disabled   (0)
               enabled   (1)"
   ::= {er1645v2Lan2FGIpV6Entry 303300608}

er1645v2Lan2FGIpV6IcmpMessagesFragTimeExceeded OBJECT-TYPE
   SYNTAX      INTEGER
               {
               disabled (0),
               enabled (1)
               }
   MAX-ACCESS  read-write
   STATUS      current
   DESCRIPTION
      "Path: ethernet2.editConf.ipV6.icmpMessages.fragTimeExceeded

       Possibilities:
               disabled   (0)
               enabled   (1)"
   ::= {er1645v2Lan2FGIpV6Entry 303366144}

er1645v2Lan2FGIpV6IcmpMessagesHeaderFieldErr OBJECT-TYPE
   SYNTAX      INTEGER
               {
               disabled (0),
               enabled (1)
               }
   MAX-ACCESS  read-write
   STATUS      current
   DESCRIPTION
      "Path: ethernet2.editConf.ipV6.icmpMessages.headerFieldErr

       Possibilities:
               disabled   (0)
               enabled   (1)"
   ::= {er1645v2Lan2FGIpV6Entry 303955968}

er1645v2Lan2FGIpV6IcmpMessagesOptionUnrecognized OBJECT-TYPE
   SYNTAX      INTEGER
               {
               disabled (0),
               enabled (1)
               }
   MAX-ACCESS  read-write
   STATUS      current
   DESCRIPTION
      "Path: ethernet2.editConf.ipV6.icmpMessages.optionUnrecognized

       Possibilities:
               disabled   (0)
               enabled   (1)"
   ::= {er1645v2Lan2FGIpV6Entry 304087040}

er1645v2Lan2FGIpV6IcmpMessagesRedirect OBJECT-TYPE
   SYNTAX      INTEGER
               {
               disabled (0),
               enabled (1)
               }
   MAX-ACCESS  read-write
   STATUS      current
   DESCRIPTION
      "Path: ethernet2.editConf.ipV6.icmpMessages.redirect

       Possibilities:
               disabled   (0)
               enabled   (1)"
   ::= {er1645v2Lan2FGIpV6Entry 304611328}

er1645v2Lan2FGIpV6Addresses OBJECT-TYPE
   SYNTAX      SEQUENCE OF Er1645v2Lan2FGIpV6AddressesEntry
   MAX-ACCESS  not-accessible
   STATUS      current
   DESCRIPTION
      ""
   ::= {er1645v2Lan2FGIpV6 50331648}

er1645v2Lan2FGIpV6AddressesEntry OBJECT-TYPE
   SYNTAX      Er1645v2Lan2FGIpV6AddressesEntry
   MAX-ACCESS  not-accessible
   STATUS      current
   DESCRIPTION
      ""
   INDEX      { er1645v2Lan2FGIpV6AddressesTableIx }
   ::= {er1645v2Lan2FGIpV6Addresses 1}

Er1645v2Lan2FGIpV6AddressesEntry ::=
   SEQUENCE
      {
      er1645v2Lan2FGIpV6AddressesActions
         VariableLengthTableActions,
      er1645v2Lan2FGIpV6AddressesTableIx
         TableIndex,
      er1645v2Lan2FGIpV6AddressesType
         INTEGER,
      er1645v2Lan2FGIpV6AddressesAddress
         Ipv6Address,
      er1645v2Lan2FGIpV6AddressesPrefixLength
         Integer32,
      er1645v2Lan2FGIpV6AddressesGeneralPrefix
         DisplayString,
      er1645v2Lan2FGIpV6AddressesRaSend
         INTEGER,
      er1645v2Lan2FGIpV6AddressesRaOnLinkFlag
         INTEGER,
      er1645v2Lan2FGIpV6AddressesRaAutoFlag
         INTEGER,
      er1645v2Lan2FGIpV6AddressesRaValidLifeTime
         TimeTicks,
      er1645v2Lan2FGIpV6AddressesRaValidLTMode
         INTEGER,
      er1645v2Lan2FGIpV6AddressesRaPrefLifeTime
         TimeTicks,
      er1645v2Lan2FGIpV6AddressesRaPrefLTMode
         INTEGER
      }

er1645v2Lan2FGIpV6AddressesActions OBJECT-TYPE
   SYNTAX      VariableLengthTableActions
   MAX-ACCESS  read-write
   STATUS      current
   DESCRIPTION
      "By way of this field, some manipulations
       on this table may be performed."
   ::= {er1645v2Lan2FGIpV6AddressesEntry 2}

er1645v2Lan2FGIpV6AddressesTableIx OBJECT-TYPE
   SYNTAX      TableIndex
   MAX-ACCESS  not-accessible
   STATUS      current
   DESCRIPTION
      ""
   ::= {er1645v2Lan2FGIpV6AddressesEntry 11}

er1645v2Lan2FGIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.ipV6.addresses.type

       Possibilities:
               unicast   (0)
               eui64   (1)
               anycast   (2)
               linkLocal   (3)
               generalPrefix   (4)"
   ::= {er1645v2Lan2FGIpV6AddressesEntry 50331648}

er1645v2Lan2FGIpV6AddressesAddress OBJECT-TYPE
   SYNTAX      Ipv6Address
   MAX-ACCESS  read-write
   STATUS      current
   DESCRIPTION
      "Path: ethernet2.editConf.ipV6.addresses.address

       ipv6 address"
   ::= {er1645v2Lan2FGIpV6AddressesEntry 16777216}

er1645v2Lan2FGIpV6AddressesPrefixLength OBJECT-TYPE
   SYNTAX      Integer32
   MAX-ACCESS  read-write
   STATUS      current
   DESCRIPTION
      "Path: ethernet2.editConf.ipV6.addresses.prefixLength"
   ::= {er1645v2Lan2FGIpV6AddressesEntry 33554432}

er1645v2Lan2FGIpV6AddressesGeneralPrefix OBJECT-TYPE
   SYNTAX      DisplayString
   MAX-ACCESS  read-write
   STATUS      current
   DESCRIPTION
      "Path: ethernet2.editConf.ipV6.addresses.generalPrefix"
   ::= {er1645v2Lan2FGIpV6AddressesEntry 83886080}

er1645v2Lan2FGIpV6AddressesRaSend OBJECT-TYPE
   SYNTAX      INTEGER
               {
               disabled (0),
               enabled (1)
               }
   MAX-ACCESS  read-write
   STATUS      current
   DESCRIPTION
      "Path: ethernet2.editConf.ipV6.addresses.ra.send

       Possibilities:
               disabled   (0)
               enabled   (1)"
   ::= {er1645v2Lan2FGIpV6AddressesEntry 67174400}

er1645v2Lan2FGIpV6AddressesRaOnLinkFlag OBJECT-TYPE
   SYNTAX      INTEGER
               {
               disabled (0),
               enabled (1)
               }
   MAX-ACCESS  read-write
   STATUS      current
   DESCRIPTION
      "Path: ethernet2.editConf.ipV6.addresses.ra.onLinkFlag

       Possibilities:
               disabled   (0)
               enabled   (1)"
   ::= {er1645v2Lan2FGIpV6AddressesEntry 67371008}

er1645v2Lan2FGIpV6AddressesRaAutoFlag OBJECT-TYPE
   SYNTAX      INTEGER
               {
               disabled (0),
               enabled (1)
               }
   MAX-ACCESS  read-write
   STATUS      current
   DESCRIPTION
      "Path: ethernet2.editConf.ipV6.addresses.ra.autonomousFlag

       Possibilities:
               disabled   (0)
               enabled   (1)"
   ::= {er1645v2Lan2FGIpV6AddressesEntry 67567616}

er1645v2Lan2FGIpV6AddressesRaValidLifeTime OBJECT-TYPE
   SYNTAX      TimeTicks
   MAX-ACCESS  read-write
   STATUS      current
   DESCRIPTION
      "Path: ethernet2.editConf.ipV6.addresses.ra.validLifeTime

       Time in centi-second."
   ::= {er1645v2Lan2FGIpV6AddressesEntry 67239936}

er1645v2Lan2FGIpV6AddressesRaValidLTMode OBJECT-TYPE
   SYNTAX      INTEGER
               {
               fixed (0),
               infinite (2)
               }
   MAX-ACCESS  read-write
   STATUS      current
   DESCRIPTION
      "Path: ethernet2.editConf.ipV6.addresses.ra.validLifeTimeMode

       Possibilities:
               fixed   (0)
               infinite   (2)"
   ::= {er1645v2Lan2FGIpV6AddressesEntry 67305472}

er1645v2Lan2FGIpV6AddressesRaPrefLifeTime OBJECT-TYPE
   SYNTAX      TimeTicks
   MAX-ACCESS  read-write
   STATUS      current
   DESCRIPTION
      "Path: ethernet2.editConf.ipV6.addresses.ra.prefLifeTime

       Time in centi-second."
   ::= {er1645v2Lan2FGIpV6AddressesEntry 67436544}

er1645v2Lan2FGIpV6AddressesRaPrefLTMode OBJECT-TYPE
   SYNTAX      INTEGER
               {
               fixed (0),
               infinite (2)
               }
   MAX-ACCESS  read-write
   STATUS      current
   DESCRIPTION
      "Path: ethernet2.editConf.ipV6.addresses.ra.prefLifeTimeMode

       Possibilities:
               fixed   (0)
               infinite   (2)"
   ::= {er1645v2Lan2FGIpV6AddressesEntry 67502080}

er1645v2Lan2FGIpV6RaDnsOptionsRdnssServers OBJECT-TYPE
   SYNTAX      SEQUENCE OF Er1645v2Lan2FGIpV6RaDnsOptionsRdnssServersEntry
   MAX-ACCESS  not-accessible
   STATUS      current
   DESCRIPTION
      ""
   ::= {er1645v2Lan2FGIpV6 101394432}

er1645v2Lan2FGIpV6RaDnsOptionsRdnssServersEntry OBJECT-TYPE
   SYNTAX      Er1645v2Lan2FGIpV6RaDnsOptionsRdnssServersEntry
   MAX-ACCESS  not-accessible
   STATUS      current
   DESCRIPTION
      ""
   INDEX      { er1645v2Lan2FGIpV6RaDnsOptionsRdnssServersTableIx }
   ::= {er1645v2Lan2FGIpV6RaDnsOptionsRdnssServers 1}

Er1645v2Lan2FGIpV6RaDnsOptionsRdnssServersEntry ::=
   SEQUENCE
      {
      er1645v2Lan2FGIpV6RaDnsOptionsRdnssServersActions
         VariableLengthTableActions,
      er1645v2Lan2FGIpV6RaDnsOptionsRdnssServersTableIx
         TableIndex,
      er1645v2Lan2FGIpV6RaDnsOptionsRdnssServersAddress
         Ipv6Address
      }

er1645v2Lan2FGIpV6RaDnsOptionsRdnssServersActions OBJECT-TYPE
   SYNTAX      VariableLengthTableActions
   MAX-ACCESS  read-write
   STATUS      current
   DESCRIPTION
      "By way of this field, some manipulations
       on this table may be performed."
   ::= {er1645v2Lan2FGIpV6RaDnsOptionsRdnssServersEntry 2}

er1645v2Lan2FGIpV6RaDnsOptionsRdnssServersTableIx OBJECT-TYPE
   SYNTAX      TableIndex
   MAX-ACCESS  not-accessible
   STATUS      current
   DESCRIPTION
      ""
   ::= {er1645v2Lan2FGIpV6RaDnsOptionsRdnssServersEntry 11}

er1645v2Lan2FGIpV6RaDnsOptionsRdnssServersAddress OBJECT-TYPE
   SYNTAX      Ipv6Address
   MAX-ACCESS  read-write
   STATUS      current
   DESCRIPTION
      "Path: ethernet2.editConf.ipV6.ra.dnsOptions.rdnss.servers.address

       ipv6 address"
   ::= {er1645v2Lan2FGIpV6RaDnsOptionsRdnssServersEntry 16777216}

er1645v2Lan2FGIpV6RaDnsOptionsDnsslDomains OBJECT-TYPE
   SYNTAX      SEQUENCE OF Er1645v2Lan2FGIpV6RaDnsOptionsDnsslDomainsEntry
   MAX-ACCESS  not-accessible
   STATUS      current
   DESCRIPTION
      ""
   ::= {er1645v2Lan2FGIpV6 101402624}

er1645v2Lan2FGIpV6RaDnsOptionsDnsslDomainsEntry OBJECT-TYPE
   SYNTAX      Er1645v2Lan2FGIpV6RaDnsOptionsDnsslDomainsEntry
   MAX-ACCESS  not-accessible
   STATUS      current
   DESCRIPTION
      ""
   INDEX      { er1645v2Lan2FGIpV6RaDnsOptionsDnsslDomainsTableIx }
   ::= {er1645v2Lan2FGIpV6RaDnsOptionsDnsslDomains 1}

Er1645v2Lan2FGIpV6RaDnsOptionsDnsslDomainsEntry ::=
   SEQUENCE
      {
      er1645v2Lan2FGIpV6RaDnsOptionsDnsslDomainsActions
         VariableLengthTableActions,
      er1645v2Lan2FGIpV6RaDnsOptionsDnsslDomainsTableIx
         TableIndex,
      er1645v2Lan2FGIpV6RaDnsOptionsDnsslDomainsName
         DisplayString
      }

er1645v2Lan2FGIpV6RaDnsOptionsDnsslDomainsActions OBJECT-TYPE
   SYNTAX      VariableLengthTableActions
   MAX-ACCESS  read-write
   STATUS      current
   DESCRIPTION
      "By way of this field, some manipulations
       on this table may be performed."
   ::= {er1645v2Lan2FGIpV6RaDnsOptionsDnsslDomainsEntry 2}

er1645v2Lan2FGIpV6RaDnsOptionsDnsslDomainsTableIx OBJECT-TYPE
   SYNTAX      TableIndex
   MAX-ACCESS  not-accessible
   STATUS      current
   DESCRIPTION
      ""
   ::= {er1645v2Lan2FGIpV6RaDnsOptionsDnsslDomainsEntry 11}

er1645v2Lan2FGIpV6RaDnsOptionsDnsslDomainsName OBJECT-TYPE
   SYNTAX      DisplayString
   MAX-ACCESS  read-write
   STATUS      current
   DESCRIPTION
      "Path: ethernet2.editConf.ipV6.ra.dnsOptions.dnssl.domains.name"
   ::= {er1645v2Lan2FGIpV6RaDnsOptionsDnsslDomainsEntry 16777216}

er1645v2Lan2FGIpV6DhcpClientUserClassOpt OBJECT-TYPE
   SYNTAX      SEQUENCE OF Er1645v2Lan2FGIpV6DhcpClientUserClassOptEntry
   MAX-ACCESS  not-accessible
   STATUS      current
   DESCRIPTION
      ""
   ::= {er1645v2Lan2FGIpV6 171442176}

er1645v2Lan2FGIpV6DhcpClientUserClassOptEntry OBJECT-TYPE
   SYNTAX      Er1645v2Lan2FGIpV6DhcpClientUserClassOptEntry
   MAX-ACCESS  not-accessible
   STATUS      current
   DESCRIPTION
      ""
   INDEX      { er1645v2Lan2FGIpV6DhcpClientUserClassOptTableIx }
   ::= {er1645v2Lan2FGIpV6DhcpClientUserClassOpt 1}

Er1645v2Lan2FGIpV6DhcpClientUserClassOptEntry ::=
   SEQUENCE
      {
      er1645v2Lan2FGIpV6DhcpClientUserClassOptActions
         VariableLengthTableActions,
      er1645v2Lan2FGIpV6DhcpClientUserClassOptTableIx
         TableIndex,
      er1645v2Lan2FGIpV6DhcpClientUserClassOptValueAscii
         DisplayString,
      er1645v2Lan2FGIpV6DhcpClientUserClassOptValueDecimal
         Integer32,
      er1645v2Lan2FGIpV6DhcpClientUserClassOptValueHexData
         OCTET STRING
      }

er1645v2Lan2FGIpV6DhcpClientUserClassOptActions OBJECT-TYPE
   SYNTAX      VariableLengthTableActions
   MAX-ACCESS  read-write
   STATUS      current
   DESCRIPTION
      "By way of this field, some manipulations
       on this table may be performed."
   ::= {er1645v2Lan2FGIpV6DhcpClientUserClassOptEntry 2}

er1645v2Lan2FGIpV6DhcpClientUserClassOptTableIx OBJECT-TYPE
   SYNTAX      TableIndex
   MAX-ACCESS  not-accessible
   STATUS      current
   DESCRIPTION
      ""
   ::= {er1645v2Lan2FGIpV6DhcpClientUserClassOptEntry 11}

er1645v2Lan2FGIpV6DhcpClientUserClassOptValueAscii OBJECT-TYPE
   SYNTAX      DisplayString
   MAX-ACCESS  read-write
   STATUS      current
   DESCRIPTION
      "Path: ethernet2.editConf.ipV6.dhcp.client.userClassOpt.value.ascii"
   ::= {er1645v2Lan2FGIpV6DhcpClientUserClassOptEntry 16842752}

er1645v2Lan2FGIpV6DhcpClientUserClassOptValueDecimal OBJECT-TYPE
   SYNTAX      Integer32
   MAX-ACCESS  read-write
   STATUS      current
   DESCRIPTION
      "Path: ethernet2.editConf.ipV6.dhcp.client.userClassOpt.value.decimal"
   ::= {er1645v2Lan2FGIpV6DhcpClientUserClassOptEntry 16908288}

er1645v2Lan2FGIpV6DhcpClientUserClassOptValueHexData OBJECT-TYPE
   SYNTAX      OCTET STRING
   MAX-ACCESS  read-write
   STATUS      current
   DESCRIPTION
      "Path: ethernet2.editConf.ipV6.dhcp.client.userClassOpt.value.hexData"
   ::= {er1645v2Lan2FGIpV6DhcpClientUserClassOptEntry 16973824}

er1645v2Lan2FGIpV6DhcpClientVendorCl OBJECT-TYPE
   SYNTAX      SEQUENCE OF Er1645v2Lan2FGIpV6DhcpClientVendorClEntry
   MAX-ACCESS  not-accessible
   STATUS      current
   DESCRIPTION
      ""
   ::= {er1645v2Lan2FGIpV6 171704320}

er1645v2Lan2FGIpV6DhcpClientVendorClEntry OBJECT-TYPE
   SYNTAX      Er1645v2Lan2FGIpV6DhcpClientVendorClEntry
   MAX-ACCESS  not-accessible
   STATUS      current
   DESCRIPTION
      ""
   INDEX      { er1645v2Lan2FGIpV6DhcpClientVendorClTableIx }
   ::= {er1645v2Lan2FGIpV6DhcpClientVendorCl 1}

Er1645v2Lan2FGIpV6DhcpClientVendorClEntry ::=
   SEQUENCE
      {
      er1645v2Lan2FGIpV6DhcpClientVendorClActions
         VariableLengthTableActions,
      er1645v2Lan2FGIpV6DhcpClientVendorClTableIx
         TableIndex,
      er1645v2Lan2FGIpV6DhcpClientVendorClValueAscii
         DisplayString,
      er1645v2Lan2FGIpV6DhcpClientVendorClValueDecimal
         Integer32,
      er1645v2Lan2FGIpV6DhcpClientVendorClValueHexData
         OCTET STRING
      }

er1645v2Lan2FGIpV6DhcpClientVendorClActions OBJECT-TYPE
   SYNTAX      VariableLengthTableActions
   MAX-ACCESS  read-write
   STATUS      current
   DESCRIPTION
      "By way of this field, some manipulations
       on this table may be performed."
   ::= {er1645v2Lan2FGIpV6DhcpClientVendorClEntry 2}

er1645v2Lan2FGIpV6DhcpClientVendorClTableIx OBJECT-TYPE
   SYNTAX      TableIndex
   MAX-ACCESS  not-accessible
   STATUS      current
   DESCRIPTION
      ""
   ::= {er1645v2Lan2FGIpV6DhcpClientVendorClEntry 11}

er1645v2Lan2FGIpV6DhcpClientVendorClValueAscii OBJECT-TYPE
   SYNTAX      DisplayString
   MAX-ACCESS  read-write
   STATUS      current
   DESCRIPTION
      "Path: ethernet2.editConf.ipV6.dhcp.client.vendorClassOpt.value.ascii"
   ::= {er1645v2Lan2FGIpV6DhcpClientVendorClEntry 16842752}

er1645v2Lan2FGIpV6DhcpClientVendorClValueDecimal OBJECT-TYPE
   SYNTAX      Integer32
   MAX-ACCESS  read-write
   STATUS      current
   DESCRIPTION
      "Path: ethernet2.editConf.ipV6.dhcp.client.vendorClassOpt.value.decimal"
   ::= {er1645v2Lan2FGIpV6DhcpClientVendorClEntry 16908288}

er1645v2Lan2FGIpV6DhcpClientVendorClValueHexData OBJECT-TYPE
   SYNTAX      OCTET STRING
   MAX-ACCESS  read-write
   STATUS      current
   DESCRIPTION
      "Path: ethernet2.editConf.ipV6.dhcp.client.vendorClassOpt.value.hexData"
   ::= {er1645v2Lan2FGIpV6DhcpClientVendorClEntry 16973824}

er1645v2Lan2FGIpV6DhcpRelayDestinations OBJECT-TYPE
   SYNTAX      SEQUENCE OF Er1645v2Lan2FGIpV6DhcpRelayDestinationsEntry
   MAX-ACCESS  not-accessible
   STATUS      current
   DESCRIPTION
      ""
   ::= {er1645v2Lan2FGIpV6 174080000}

er1645v2Lan2FGIpV6DhcpRelayDestinationsEntry OBJECT-TYPE
   SYNTAX      Er1645v2Lan2FGIpV6DhcpRelayDestinationsEntry
   MAX-ACCESS  not-accessible
   STATUS      current
   DESCRIPTION
      ""
   INDEX      { er1645v2Lan2FGIpV6DhcpRelayDestinationsTableIx }
   ::= {er1645v2Lan2FGIpV6DhcpRelayDestinations 1}

Er1645v2Lan2FGIpV6DhcpRelayDestinationsEntry ::=
   SEQUENCE
      {
      er1645v2Lan2FGIpV6DhcpRelayDestinationsActions
         VariableLengthTableActions,
      er1645v2Lan2FGIpV6DhcpRelayDestinationsTableIx
         TableIndex,
      er1645v2Lan2FGIpV6DhcpRelayDestinationsAddress
         Ipv6Address,
      er1645v2Lan2FGIpV6DhcpRelayDestinationsInterface
         DisplayString
      }

er1645v2Lan2FGIpV6DhcpRelayDestinationsActions OBJECT-TYPE
   SYNTAX      VariableLengthTableActions
   MAX-ACCESS  read-write
   STATUS      current
   DESCRIPTION
      "By way of this field, some manipulations
       on this table may be performed."
   ::= {er1645v2Lan2FGIpV6DhcpRelayDestinationsEntry 2}

er1645v2Lan2FGIpV6DhcpRelayDestinationsTableIx OBJECT-TYPE
   SYNTAX      TableIndex
   MAX-ACCESS  not-accessible
   STATUS      current
   DESCRIPTION
      ""
   ::= {er1645v2Lan2FGIpV6DhcpRelayDestinationsEntry 11}

er1645v2Lan2FGIpV6DhcpRelayDestinationsAddress OBJECT-TYPE
   SYNTAX      Ipv6Address
   MAX-ACCESS  read-write
   STATUS      current
   DESCRIPTION
      "Path: ethernet2.editConf.ipV6.dhcp.relay.destinations.address

       ipv6 address"
   ::= {er1645v2Lan2FGIpV6DhcpRelayDestinationsEntry 16777216}

er1645v2Lan2FGIpV6DhcpRelayDestinationsInterface OBJECT-TYPE
   SYNTAX      DisplayString
   MAX-ACCESS  read-write
   STATUS      current
   DESCRIPTION
      "Path: ethernet2.editConf.ipV6.dhcp.relay.destinations.interface"
   ::= {er1645v2Lan2FGIpV6DhcpRelayDestinationsEntry 33554432}


er1645v2Lan2FGFlowControl OBJECT-TYPE
   SYNTAX      INTEGER
               {
               disabled (1),
               rx (2),
               tx (3),
               rxAndTx (4)
               }
   MAX-ACCESS  read-write
   STATUS      current
   DESCRIPTION
      "Path: ethernet2.editConf.flowControl
       Info: LAN flow control

       Possibilities:
               disabled   (1)
               rx   (2)
               tx   (3)
               rxAndTx   (4)"
   ::= {er1645v2Lan2FG 7}


er1645v2Lan2FGInboundNUcastPriority OBJECT IDENTIFIER ::= {er1645v2Lan2FG 230}

er1645v2Lan2FGInboundNUcastPrioritySSC OBJECT IDENTIFIER ::= {er1645v2Lan2FGInboundNUcastPriority 1}

er1645v2Lan2FGInboundNUcastPriorityEntry OBJECT IDENTIFIER ::= {er1645v2Lan2FGInboundNUcastPrioritySSC 1}

er1645v2Lan2FGInboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundNUcastPriority.broadcast

       Possibilities:
               queue1   (0)
               queue2   (1)
               queue3   (2)
               queue4   (3)
               queue5   (4)
               lowDelayQueue   (5)
               lowDelay2Queue   (6)
               systemQueue   (7)"
   ::= {er1645v2Lan2FGInboundNUcastPriorityEntry 16777216}

er1645v2Lan2FGInboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundNUcastPriority.multicast

       Possibilities:
               queue1   (0)
               queue2   (1)
               queue3   (2)
               queue4   (3)
               queue5   (4)
               lowDelayQueue   (5)
               lowDelay2Queue   (6)
               systemQueue   (7)"
   ::= {er1645v2Lan2FGInboundNUcastPriorityEntry 33554432}


er1645v2Lan2FGIp OBJECT IDENTIFIER ::= {er1645v2Lan2FG 1}

er1645v2Lan2FGIpSSC OBJECT IDENTIFIER ::= {er1645v2Lan2FGIp 1}

er1645v2Lan2FGIpEntry OBJECT IDENTIFIER ::= {er1645v2Lan2FGIpSSC 1}

er1645v2Lan2FGIpVrfRouter OBJECT-TYPE
   SYNTAX      DisplayString
   MAX-ACCESS  read-write
   STATUS      current
   DESCRIPTION
      "Path: ethernet2.editConf.ip.vrfRouter"
   ::= {er1645v2Lan2FGIpEntry 738197504}

er1645v2Lan2FGIpAdr OBJECT-TYPE
   SYNTAX      IpAddress
   MAX-ACCESS  read-write
   STATUS      current
   DESCRIPTION
      "Path: ethernet2.editConf.ip.address"
   ::= {er1645v2Lan2FGIpEntry 2030043136}

er1645v2Lan2FGIpNetm OBJECT-TYPE
   SYNTAX      IpAddress
   MAX-ACCESS  read-write
   STATUS      current
   DESCRIPTION
      "Path: ethernet2.editConf.ip.netMask"
   ::= {er1645v2Lan2FGIpEntry 2063597568}

er1645v2Lan2FGIpSNetName OBJECT-TYPE
   SYNTAX      INTEGER
               {
               slOPTg (0),
               corp (2),
               dmz (3),
               internet (1)
               }
   MAX-ACCESS  read-write
   STATUS      current
   DESCRIPTION
      "Path: ethernet2.editConf.ip.sNet.name

       Possibilities:
               <OPT>   (0)
               corp   (2)
               dmz   (3)
               internet   (1)"
   ::= {er1645v2Lan2FGIpEntry 855703552}

er1645v2Lan2FGIpSNetCust OBJECT-TYPE
   SYNTAX      DisplayString
   MAX-ACCESS  read-write
   STATUS      current
   DESCRIPTION
      "Path: ethernet2.editConf.ip.sNet.custom"
   ::= {er1645v2Lan2FGIpEntry 855769088}

er1645v2Lan2FGIpDhcpC OBJECT-TYPE
   SYNTAX      INTEGER
               {
               disabled (0),
               enabled (1)
               }
   MAX-ACCESS  read-write
   STATUS      current
   DESCRIPTION
      "Path: ethernet2.editConf.ip.dhcpClient

       Possibilities:
               disabled   (0)
               enabled   (1)"
   ::= {er1645v2Lan2FGIpEntry 838860800}

er1645v2Lan2FGIpDhcpGatewayPreference OBJECT-TYPE
   SYNTAX      Integer32
   MAX-ACCESS  read-write
   STATUS      current
   DESCRIPTION
      "Path: ethernet2.editConf.ip.dhcp.gatewayPreference"
   ::= {er1645v2Lan2FGIpEntry 872480768}

er1645v2Lan2FGIpDhcpRoutePreference OBJECT-TYPE
   SYNTAX      Integer32
   MAX-ACCESS  read-write
   STATUS      current
   DESCRIPTION
      "Path: ethernet2.editConf.ip.dhcp.routePreference"
   ::= {er1645v2Lan2FGIpEntry 872546304}

er1645v2Lan2FGIpDhcpDnsPreference OBJECT-TYPE
   SYNTAX      Integer32
   MAX-ACCESS  read-write
   STATUS      current
   DESCRIPTION
      "Path: ethernet2.editConf.ip.dhcp.dnsPreference"
   ::= {er1645v2Lan2FGIpEntry 872611840}

er1645v2Lan2FGIpMtu OBJECT-TYPE
   SYNTAX      Integer32
   MAX-ACCESS  read-write
   STATUS      current
   DESCRIPTION
      "Path: ethernet2.editConf.ip.mtu"
   ::= {er1645v2Lan2FGIpEntry 671088640}

er1645v2Lan2FGIpMssAdjust OBJECT-TYPE
   SYNTAX      INTEGER
               {
               disabled (0),
               auto (65536)
               }
   MAX-ACCESS  read-write
   STATUS      current
   DESCRIPTION
      "Path: ethernet2.editConf.ip.mssAdjust

       Possibilities:
               disabled   (0)
               auto   (65536)"
   ::= {er1645v2Lan2FGIpEntry 754974720}

er1645v2Lan2FGIpRipMetric OBJECT-TYPE
   SYNTAX      Integer32
   MAX-ACCESS  read-write
   STATUS      current
   DESCRIPTION
      "Path: ethernet2.editConf.ip.rip.metric"
   ::= {er1645v2Lan2FGIpEntry 353566720}

er1645v2Lan2FGIpRipMetricOut OBJECT-TYPE
   SYNTAX      Integer32
   MAX-ACCESS  read-write
   STATUS      current
   DESCRIPTION
      "Path: ethernet2.editConf.ip.rip.metricOut"
   ::= {er1645v2Lan2FGIpEntry 353632256}

er1645v2Lan2FGIpRipMode OBJECT-TYPE
   SYNTAX      INTEGER
               {
               disabled (0),
               passive (1),
               active (2)
               }
   MAX-ACCESS  read-write
   STATUS      current
   DESCRIPTION
      "Path: ethernet2.editConf.ip.rip.mode

       Possibilities:
               disabled   (0)
               passive   (1)
               active   (2)"
   ::= {er1645v2Lan2FGIpEntry 353697792}

er1645v2Lan2FGIpRipTxVer OBJECT-TYPE
   SYNTAX      INTEGER
               {
               rip1 (0),
               rip2 (1),
               rip1mcompatible (2)
               }
   MAX-ACCESS  read-write
   STATUS      current
   DESCRIPTION
      "Path: ethernet2.editConf.ip.rip.txVersion

       Possibilities:
               rip1   (0)
               rip2   (1)
               rip1-compatible   (2)"
   ::= {er1645v2Lan2FGIpEntry 354615296}

er1645v2Lan2FGIpRipRxVer OBJECT-TYPE
   SYNTAX      INTEGER
               {
               rip1only (0),
               rip2only (1),
               rip12 (2)
               }
   MAX-ACCESS  read-write
   STATUS      current
   DESCRIPTION
      "Path: ethernet2.editConf.ip.rip.rxVersion

       Possibilities:
               rip1only   (0)
               rip2only   (1)
               rip1&2   (2)"
   ::= {er1645v2Lan2FGIpEntry 354680832}

er1645v2Lan2FGIpRipSplitH OBJECT-TYPE
   SYNTAX      INTEGER
               {
               disabled (0),
               enabled (1),
               poisonedReverse (2)
               }
   MAX-ACCESS  read-write
   STATUS      current
   DESCRIPTION
      "Path: ethernet2.editConf.ip.rip.splitHorizon

       Possibilities:
               disabled   (0)
               enabled   (1)
               poisonedReverse   (2)"
   ::= {er1645v2Lan2FGIpEntry 353828864}

er1645v2Lan2FGIpRipAuth OBJECT-TYPE
   SYNTAX      INTEGER
               {
               disabled (0),
               texts (1),
               md5 (2)
               }
   MAX-ACCESS  read-write
   STATUS      current
   DESCRIPTION
      "Path: ethernet2.editConf.ip.rip.authentication

       Possibilities:
               disabled   (0)
               text    (1)
               md5   (2)"
   ::= {er1645v2Lan2FGIpEntry 353501184}

er1645v2Lan2FGIpRipFilter OBJECT-TYPE
   SYNTAX      DisplayString
   MAX-ACCESS  read-write
   STATUS      current
   DESCRIPTION
      "Path: ethernet2.editConf.ip.rip.filter"
   ::= {er1645v2Lan2FGIpEntry 354418688}

er1645v2Lan2FGIpRipFilterIn OBJECT-TYPE
   SYNTAX      DisplayString
   MAX-ACCESS  read-write
   STATUS      current
   DESCRIPTION
      "Path: ethernet2.editConf.ip.rip.filterIn"
   ::= {er1645v2Lan2FGIpEntry 354484224}

er1645v2Lan2FGIpRipClearNextHop OBJECT-TYPE
   SYNTAX      INTEGER
               {
               disabled (0),
               enabled (1)
               }
   MAX-ACCESS  read-write
   STATUS      current
   DESCRIPTION
      "Path: ethernet2.editConf.ip.rip.clearNextHop

       Possibilities:
               disabled   (0)
               enabled   (1)"
   ::= {er1645v2Lan2FGIpEntry 352452608}

er1645v2Lan2FGIpAccPol OBJECT-TYPE
   SYNTAX      DisplayString
   MAX-ACCESS  read-write
   STATUS      current
   DESCRIPTION
      "Path: ethernet2.editConf.ip.accessPolicy"
   ::= {er1645v2Lan2FGIpEntry 704643072}

er1645v2Lan2FGIpAB OBJECT-TYPE
   SYNTAX      DisplayString
   MAX-ACCESS  read-write
   STATUS      current
   DESCRIPTION
      "Path: ethernet2.editConf.ip.trafficPolicy"
   ::= {er1645v2Lan2FGIpEntry 234881024}

er1645v2Lan2FGIpMA OBJECT-TYPE
   SYNTAX      INTEGER
               {
               disabled (0),
               enabled (1)
               }
   MAX-ACCESS  read-write
   STATUS      current
   DESCRIPTION
      "Path: ethernet2.editConf.ip.mgmtAccess

       Possibilities:
               disabled   (0)
               enabled   (1)"
   ::= {er1645v2Lan2FGIpEntry 268435456}

er1645v2Lan2FGIpMF OBJECT-TYPE
   SYNTAX      Integer32
   MAX-ACCESS  read-write
   STATUS      current
   DESCRIPTION
      "Path: ethernet2.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2FGIpEntry 285212672}

er1645v2Lan2FGIpDB OBJECT-TYPE
   SYNTAX      INTEGER
               {
               disabled (0),
               enabled (1)
               }
   MAX-ACCESS  read-write
   STATUS      current
   DESCRIPTION
      "Path: ethernet2.editConf.ip.directedBroadcasts

       Possibilities:
               disabled   (0)
               enabled   (1)"
   ::= {er1645v2Lan2FGIpEntry 369098752}

er1645v2Lan2FGIpIR OBJECT-TYPE
   SYNTAX      INTEGER
               {
               disabled (0),
               enabled (1)
               }
   MAX-ACCESS  read-write
   STATUS      current
   DESCRIPTION
      "Path: ethernet2.editConf.ip.icmpRedirects

       Possibilities:
               disabled   (0)
               enabled   (1)"
   ::= {er1645v2Lan2FGIpEntry 436207616}

er1645v2Lan2FGIpIgmp OBJECT-TYPE
   SYNTAX      INTEGER
               {
               disabled (0),
               proxy (1),
               router (2),
               v3Router (5)
               }
   MAX-ACCESS  read-write
   STATUS      current
   DESCRIPTION
      "Path: ethernet2.editConf.ip.igmp

       Possibilities:
               disabled   (0)
               proxy   (1)
               router   (2)
               v3Router   (5)"
   ::= {er1645v2Lan2FGIpEntry 536870912}

er1645v2Lan2FGIpNN OBJECT-TYPE
   SYNTAX      DisplayString
   MAX-ACCESS  read-write
   STATUS      current
   DESCRIPTION
      "Path: ethernet2.editConf.ip.nat"
   ::= {er1645v2Lan2FGIpEntry 452984832}

er1645v2Lan2FGIpVrrp OBJECT-TYPE
   SYNTAX      INTEGER
               {
               disabled (0),
               enabled (1)
               }
   MAX-ACCESS  read-write
   STATUS      current
   DESCRIPTION
      "Path: ethernet2.editConf.ip.vrrp

       Possibilities:
               disabled   (0)
               enabled   (1)"
   ::= {er1645v2Lan2FGIpEntry 721420288}

er1645v2Lan2FGIpPimMode OBJECT-TYPE
   SYNTAX      INTEGER
               {
               disabled (0),
               sparse (1),
               passive (2)
               }
   MAX-ACCESS  read-write
   STATUS      current
   DESCRIPTION
      "Path: ethernet2.editConf.ip.pim.mode

       Possibilities:
               disabled   (0)
               sparse   (1)
               passive   (2)"
   ::= {er1645v2Lan2FGIpEntry 771817472}

er1645v2Lan2FGIpPimDrPriority OBJECT-TYPE
   SYNTAX      Counter32
   MAX-ACCESS  read-write
   STATUS      current
   DESCRIPTION
      "Path: ethernet2.editConf.ip.pim.drPriority

       32 bit unsigned wrappable counter."
   ::= {er1645v2Lan2FGIpEntry 771883008}

er1645v2Lan2FGIpPimHelloTime OBJECT-TYPE
   SYNTAX      TimeTicks
   MAX-ACCESS  read-write
   STATUS      current
   DESCRIPTION
      "Path: ethernet2.editConf.ip.pim.helloTime

       Time in centi-second."
   ::= {er1645v2Lan2FGIpEntry 771948544}

er1645v2Lan2FGIpPimPropagationDelay OBJECT-TYPE
   SYNTAX      TimeTicks
   MAX-ACCESS  read-write
   STATUS      current
   DESCRIPTION
      "Path: ethernet2.editConf.ip.pim.propagationDelay

       Time in centi-second."
   ::= {er1645v2Lan2FGIpEntry 772014080}

er1645v2Lan2FGIpPimOverrideInterval OBJECT-TYPE
   SYNTAX      TimeTicks
   MAX-ACCESS  read-write
   STATUS      current
   DESCRIPTION
      "Path: ethernet2.editConf.ip.pim.overrideInterval

       Time in centi-second."
   ::= {er1645v2Lan2FGIpEntry 772079616}

er1645v2Lan2FGIpPimBsrBorder OBJECT-TYPE
   SYNTAX      INTEGER
               {
               disabled (0),
               enabled (1)
               }
   MAX-ACCESS  read-write
   STATUS      current
   DESCRIPTION
      "Path: ethernet2.editConf.ip.pim.bsrBorder

       Possibilities:
               disabled   (0)
               enabled   (1)"
   ::= {er1645v2Lan2FGIpEntry 772145152}

er1645v2Lan2FGIpPimTtlThreshold OBJECT-TYPE
   SYNTAX      Integer32
   MAX-ACCESS  read-write
   STATUS      current
   DESCRIPTION
      "Path: ethernet2.editConf.ip.pim.ttlThreshold"
   ::= {er1645v2Lan2FGIpEntry 772210688}

er1645v2Lan2FGIpIMNetworkUnreachable OBJECT-TYPE
   SYNTAX      INTEGER
               {
               disabled (0),
               enabled (1)
               }
   MAX-ACCESS  read-write
   STATUS      current
   DESCRIPTION
      "Path: ethernet2.editConf.ip.icmpMessages.networkUnreachable

       Possibilities:
               disabled   (0)
               enabled   (1)"
   ::= {er1645v2Lan2FGIpEntry 788594688}

er1645v2Lan2FGIpIMHostUnreachable OBJECT-TYPE
   SYNTAX      INTEGER
               {
               disabled (0),
               enabled (1)
               }
   MAX-ACCESS  read-write
   STATUS      current
   DESCRIPTION
      "Path: ethernet2.editConf.ip.icmpMessages.hostUnreachable

       Possibilities:
               disabled   (0)
               enabled   (1)"
   ::= {er1645v2Lan2FGIpEntry 788660224}

er1645v2Lan2FGIpIMProtocolUnreachable OBJECT-TYPE
   SYNTAX      INTEGER
               {
               disabled (0),
               enabled (1)
               }
   MAX-ACCESS  read-write
   STATUS      current
   DESCRIPTION
      "Path: ethernet2.editConf.ip.icmpMessages.protocolUnreachable

       Possibilities:
               disabled   (0)
               enabled   (1)"
   ::= {er1645v2Lan2FGIpEntry 788725760}

er1645v2Lan2FGIpIMPortUnreachable OBJECT-TYPE
   SYNTAX      INTEGER
               {
               disabled (0),
               enabled (1)
               }
   MAX-ACCESS  read-write
   STATUS      current
   DESCRIPTION
      "Path: ethernet2.editConf.ip.icmpMessages.portUnreachable

       Possibilities:
               disabled   (0)
               enabled   (1)"
   ::= {er1645v2Lan2FGIpEntry 788791296}

er1645v2Lan2FGIpIMMtuExceeded OBJECT-TYPE
   SYNTAX      INTEGER
               {
               disabled (0),
               enabled (1)
               }
   MAX-ACCESS  read-write
   STATUS      current
   DESCRIPTION
      "Path: ethernet2.editConf.ip.icmpMessages.mtuExceeded

       Possibilities:
               disabled   (0)
               enabled   (1)"
   ::= {er1645v2Lan2FGIpEntry 788856832}

er1645v2Lan2FGIpIMAdminProhibited OBJECT-TYPE
   SYNTAX      INTEGER
               {
               disabled (0),
               enabled (1)
               }
   MAX-ACCESS  read-write
   STATUS      current
   DESCRIPTION
      "Path: ethernet2.editConf.ip.icmpMessages.adminProhibited

       Possibilities:
               disabled   (0)
               enabled   (1)"
   ::= {er1645v2Lan2FGIpEntry 788922368}

er1645v2Lan2FGIpIMTtlExceeded OBJECT-TYPE
   SYNTAX      INTEGER
               {
               disabled (0),
               enabled (1)
               }
   MAX-ACCESS  read-write
   STATUS      current
   DESCRIPTION
      "Path: ethernet2.editConf.ip.icmpMessages.ttlExceeded

       Possibilities:
               disabled   (0)
               enabled   (1)"
   ::= {er1645v2Lan2FGIpEntry 788987904}

er1645v2Lan2FGIpIMRedirect OBJECT-TYPE
   SYNTAX      INTEGER
               {
               disabled (0),
               enabled (1)
               }
   MAX-ACCESS  read-write
   STATUS      current
   DESCRIPTION
      "Path: ethernet2.editConf.ip.icmpMessages.redirect

       Possibilities:
               disabled   (0)
               enabled   (1)"
   ::= {er1645v2Lan2FGIpEntry 789053440}

er1645v2Lan2FGIpSaddr OBJECT-TYPE
   SYNTAX      SEQUENCE OF Er1645v2Lan2FGIpSaddrEntry
   MAX-ACCESS  not-accessible
   STATUS      current
   DESCRIPTION
      ""
   ::= {er1645v2Lan2FGIp 385875968}

er1645v2Lan2FGIpSaddrEntry OBJECT-TYPE
   SYNTAX      Er1645v2Lan2FGIpSaddrEntry
   MAX-ACCESS  not-accessible
   STATUS      current
   DESCRIPTION
      ""
   INDEX      { er1645v2Lan2FGIpSaddrTableIx }
   ::= {er1645v2Lan2FGIpSaddr 1}

Er1645v2Lan2FGIpSaddrEntry ::=
   SEQUENCE
      {
      er1645v2Lan2FGIpSaddrActions
         VariableLengthTableActions,
      er1645v2Lan2FGIpSaddrTableIx
         TableIndex,
      er1645v2Lan2FGIpSaddrAddress
         IpAddress,
      er1645v2Lan2FGIpSaddrNetMask
         IpAddress
      }

er1645v2Lan2FGIpSaddrActions OBJECT-TYPE
   SYNTAX      VariableLengthTableActions
   MAX-ACCESS  read-write
   STATUS      current
   DESCRIPTION
      "By way of this field, some manipulations
       on this table may be performed."
   ::= {er1645v2Lan2FGIpSaddrEntry 2}

er1645v2Lan2FGIpSaddrTableIx OBJECT-TYPE
   SYNTAX      TableIndex
   MAX-ACCESS  not-accessible
   STATUS      current
   DESCRIPTION
      ""
   ::= {er1645v2Lan2FGIpSaddrEntry 11}

er1645v2Lan2FGIpSaddrAddress OBJECT-TYPE
   SYNTAX      IpAddress
   MAX-ACCESS  read-write
   STATUS      current
   DESCRIPTION
      "Path: ethernet2.editConf.ip.secondaryIp.address"
   ::= {er1645v2Lan2FGIpSaddrEntry 2030043136}

er1645v2Lan2FGIpSaddrNetMask OBJECT-TYPE
   SYNTAX      IpAddress
   MAX-ACCESS  read-write
   STATUS      current
   DESCRIPTION
      "Path: ethernet2.editConf.ip.secondaryIp.netMask"
   ::= {er1645v2Lan2FGIpSaddrEntry 2063597568}

er1645v2Lan2FGIpH OBJECT-TYPE
   SYNTAX      SEQUENCE OF Er1645v2Lan2FGIpHEntry
   MAX-ACCESS  not-accessible
   STATUS      current
   DESCRIPTION
      ""
   ::= {er1645v2Lan2FGIp 251658240}

er1645v2Lan2FGIpHEntry OBJECT-TYPE
   SYNTAX      Er1645v2Lan2FGIpHEntry
   MAX-ACCESS  not-accessible
   STATUS      current
   DESCRIPTION
      ""
   INDEX      { er1645v2Lan2FGIpHTableIx }
   ::= {er1645v2Lan2FGIpH 1}

Er1645v2Lan2FGIpHEntry ::=
   SEQUENCE
      {
      er1645v2Lan2FGIpHActions
         VariableLengthTableActions,
      er1645v2Lan2FGIpHTableIx
         TableIndex,
      er1645v2Lan2FGIpHAddress
         IpAddress,
      er1645v2Lan2FGIpHDhcpRelayOptionSubscriberId
         DisplayString
      }

er1645v2Lan2FGIpHActions OBJECT-TYPE
   SYNTAX      VariableLengthTableActions
   MAX-ACCESS  read-write
   STATUS      current
   DESCRIPTION
      "By way of this field, some manipulations
       on this table may be performed."
   ::= {er1645v2Lan2FGIpHEntry 2}

er1645v2Lan2FGIpHTableIx OBJECT-TYPE
   SYNTAX      TableIndex
   MAX-ACCESS  not-accessible
   STATUS      current
   DESCRIPTION
      ""
   ::= {er1645v2Lan2FGIpHEntry 11}

er1645v2Lan2FGIpHAddress OBJECT-TYPE
   SYNTAX      IpAddress
   MAX-ACCESS  read-write
   STATUS      current
   DESCRIPTION
      "Path: ethernet2.editConf.ip.helpers.address"
   ::= {er1645v2Lan2FGIpHEntry 16777216}

er1645v2Lan2FGIpHDhcpRelayOptionSubscriberId OBJECT-TYPE
   SYNTAX      DisplayString
   MAX-ACCESS  read-write
   STATUS      current
   DESCRIPTION
      "Path: ethernet2.editConf.ip.helpers.dhcpRelayOption.subscriberId"
   ::= {er1645v2Lan2FGIpHEntry 33947648}


er1645v2Lan2FGAdapter OBJECT-TYPE
   SYNTAX      INTEGER
               {
               autoDetect (0),
               s10MbhalfDuplex (1),
               s10MbfullDuplex (2),
               s100MbhalfDuplex (3),
               s100MbfullDuplex (4),
               s1000MbfullDuplex (6)
               }
   MAX-ACCESS  read-write
   STATUS      current
   DESCRIPTION
      "Path: ethernet2.editConf.adapter

       Possibilities:
               autoDetect   (0)
               10Mb/halfDuplex   (1)
               10Mb/fullDuplex   (2)
               100Mb/halfDuplex   (3)
               100Mb/fullDuplex   (4)
               1000Mb/fullDuplex   (6)"
   ::= {er1645v2Lan2FG 32}


er1645v2Lan2FGVlan OBJECT IDENTIFIER ::= {er1645v2Lan2FG 33}

er1645v2Lan2FGVlanSSCTable OBJECT-TYPE
   SYNTAX      SEQUENCE OF Er1645v2Lan2FGVlanEntry
   MAX-ACCESS  not-accessible
   STATUS      current
   DESCRIPTION
      ""
   ::= {er1645v2Lan2FGVlan 1}

er1645v2Lan2FGVlanEntry OBJECT-TYPE
   SYNTAX      Er1645v2Lan2FGVlanEntry
   MAX-ACCESS  not-accessible
   STATUS      current
   DESCRIPTION
      ""
   INDEX      { er1645v2Lan2FGVlanTableIx }
   ::= {er1645v2Lan2FGVlanSSCTable 1}

Er1645v2Lan2FGVlanEntry ::=
   SEQUENCE
      {
      er1645v2Lan2FGVlanActions
         VariableLengthTableActions,
      er1645v2Lan2FGVlanTableIx
         TableIndex,
      er1645v2Lan2FGVlanName
         DisplayString,
      er1645v2Lan2FGVlanRemark
         DisplayString,
      er1645v2Lan2FGVlanAdminStatus
         INTEGER,
      er1645v2Lan2FGVlanMode
         INTEGER,
      er1645v2Lan2FGVlanPriorityPolicy
         DisplayString,
      er1645v2Lan2FGVlanIpVrfRouter
         DisplayString,
      er1645v2Lan2FGVlanIpAdr
         IpAddress,
      er1645v2Lan2FGVlanIpNetm
         IpAddress,
      er1645v2Lan2FGVlanIpSNetName
         INTEGER,
      er1645v2Lan2FGVlanIpSNetCust
         DisplayString,
      er1645v2Lan2FGVlanIpDhcpC
         INTEGER,
      er1645v2Lan2FGVlanIpDhcpGatewayPreference
         Integer32,
      er1645v2Lan2FGVlanIpDhcpRoutePreference
         Integer32,
      er1645v2Lan2FGVlanIpDhcpDnsPreference
         Integer32,
      er1645v2Lan2FGVlanIpMtu
         Integer32,
      er1645v2Lan2FGVlanIpMssAdjust
         INTEGER,
      er1645v2Lan2FGVlanIpRipMetric
         Integer32,
      er1645v2Lan2FGVlanIpRipMetricOut
         Integer32,
      er1645v2Lan2FGVlanIpRipMode
         INTEGER,
      er1645v2Lan2FGVlanIpRipTxVer
         INTEGER,
      er1645v2Lan2FGVlanIpRipRxVer
         INTEGER,
      er1645v2Lan2FGVlanIpRipSplitH
         INTEGER,
      er1645v2Lan2FGVlanIpRipAuth
         INTEGER,
      er1645v2Lan2FGVlanIpRipFilter
         DisplayString,
      er1645v2Lan2FGVlanIpRipFilterIn
         DisplayString,
      er1645v2Lan2FGVlanIpRipClearNextHop
         INTEGER,
      er1645v2Lan2FGVlanIpAccPol
         DisplayString,
      er1645v2Lan2FGVlanIpAB
         DisplayString,
      er1645v2Lan2FGVlanIpMA
         INTEGER,
      er1645v2Lan2FGVlanIpMF
         Integer32,
      er1645v2Lan2FGVlanIpDB
         INTEGER,
      er1645v2Lan2FGVlanIpIR
         INTEGER,
      er1645v2Lan2FGVlanIpIgmp
         INTEGER,
      er1645v2Lan2FGVlanIpNN
         DisplayString,
      er1645v2Lan2FGVlanIpVrrp
         INTEGER,
      er1645v2Lan2FGVlanIpPimMode
         INTEGER,
      er1645v2Lan2FGVlanIpPimDrPriority
         Counter32,
      er1645v2Lan2FGVlanIpPimHelloTime
         TimeTicks,
      er1645v2Lan2FGVlanIpPimPropagationDelay
         TimeTicks,
      er1645v2Lan2FGVlanIpPimOverrideInterval
         TimeTicks,
      er1645v2Lan2FGVlanIpPimBsrBorder
         INTEGER,
      er1645v2Lan2FGVlanIpPimTtlThreshold
         Integer32,
      er1645v2Lan2FGVlanIpIMNetworkUnreachable
         INTEGER,
      er1645v2Lan2FGVlanIpIMHostUnreachable
         INTEGER,
      er1645v2Lan2FGVlanIpIMProtocolUnreachable
         INTEGER,
      er1645v2Lan2FGVlanIpIMPortUnreachable
         INTEGER,
      er1645v2Lan2FGVlanIpIMMtuExceeded
         INTEGER,
      er1645v2Lan2FGVlanIpIMAdminProhibited
         INTEGER,
      er1645v2Lan2FGVlanIpIMTtlExceeded
         INTEGER,
      er1645v2Lan2FGVlanIpIMRedirect
         INTEGER,
      er1645v2Lan2FGVlanIpV6VrfRouter
         DisplayString,
      er1645v2Lan2FGVlanIpV6AddrAutoConfigNrDupAddrDetects
         Integer32,
      er1645v2Lan2FGVlanIpV6AddrAutoConfigAcceptRa
         INTEGER,
      er1645v2Lan2FGVlanIpV6AddrAutoConfigAcceptRaRdnss
         INTEGER,
      er1645v2Lan2FGVlanIpV6AddrAutoConfigAcceptRaDnssl
         INTEGER,
      er1645v2Lan2FGVlanIpV6DefaultRoute
         INTEGER,
      er1645v2Lan2FGVlanIpV6RaSend
         INTEGER,
      er1645v2Lan2FGVlanIpV6RaMinInterval
         TimeTicks,
      er1645v2Lan2FGVlanIpV6RaMaxInterval
         TimeTicks,
      er1645v2Lan2FGVlanIpV6RaManagedFlag
         INTEGER,
      er1645v2Lan2FGVlanIpV6RaOtherConfFlag
         INTEGER,
      er1645v2Lan2FGVlanIpV6RaLinkMtu
         Integer32,
      er1645v2Lan2FGVlanIpV6RaReachableTime
         TimeTicks,
      er1645v2Lan2FGVlanIpV6RaRetransmitTime
         TimeTicks,
      er1645v2Lan2FGVlanIpV6RaHopLimit
         Integer32,
      er1645v2Lan2FGVlanIpV6RaDefaultLifeTime
         TimeTicks,
      er1645v2Lan2FGVlanIpV6RaDnsOptionsRdnssLifeTime
         TimeTicks,
      er1645v2Lan2FGVlanIpV6RaDnsOptionsRdnssImportServers
         INTEGER,
      er1645v2Lan2FGVlanIpV6RaDnsOptionsDnsslLifeTime
         TimeTicks,
      er1645v2Lan2FGVlanIpV6RaDnsOptionsDnsslImportDomains
         INTEGER,
      er1645v2Lan2FGVlanIpV6RsSend
         INTEGER,
      er1645v2Lan2FGVlanIpV6RsMaxRandomDelay
         TimeTicks,
      er1645v2Lan2FGVlanIpV6RsInterval
         TimeTicks,
      er1645v2Lan2FGVlanIpV6RsMaxSolicitations
         Integer32,
      er1645v2Lan2FGVlanIpV6TrafficPolicyInbound
         DisplayString,
      er1645v2Lan2FGVlanIpV6TrafficPolicyOutbound
         DisplayString,
      er1645v2Lan2FGVlanIpV6FirewallZone
         DisplayString,
      er1645v2Lan2FGVlanIpV6DhcpClientAddrAC
         INTEGER,
      er1645v2Lan2FGVlanIpV6DhcpClientPrDelMode
         INTEGER,
      er1645v2Lan2FGVlanIpV6DhcpClientPrDelPool
         DisplayString,
      er1645v2Lan2FGVlanIpV6DhcpClientPrDelPdExclOpt
         INTEGER,
      er1645v2Lan2FGVlanIpV6DhcpClientDnsServerPref
         Integer32,
      er1645v2Lan2FGVlanIpV6DhcpClientRapidCommit
         INTEGER,
      er1645v2Lan2FGVlanIpV6DhcpClientTimersSolTimeOut
         TimeTicks,
      er1645v2Lan2FGVlanIpV6DhcpClientTimersSolMaxRt
         TimeTicks,
      er1645v2Lan2FGVlanIpV6DhcpClientTimersInfoRefresh
         TimeTicks,
      er1645v2Lan2FGVlanIpV6DhcpServerMode
         INTEGER,
      er1645v2Lan2FGVlanIpV6DhcpServerPreference
         Integer32,
      er1645v2Lan2FGVlanIpV6DhcpServerPool
         DisplayString,
      er1645v2Lan2FGVlanIpV6DhcpServerRapidCommit
         INTEGER,
      er1645v2Lan2FGVlanIpV6DhcpServerTimersInfoRefresh
         TimeTicks,
      er1645v2Lan2FGVlanIpV6DhcpRelayMode
         INTEGER,
      er1645v2Lan2FGVlanIpV6SendRedirect
         INTEGER,
      er1645v2Lan2FGVlanIpV6LinkMtu
         Integer32,
      er1645v2Lan2FGVlanIpV6InterfaceId
         OCTET STRING,
      er1645v2Lan2FGVlanIpV6MF
         Integer32,
      er1645v2Lan2FGVlanIpV6IcmpMessagesNoRoute
         INTEGER,
      er1645v2Lan2FGVlanIpV6IcmpMessagesBeyondScope
         INTEGER,
      er1645v2Lan2FGVlanIpV6IcmpMessagesAddressUnreachable
         INTEGER,
      er1645v2Lan2FGVlanIpV6IcmpMessagesPortUnreachable
         INTEGER,
      er1645v2Lan2FGVlanIpV6IcmpMessagesPacketTooBig
         INTEGER,
      er1645v2Lan2FGVlanIpV6IcmpMessagesHopLimitExceeded
         INTEGER,
      er1645v2Lan2FGVlanIpV6IcmpMessagesFragTimeExceeded
         INTEGER,
      er1645v2Lan2FGVlanIpV6IcmpMessagesHeaderFieldErr
         INTEGER,
      er1645v2Lan2FGVlanIpV6IcmpMessagesOptionUnrecognized
         INTEGER,
      er1645v2Lan2FGVlanIpV6IcmpMessagesRedirect
         INTEGER,
      er1645v2Lan2FGVlanBridgingAccList
         DisplayString,
      er1645v2Lan2FGVlanBridgingInACL
         DisplayString,
      er1645v2Lan2FGVlanBridgingTp
         DisplayString,
      er1645v2Lan2FGVlanBridgingBrGrp
         DisplayString,
      er1645v2Lan2FGVlanBridgingLimBC
         INTEGER,
      er1645v2Lan2FGVlanBridgingPrivateMode
         INTEGER,
      er1645v2Lan2FGVlanBridgingLearning
         INTEGER,
      er1645v2Lan2FGVlanBridgingMaxCacheSize
         INTEGER,
      er1645v2Lan2FGVlanBridgingRelearnDropOnRelearn
         INTEGER,
      er1645v2Lan2FGVlanBridgingRelearnShutdownThreshold
         Integer32,
      er1645v2Lan2FGVlanBridgingRelearnShutdownTime
         TimeTicks,
      er1645v2Lan2FGVlanBridgingRelearnLoopDetection
         INTEGER,
      er1645v2Lan2FGVlanBridgingRelearnLoopDetectionInterval
         TimeTicks,
      er1645v2Lan2FGVlanBridgingVlanMemberShip
         INTEGER,
      er1645v2Lan2FGVlanBridgingVlTUntaggedAction
         INTEGER,
      er1645v2Lan2FGVlanBridgingVlTUntaggedTagInfoTpid
         INTEGER,
      er1645v2Lan2FGVlanBridgingVlTUntaggedTagInfoVid
         Integer32,
      er1645v2Lan2FGVlanBridgingVlTUnknownVlansAction
         INTEGER,
      er1645v2Lan2FGVlanBridgingVlTUnknownVlansTagInfoTpid
         INTEGER,
      er1645v2Lan2FGVlanBridgingVlTUnknownVlansTagInfoVid
         Integer32,
      er1645v2Lan2FGVlanBridgingDot1adType
         INTEGER,
      er1645v2Lan2FGVlanBridgingPriority
         Integer32,
      er1645v2Lan2FGVlanBridgingPathCost
         Integer32,
      er1645v2Lan2FGVlanBridgingInternalPathCost
         Integer32,
      er1645v2Lan2FGVlanBridgingTCD
         INTEGER,
      er1645v2Lan2FGVlanBridgingRestrictedRole
         INTEGER,
      er1645v2Lan2FGVlanBridgingAdminEdge
         INTEGER,
      er1645v2Lan2FGVlanBridgingOamMacDeviceMac
         DisplayString,
      er1645v2Lan2FGVlanBridgingOamMacUserMac
         OCTET STRING,
      er1645v2Lan2FGVlanBridgingOamMacBridgeMac
         DisplayString,
      er1645v2Lan2FGVlanBridgingMgmtInline
         INTEGER,
      er1645v2Lan2FGVlanBridgingL2ptMode
         INTEGER,
      er1645v2Lan2FGVlanBridgingL2ptProtocols
         Integer32,
      er1645v2Lan2FGVlanBridgingL2ptDestMac
         OCTET STRING,
      er1645v2Lan2FGVlanBridgingL2ptCos
         INTEGER,
      er1645v2Lan2FGVlanBridgingL2ptDropThrStp
         INTEGER,
      er1645v2Lan2FGVlanBridgingL2ptDropThrLldp
         INTEGER,
      er1645v2Lan2FGVlanBridgingL2ptDropThrOam
         INTEGER,
      er1645v2Lan2FGVlanBridgingL2ptDropThrCdp
         INTEGER,
      er1645v2Lan2FGVlanBridgingL2ptDropThrVtp
         INTEGER,
      er1645v2Lan2FGVlanBridgingL2ptDropThrLacp
         INTEGER,
      er1645v2Lan2FGVlanBridgingL2ptDropThrEfmOam
         INTEGER,
      er1645v2Lan2FGVlanBridgingL2ptDropThrPvst
         INTEGER,
      er1645v2Lan2FGVlanBridgingL2ptDropThrMmrp
         INTEGER,
      er1645v2Lan2FGVlanBridgingL2ptDropThrMvrp
         INTEGER,
      er1645v2Lan2FGVlanBridgingL2ptDropThrGvrp
         INTEGER,
      er1645v2Lan2FGVlanBridgingL2ptDropThrGmrp
         INTEGER,
      er1645v2Lan2FGVlanBridgingL2ptDropThrDtp
         INTEGER,
      er1645v2Lan2FGVlanBridgingL2ptDropThrPagp
         INTEGER,
      er1645v2Lan2FGVlanBridgingL2ptDropThrUdld
         INTEGER,
      er1645v2Lan2FGVlanVlanVid
         INTEGER,
      er1645v2Lan2FGVlanVlanVidExtensionSingle
         OCTET STRING,
      er1645v2Lan2FGVlanVlanVidExtensionEndVid
         Integer32,
      er1645v2Lan2FGVlanVlanTpid
         INTEGER,
      er1645v2Lan2FGVlanVlanTagSign
         INTEGER,
      er1645v2Lan2FGVlanVlanChTos
         INTEGER,
      er1645v2Lan2FGVlanVlanCTMapP0
         INTEGER,
      er1645v2Lan2FGVlanVlanCTMapP1
         INTEGER,
      er1645v2Lan2FGVlanVlanCTMapP2
         INTEGER,
      er1645v2Lan2FGVlanVlanCTMapP3
         INTEGER,
      er1645v2Lan2FGVlanVlanCTMapP4
         INTEGER,
      er1645v2Lan2FGVlanVlanCTMapP5
         INTEGER,
      er1645v2Lan2FGVlanVlanCTMapP6
         INTEGER,
      er1645v2Lan2FGVlanVlanCTMapP7
         INTEGER,
      er1645v2Lan2FGVlanVlanTxCos
         INTEGER,
      er1645v2Lan2FGVlanVlanCCMapP0
         Integer32,
      er1645v2Lan2FGVlanVlanCCMapP1
         Integer32,
      er1645v2Lan2FGVlanVlanCCMapP2
         Integer32,
      er1645v2Lan2FGVlanVlanCCMapP3
         Integer32,
      er1645v2Lan2FGVlanVlanCCMapP4
         Integer32,
      er1645v2Lan2FGVlanVlanCCMapP5
         Integer32,
      er1645v2Lan2FGVlanVlanCCMapP6
         Integer32,
      er1645v2Lan2FGVlanVlanCCMapP7
         Integer32,
      er1645v2Lan2FGVlanVlanQCMapQueue1
         Integer32,
      er1645v2Lan2FGVlanVlanQCMapQueue2
         Integer32,
      er1645v2Lan2FGVlanVlanQCMapQueue3
         Integer32,
      er1645v2Lan2FGVlanVlanQCMapQueue4
         Integer32,
      er1645v2Lan2FGVlanVlanQCMapQueue5
         Integer32,
      er1645v2Lan2FGVlanVlanQCMapLowDelayQueue
         Integer32,
      er1645v2Lan2FGVlanVlanQCMapLowDelay2Queue
         Integer32,
      er1645v2Lan2FGVlanVlanQCMapSystemQueue
         Integer32,
      er1645v2Lan2FGVlanVlanQinQSVid
         Integer32,
      er1645v2Lan2FGVlanVlanQinQSTpid
         INTEGER,
      er1645v2Lan2FGVlanVlanArpTimeOut
         TimeTicks,
      er1645v2Lan2FGVlanVlanArpProxyArp
         INTEGER,
      er1645v2Lan2FGVlanBandwidthMode
         INTEGER,
      er1645v2Lan2FGVlanBandwidthCir
         Integer32,
      er1645v2Lan2FGVlanBandwidthEir
         Integer32,
      er1645v2Lan2FGVlanBandwidthUnit
         INTEGER,
      er1645v2Lan2FGVlanBandwidthTc
         INTEGER,
      er1645v2Lan2FGVlanBandwidthTcFactor
         INTEGER,
      er1645v2Lan2FGVlanBandwidthCorrType
         INTEGER,
      er1645v2Lan2FGVlanBandwidthCorrPredefEncapsFrameRelay
         DisplayString,
      er1645v2Lan2FGVlanBandwidthCorrPredefEncapsPpp
         DisplayString,
      er1645v2Lan2FGVlanBandwidthCorrPredefEncapsAtmHl
         INTEGER,
      er1645v2Lan2FGVlanBandwidthCorrPredefEncapsAtmMp
         INTEGER,
      er1645v2Lan2FGVlanBandwidthCorrPredefEncapsHdlc
         DisplayString,
      er1645v2Lan2FGVlanBandwidthCorrPredefEncapsEfmFs
         Integer32,
      er1645v2Lan2FGVlanBandwidthCorrPredefEncapsEfmIb
         Integer32,
      er1645v2Lan2FGVlanBandwidthCorrPredefMode
         INTEGER,
      er1645v2Lan2FGVlanBandwidthCorrManualOverhead
         Integer32,
      er1645v2Lan2FGVlanBandwidthCorrManualFrameData
         Counter32,
      er1645v2Lan2FGVlanBandwidthCorrManualFrameHeader
         Counter32,
      er1645v2Lan2FGVlanBandwidthMaxFifoQLen
         Integer32,
      er1645v2Lan2FGVlanBandwidthDeFlagCir
         INTEGER,
      er1645v2Lan2FGVlanBandwidthDeFlagEir
         INTEGER,
      er1645v2Lan2FGVlanBandwidthDeFlagViolate
         INTEGER,
      er1645v2Lan2FGVlanBandwidthActCirActNone
         OCTET STRING,
      er1645v2Lan2FGVlanBandwidthActCirActEthCos1
         INTEGER,
      er1645v2Lan2FGVlanBandwidthActCirActEthDei1
         INTEGER,
      er1645v2Lan2FGVlanBandwidthActCirActEthCos2
         INTEGER,
      er1645v2Lan2FGVlanBandwidthActCirActEthDei2
         INTEGER,
      er1645v2Lan2FGVlanBandwidthActCirActEthCos3
         INTEGER,
      er1645v2Lan2FGVlanBandwidthActCirActEthDei3
         INTEGER,
      er1645v2Lan2FGVlanBandwidthActCirActEthCos4
         INTEGER,
      er1645v2Lan2FGVlanBandwidthActCirActEthDei4
         INTEGER,
      er1645v2Lan2FGVlanBandwidthActCirActEthCos5
         INTEGER,
      er1645v2Lan2FGVlanBandwidthActCirActEthDei5
         INTEGER,
      er1645v2Lan2FGVlanBandwidthActCirActEthCos6
         INTEGER,
      er1645v2Lan2FGVlanBandwidthActCirActEthDei6
         INTEGER,
      er1645v2Lan2FGVlanBandwidthActCirActEthCos7
         INTEGER,
      er1645v2Lan2FGVlanBandwidthActCirActEthDei7
         INTEGER,
      er1645v2Lan2FGVlanBandwidthActCirActEthCos8
         INTEGER,
      er1645v2Lan2FGVlanBandwidthActCirActEthDei8
         INTEGER,
      er1645v2Lan2FGVlanBandwidthActCirActEthTos
         INTEGER,
      er1645v2Lan2FGVlanBandwidthActCirActEthQueue
         INTEGER,
      er1645v2Lan2FGVlanBandwidthActCirActEthDrpLev
         INTEGER,
      er1645v2Lan2FGVlanBandwidthActCirActEthDeFlag
         INTEGER,
      er1645v2Lan2FGVlanBandwidthActCirActIpTos
         INTEGER,
      er1645v2Lan2FGVlanBandwidthActCirActIpQueue
         INTEGER,
      er1645v2Lan2FGVlanBandwidthActCirActIpDrpLev
         INTEGER,
      er1645v2Lan2FGVlanBandwidthActCirActIpDeFlag
         INTEGER,
      er1645v2Lan2FGVlanBandwidthActEirActNone
         OCTET STRING,
      er1645v2Lan2FGVlanBandwidthActEirActEthCos1
         INTEGER,
      er1645v2Lan2FGVlanBandwidthActEirActEthDei1
         INTEGER,
      er1645v2Lan2FGVlanBandwidthActEirActEthCos2
         INTEGER,
      er1645v2Lan2FGVlanBandwidthActEirActEthDei2
         INTEGER,
      er1645v2Lan2FGVlanBandwidthActEirActEthCos3
         INTEGER,
      er1645v2Lan2FGVlanBandwidthActEirActEthDei3
         INTEGER,
      er1645v2Lan2FGVlanBandwidthActEirActEthCos4
         INTEGER,
      er1645v2Lan2FGVlanBandwidthActEirActEthDei4
         INTEGER,
      er1645v2Lan2FGVlanBandwidthActEirActEthCos5
         INTEGER,
      er1645v2Lan2FGVlanBandwidthActEirActEthDei5
         INTEGER,
      er1645v2Lan2FGVlanBandwidthActEirActEthCos6
         INTEGER,
      er1645v2Lan2FGVlanBandwidthActEirActEthDei6
         INTEGER,
      er1645v2Lan2FGVlanBandwidthActEirActEthCos7
         INTEGER,
      er1645v2Lan2FGVlanBandwidthActEirActEthDei7
         INTEGER,
      er1645v2Lan2FGVlanBandwidthActEirActEthCos8
         INTEGER,
      er1645v2Lan2FGVlanBandwidthActEirActEthDei8
         INTEGER,
      er1645v2Lan2FGVlanBandwidthActEirActEthTos
         INTEGER,
      er1645v2Lan2FGVlanBandwidthActEirActEthQueue
         INTEGER,
      er1645v2Lan2FGVlanBandwidthActEirActEthDrpLev
         INTEGER,
      er1645v2Lan2FGVlanBandwidthActEirActEthDeFlag
         INTEGER,
      er1645v2Lan2FGVlanBandwidthActEirActIpTos
         INTEGER,
      er1645v2Lan2FGVlanBandwidthActEirActIpQueue
         INTEGER,
      er1645v2Lan2FGVlanBandwidthActEirActIpDrpLev
         INTEGER,
      er1645v2Lan2FGVlanBandwidthActEirActIpDeFlag
         INTEGER,
      er1645v2Lan2FGVlanBandwidthActViolActNone
         OCTET STRING,
      er1645v2Lan2FGVlanBandwidthActViolActDrop
         OCTET STRING,
      er1645v2Lan2FGVlanBandwidthActViolActEthCos1
         INTEGER,
      er1645v2Lan2FGVlanBandwidthActViolActEthDei1
         INTEGER,
      er1645v2Lan2FGVlanBandwidthActViolActEthCos2
         INTEGER,
      er1645v2Lan2FGVlanBandwidthActViolActEthDei2
         INTEGER,
      er1645v2Lan2FGVlanBandwidthActViolActEthCos3
         INTEGER,
      er1645v2Lan2FGVlanBandwidthActViolActEthDei3
         INTEGER,
      er1645v2Lan2FGVlanBandwidthActViolActEthCos4
         INTEGER,
      er1645v2Lan2FGVlanBandwidthActViolActEthDei4
         INTEGER,
      er1645v2Lan2FGVlanBandwidthActViolActEthCos5
         INTEGER,
      er1645v2Lan2FGVlanBandwidthActViolActEthDei5
         INTEGER,
      er1645v2Lan2FGVlanBandwidthActViolActEthCos6
         INTEGER,
      er1645v2Lan2FGVlanBandwidthActViolActEthDei6
         INTEGER,
      er1645v2Lan2FGVlanBandwidthActViolActEthCos7
         INTEGER,
      er1645v2Lan2FGVlanBandwidthActViolActEthDei7
         INTEGER,
      er1645v2Lan2FGVlanBandwidthActViolActEthCos8
         INTEGER,
      er1645v2Lan2FGVlanBandwidthActViolActEthDei8
         INTEGER,
      er1645v2Lan2FGVlanBandwidthActViolActEthTos
         INTEGER,
      er1645v2Lan2FGVlanBandwidthActViolActEthQueue
         INTEGER,
      er1645v2Lan2FGVlanBandwidthActViolActEthDrpLev
         INTEGER,
      er1645v2Lan2FGVlanBandwidthActViolActEthDeFlag
         INTEGER,
      er1645v2Lan2FGVlanBandwidthActViolActIpTos
         INTEGER,
      er1645v2Lan2FGVlanBandwidthActViolActIpQueue
         INTEGER,
      er1645v2Lan2FGVlanBandwidthActViolActIpDrpLev
         INTEGER,
      er1645v2Lan2FGVlanBandwidthActViolActIpDeFlag
         INTEGER,
      er1645v2Lan2FGVlanInbBwMode
         INTEGER,
      er1645v2Lan2FGVlanInbBwCir
         Integer32,
      er1645v2Lan2FGVlanInbBwEir
         Integer32,
      er1645v2Lan2FGVlanInbBwUnit
         INTEGER,
      er1645v2Lan2FGVlanInbBwTc
         INTEGER,
      er1645v2Lan2FGVlanInbBwTcFactor
         INTEGER,
      er1645v2Lan2FGVlanInbBwCorrType
         INTEGER,
      er1645v2Lan2FGVlanInbBwCorrPredefEncapsFrameRelay
         DisplayString,
      er1645v2Lan2FGVlanInbBwCorrPredefEncapsPpp
         DisplayString,
      er1645v2Lan2FGVlanInbBwCorrPredefEncapsAtmHl
         INTEGER,
      er1645v2Lan2FGVlanInbBwCorrPredefEncapsAtmMp
         INTEGER,
      er1645v2Lan2FGVlanInbBwCorrPredefEncapsHdlc
         DisplayString,
      er1645v2Lan2FGVlanInbBwCorrPredefEncapsEfmFs
         Integer32,
      er1645v2Lan2FGVlanInbBwCorrPredefEncapsEfmIb
         Integer32,
      er1645v2Lan2FGVlanInbBwCorrPredefMode
         INTEGER,
      er1645v2Lan2FGVlanInbBwCorrManualOverhead
         Integer32,
      er1645v2Lan2FGVlanInbBwCorrManualFrameData
         Counter32,
      er1645v2Lan2FGVlanInbBwCorrManualFrameHeader
         Counter32,
      er1645v2Lan2FGVlanInbBwMaxFifoQLen
         Integer32,
      er1645v2Lan2FGVlanInbBwPriorityPolicy
         DisplayString,
      er1645v2Lan2FGVlanInbBwDeFlagCir
         INTEGER,
      er1645v2Lan2FGVlanInbBwDeFlagEir
         INTEGER,
      er1645v2Lan2FGVlanInbBwDeFlagViolate
         INTEGER,
      er1645v2Lan2FGVlanInbBwActCirActNone
         OCTET STRING,
      er1645v2Lan2FGVlanInbBwActCirActEthCos1
         INTEGER,
      er1645v2Lan2FGVlanInbBwActCirActEthDei1
         INTEGER,
      er1645v2Lan2FGVlanInbBwActCirActEthCos2
         INTEGER,
      er1645v2Lan2FGVlanInbBwActCirActEthDei2
         INTEGER,
      er1645v2Lan2FGVlanInbBwActCirActEthCos3
         INTEGER,
      er1645v2Lan2FGVlanInbBwActCirActEthDei3
         INTEGER,
      er1645v2Lan2FGVlanInbBwActCirActEthCos4
         INTEGER,
      er1645v2Lan2FGVlanInbBwActCirActEthDei4
         INTEGER,
      er1645v2Lan2FGVlanInbBwActCirActEthCos5
         INTEGER,
      er1645v2Lan2FGVlanInbBwActCirActEthDei5
         INTEGER,
      er1645v2Lan2FGVlanInbBwActCirActEthCos6
         INTEGER,
      er1645v2Lan2FGVlanInbBwActCirActEthDei6
         INTEGER,
      er1645v2Lan2FGVlanInbBwActCirActEthCos7
         INTEGER,
      er1645v2Lan2FGVlanInbBwActCirActEthDei7
         INTEGER,
      er1645v2Lan2FGVlanInbBwActCirActEthCos8
         INTEGER,
      er1645v2Lan2FGVlanInbBwActCirActEthDei8
         INTEGER,
      er1645v2Lan2FGVlanInbBwActCirActEthTos
         INTEGER,
      er1645v2Lan2FGVlanInbBwActCirActEthQueue
         INTEGER,
      er1645v2Lan2FGVlanInbBwActCirActEthDrpLev
         INTEGER,
      er1645v2Lan2FGVlanInbBwActCirActEthDeFlag
         INTEGER,
      er1645v2Lan2FGVlanInbBwActCirActIpTos
         INTEGER,
      er1645v2Lan2FGVlanInbBwActCirActIpQueue
         INTEGER,
      er1645v2Lan2FGVlanInbBwActCirActIpDrpLev
         INTEGER,
      er1645v2Lan2FGVlanInbBwActCirActIpDeFlag
         INTEGER,
      er1645v2Lan2FGVlanInbBwActEirActNone
         OCTET STRING,
      er1645v2Lan2FGVlanInbBwActEirActEthCos1
         INTEGER,
      er1645v2Lan2FGVlanInbBwActEirActEthDei1
         INTEGER,
      er1645v2Lan2FGVlanInbBwActEirActEthCos2
         INTEGER,
      er1645v2Lan2FGVlanInbBwActEirActEthDei2
         INTEGER,
      er1645v2Lan2FGVlanInbBwActEirActEthCos3
         INTEGER,
      er1645v2Lan2FGVlanInbBwActEirActEthDei3
         INTEGER,
      er1645v2Lan2FGVlanInbBwActEirActEthCos4
         INTEGER,
      er1645v2Lan2FGVlanInbBwActEirActEthDei4
         INTEGER,
      er1645v2Lan2FGVlanInbBwActEirActEthCos5
         INTEGER,
      er1645v2Lan2FGVlanInbBwActEirActEthDei5
         INTEGER,
      er1645v2Lan2FGVlanInbBwActEirActEthCos6
         INTEGER,
      er1645v2Lan2FGVlanInbBwActEirActEthDei6
         INTEGER,
      er1645v2Lan2FGVlanInbBwActEirActEthCos7
         INTEGER,
      er1645v2Lan2FGVlanInbBwActEirActEthDei7
         INTEGER,
      er1645v2Lan2FGVlanInbBwActEirActEthCos8
         INTEGER,
      er1645v2Lan2FGVlanInbBwActEirActEthDei8
         INTEGER,
      er1645v2Lan2FGVlanInbBwActEirActEthTos
         INTEGER,
      er1645v2Lan2FGVlanInbBwActEirActEthQueue
         INTEGER,
      er1645v2Lan2FGVlanInbBwActEirActEthDrpLev
         INTEGER,
      er1645v2Lan2FGVlanInbBwActEirActEthDeFlag
         INTEGER,
      er1645v2Lan2FGVlanInbBwActEirActIpTos
         INTEGER,
      er1645v2Lan2FGVlanInbBwActEirActIpQueue
         INTEGER,
      er1645v2Lan2FGVlanInbBwActEirActIpDrpLev
         INTEGER,
      er1645v2Lan2FGVlanInbBwActEirActIpDeFlag
         INTEGER,
      er1645v2Lan2FGVlanInbBwActViolActNone
         OCTET STRING,
      er1645v2Lan2FGVlanInbBwActViolActDrop
         OCTET STRING,
      er1645v2Lan2FGVlanInbBwActViolActEthCos1
         INTEGER,
      er1645v2Lan2FGVlanInbBwActViolActEthDei1
         INTEGER,
      er1645v2Lan2FGVlanInbBwActViolActEthCos2
         INTEGER,
      er1645v2Lan2FGVlanInbBwActViolActEthDei2
         INTEGER,
      er1645v2Lan2FGVlanInbBwActViolActEthCos3
         INTEGER,
      er1645v2Lan2FGVlanInbBwActViolActEthDei3
         INTEGER,
      er1645v2Lan2FGVlanInbBwActViolActEthCos4
         INTEGER,
      er1645v2Lan2FGVlanInbBwActViolActEthDei4
         INTEGER,
      er1645v2Lan2FGVlanInbBwActViolActEthCos5
         INTEGER,
      er1645v2Lan2FGVlanInbBwActViolActEthDei5
         INTEGER,
      er1645v2Lan2FGVlanInbBwActViolActEthCos6
         INTEGER,
      er1645v2Lan2FGVlanInbBwActViolActEthDei6
         INTEGER,
      er1645v2Lan2FGVlanInbBwActViolActEthCos7
         INTEGER,
      er1645v2Lan2FGVlanInbBwActViolActEthDei7
         INTEGER,
      er1645v2Lan2FGVlanInbBwActViolActEthCos8
         INTEGER,
      er1645v2Lan2FGVlanInbBwActViolActEthDei8
         INTEGER,
      er1645v2Lan2FGVlanInbBwActViolActEthTos
         INTEGER,
      er1645v2Lan2FGVlanInbBwActViolActEthQueue
         INTEGER,
      er1645v2Lan2FGVlanInbBwActViolActEthDrpLev
         INTEGER,
      er1645v2Lan2FGVlanInbBwActViolActEthDeFlag
         INTEGER,
      er1645v2Lan2FGVlanInbBwActViolActIpTos
         INTEGER,
      er1645v2Lan2FGVlanInbBwActViolActIpQueue
         INTEGER,
      er1645v2Lan2FGVlanInbBwActViolActIpDrpLev
         INTEGER,
      er1645v2Lan2FGVlanInbBwActViolActIpDeFlag
         INTEGER,
      er1645v2Lan2FGVlanPppoE
         INTEGER,
      er1645v2Lan2FGVlanPppLnkMOperation
         INTEGER,
      er1645v2Lan2FGVlanPppLnkMInterval
         TimeTicks,
      er1645v2Lan2FGVlanPppLnkMRepTimeOut
         TimeTicks,
      er1645v2Lan2FGVlanPppLnkMFailsPrmt
         Integer32,
      er1645v2Lan2FGVlanPppAuthentication
         INTEGER,
      er1645v2Lan2FGVlanPppAuthenPeriod
         TimeTicks,
      er1645v2Lan2FGVlanPppSessionName
         DisplayString,
      er1645v2Lan2FGVlanPppSessionSecret
         DisplayString,
      er1645v2Lan2FGVlanPppEncModeSessionSecret
         INTEGER,
      er1645v2Lan2FGVlanPppEncSessionSecret
         DisplayString,
      er1645v2Lan2FGVlanPppServiceName
         DisplayString,
      er1645v2Lan2FGVlanPbbMode
         INTEGER,
      er1645v2Lan2FGVlanPbbTxCos
         Integer32,
      er1645v2Lan2FGVlanPbbIsid
         Integer32,
      er1645v2Lan2FGVlanPbbDestMac
         OCTET STRING,
      er1645v2Lan2FGVlanPbbCustomGroupMac
         OCTET STRING
      }

er1645v2Lan2FGVlanActions OBJECT-TYPE
   SYNTAX      VariableLengthTableActions
   MAX-ACCESS  read-write
   STATUS      current
   DESCRIPTION
      "By way of this field, some manipulations
       on this table may be performed."
   ::= {er1645v2Lan2FGVlanEntry 2}

er1645v2Lan2FGVlanTableIx OBJECT-TYPE
   SYNTAX      TableIndex
   MAX-ACCESS  not-accessible
   STATUS      current
   DESCRIPTION
      ""
   ::= {er1645v2Lan2FGVlanEntry 11}

er1645v2Lan2FGVlanName OBJECT-TYPE
   SYNTAX      DisplayString
   MAX-ACCESS  read-write
   STATUS      current
   DESCRIPTION
      "Path: ethernet2.editConf.vlan.name"
   ::= {er1645v2Lan2FGVlanEntry 16777216}

er1645v2Lan2FGVlanRemark OBJECT-TYPE
   SYNTAX      DisplayString
   MAX-ACCESS  read-write
   STATUS      current
   DESCRIPTION
      "Path: ethernet2.editConf.vlan.remark"
   ::= {er1645v2Lan2FGVlanEntry 1157627904}

er1645v2Lan2FGVlanAdminStatus OBJECT-TYPE
   SYNTAX      INTEGER
               {
               up (1),
               down (2)
               }
   MAX-ACCESS  read-write
   STATUS      current
   DESCRIPTION
      "Path: ethernet2.editConf.vlan.adminStatus

       Possibilities:
               up   (1)
               down   (2)"
   ::= {er1645v2Lan2FGVlanEntry 33554432}

er1645v2Lan2FGVlanMode OBJECT-TYPE
   SYNTAX      INTEGER
               {
               routing (1),
               bridging (2),
               ipV6 (16),
               ipV6ipV4 (17),
               multilink (8)
               }
   MAX-ACCESS  read-write
   STATUS      current
   DESCRIPTION
      "Path: ethernet2.editConf.vlan.mode

       Possibilities:
               routing   (1)
               bridging   (2)
               ipV6   (16)
               ipV6/ipV4   (17)
               multilink   (8)"
   ::= {er1645v2Lan2FGVlanEntry 67108864}

er1645v2Lan2FGVlanPriorityPolicy OBJECT-TYPE
   SYNTAX      DisplayString
   MAX-ACCESS  read-write
   STATUS      current
   DESCRIPTION
      "Path: ethernet2.editConf.vlan.priorityPolicy"
   ::= {er1645v2Lan2FGVlanEntry 83886080}

er1645v2Lan2FGVlanIpVrfRouter OBJECT-TYPE
   SYNTAX      DisplayString
   MAX-ACCESS  read-write
   STATUS      current
   DESCRIPTION
      "Path: ethernet2.editConf.vlan.ip.vrfRouter"
   ::= {er1645v2Lan2FGVlanEntry 53215232}

er1645v2Lan2FGVlanIpAdr OBJECT-TYPE
   SYNTAX      IpAddress
   MAX-ACCESS  read-write
   STATUS      current
   DESCRIPTION
      "Path: ethernet2.editConf.vlan.ip.address"
   ::= {er1645v2Lan2FGVlanEntry 58261504}

er1645v2Lan2FGVlanIpNetm OBJECT-TYPE
   SYNTAX      IpAddress
   MAX-ACCESS  read-write
   STATUS      current
   DESCRIPTION
      "Path: ethernet2.editConf.vlan.ip.netMask"
   ::= {er1645v2Lan2FGVlanEntry 58392576}

er1645v2Lan2FGVlanIpSNetName OBJECT-TYPE
   SYNTAX      INTEGER
               {
               slOPTg (0),
               corp (2),
               dmz (3),
               internet (1)
               }
   MAX-ACCESS  read-write
   STATUS      current
   DESCRIPTION
      "Path: ethernet2.editConf.vlan.ip.sNet.name

       Possibilities:
               <OPT>   (0)
               corp   (2)
               dmz   (3)
               internet   (1)"
   ::= {er1645v2Lan2FGVlanEntry 53674240}

er1645v2Lan2FGVlanIpSNetCust OBJECT-TYPE
   SYNTAX      DisplayString
   MAX-ACCESS  read-write
   STATUS      current
   DESCRIPTION
      "Path: ethernet2.editConf.vlan.ip.sNet.custom"
   ::= {er1645v2Lan2FGVlanEntry 53674496}

er1645v2Lan2FGVlanIpDhcpC OBJECT-TYPE
   SYNTAX      INTEGER
               {
               disabled (0),
               enabled (1)
               }
   MAX-ACCESS  read-write
   STATUS      current
   DESCRIPTION
      "Path: ethernet2.editConf.vlan.ip.dhcpClient

       Possibilities:
               disabled   (0)
               enabled   (1)"
   ::= {er1645v2Lan2FGVlanEntry 53608448}

er1645v2Lan2FGVlanIpDhcpGatewayPreference OBJECT-TYPE
   SYNTAX      Integer32
   MAX-ACCESS  read-write
   STATUS      current
   DESCRIPTION
      "Path: ethernet2.editConf.vlan.ip.dhcp.gatewayPreference"
   ::= {er1645v2Lan2FGVlanEntry 53739776}

er1645v2Lan2FGVlanIpDhcpRoutePreference OBJECT-TYPE
   SYNTAX      Integer32
   MAX-ACCESS  read-write
   STATUS      current
   DESCRIPTION
      "Path: ethernet2.editConf.vlan.ip.dhcp.routePreference"
   ::= {er1645v2Lan2FGVlanEntry 53740032}

er1645v2Lan2FGVlanIpDhcpDnsPreference OBJECT-TYPE
   SYNTAX      Integer32
   MAX-ACCESS  read-write
   STATUS      current
   DESCRIPTION
      "Path: ethernet2.editConf.vlan.ip.dhcp.dnsPreference"
   ::= {er1645v2Lan2FGVlanEntry 53740288}

er1645v2Lan2FGVlanIpMtu OBJECT-TYPE
   SYNTAX      Integer32
   MAX-ACCESS  read-write
   STATUS      current
   DESCRIPTION
      "Path: ethernet2.editConf.vlan.ip.mtu"
   ::= {er1645v2Lan2FGVlanEntry 52953088}

er1645v2Lan2FGVlanIpMssAdjust OBJECT-TYPE
   SYNTAX      INTEGER
               {
               disabled (0),
               auto (65536)
               }
   MAX-ACCESS  read-write
   STATUS      current
   DESCRIPTION
      "Path: ethernet2.editConf.vlan.ip.mssAdjust

       Possibilities:
               disabled   (0)
               auto   (65536)"
   ::= {er1645v2Lan2FGVlanEntry 53280768}

er1645v2Lan2FGVlanIpRipMetric OBJECT-TYPE
   SYNTAX      Integer32
   MAX-ACCESS  read-write
   STATUS      current
   DESCRIPTION
      "Path: ethernet2.editConf.vlan.ip.rip.metric"
   ::= {er1645v2Lan2FGVlanEntry 51712768}

er1645v2Lan2FGVlanIpRipMetricOut OBJECT-TYPE
   SYNTAX      Integer32
   MAX-ACCESS  read-write
   STATUS      current
   DESCRIPTION
      "Path: ethernet2.editConf.vlan.ip.rip.metricOut"
   ::= {er1645v2Lan2FGVlanEntry 51713024}

er1645v2Lan2FGVlanIpRipMode OBJECT-TYPE
   SYNTAX      INTEGER
               {
               disabled (0),
               passive (1),
               active (2)
               }
   MAX-ACCESS  read-write
   STATUS      current
   DESCRIPTION
      "Path: ethernet2.editConf.vlan.ip.rip.mode

       Possibilities:
               disabled   (0)
               passive   (1)
               active   (2)"
   ::= {er1645v2Lan2FGVlanEntry 51713280}

er1645v2Lan2FGVlanIpRipTxVer OBJECT-TYPE
   SYNTAX      INTEGER
               {
               rip1 (0),
               rip2 (1),
               rip1mcompatible (2)
               }
   MAX-ACCESS  read-write
   STATUS      current
   DESCRIPTION
      "Path: ethernet2.editConf.vlan.ip.rip.txVersion

       Possibilities:
               rip1   (0)
               rip2   (1)
               rip1-compatible   (2)"
   ::= {er1645v2Lan2FGVlanEntry 51716864}

er1645v2Lan2FGVlanIpRipRxVer OBJECT-TYPE
   SYNTAX      INTEGER
               {
               rip1only (0),
               rip2only (1),
               rip12 (2)
               }
   MAX-ACCESS  read-write
   STATUS      current
   DESCRIPTION
      "Path: ethernet2.editConf.vlan.ip.rip.rxVersion

       Possibilities:
               rip1only   (0)
               rip2only   (1)
               rip1&2   (2)"
   ::= {er1645v2Lan2FGVlanEntry 51717120}

er1645v2Lan2FGVlanIpRipSplitH OBJECT-TYPE
   SYNTAX      INTEGER
               {
               disabled (0),
               enabled (1),
               poisonedReverse (2)
               }
   MAX-ACCESS  read-write
   STATUS      current
   DESCRIPTION
      "Path: ethernet2.editConf.vlan.ip.rip.splitHorizon

       Possibilities:
               disabled   (0)
               enabled   (1)
               poisonedReverse   (2)"
   ::= {er1645v2Lan2FGVlanEntry 51713792}

er1645v2Lan2FGVlanIpRipAuth OBJECT-TYPE
   SYNTAX      INTEGER
               {
               disabled (0),
               texts (1),
               md5 (2)
               }
   MAX-ACCESS  read-write
   STATUS      current
   DESCRIPTION
      "Path: ethernet2.editConf.vlan.ip.rip.authentication

       Possibilities:
               disabled   (0)
               text    (1)
               md5   (2)"
   ::= {er1645v2Lan2FGVlanEntry 51712512}

er1645v2Lan2FGVlanIpRipFilter OBJECT-TYPE
   SYNTAX      DisplayString
   MAX-ACCESS  read-write
   STATUS      current
   DESCRIPTION
      "Path: ethernet2.editConf.vlan.ip.rip.filter"
   ::= {er1645v2Lan2FGVlanEntry 51716096}

er1645v2Lan2FGVlanIpRipFilterIn OBJECT-TYPE
   SYNTAX      DisplayString
   MAX-ACCESS  read-write
   STATUS      current
   DESCRIPTION
      "Path: ethernet2.editConf.vlan.ip.rip.filterIn"
   ::= {er1645v2Lan2FGVlanEntry 51716352}

er1645v2Lan2FGVlanIpRipClearNextHop OBJECT-TYPE
   SYNTAX      INTEGER
               {
               disabled (0),
               enabled (1)
               }
   MAX-ACCESS  read-write
   STATUS      current
   DESCRIPTION
      "Path: ethernet2.editConf.vlan.ip.rip.clearNextHop

       Possibilities:
               disabled   (0)
               enabled   (1)"
   ::= {er1645v2Lan2FGVlanEntry 51708416}

er1645v2Lan2FGVlanIpAccPol OBJECT-TYPE
   SYNTAX      DisplayString
   MAX-ACCESS  read-write
   STATUS      current
   DESCRIPTION
      "Path: ethernet2.editConf.vlan.ip.accessPolicy"
   ::= {er1645v2Lan2FGVlanEntry 53084160}

er1645v2Lan2FGVlanIpAB OBJECT-TYPE
   SYNTAX      DisplayString
   MAX-ACCESS  read-write
   STATUS      current
   DESCRIPTION
      "Path: ethernet2.editConf.vlan.ip.trafficPolicy"
   ::= {er1645v2Lan2FGVlanEntry 51249152}

er1645v2Lan2FGVlanIpMA OBJECT-TYPE
   SYNTAX      INTEGER
               {
               disabled (0),
               enabled (1)
               }
   MAX-ACCESS  read-write
   STATUS      current
   DESCRIPTION
      "Path: ethernet2.editConf.vlan.ip.mgmtAccess

       Possibilities:
               disabled   (0)
               enabled   (1)"
   ::= {er1645v2Lan2FGVlanEntry 51380224}

er1645v2Lan2FGVlanIpMF OBJECT-TYPE
   SYNTAX      Integer32
   MAX-ACCESS  read-write
   STATUS      current
   DESCRIPTION
      "Path: ethernet2.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2FGVlanEntry 51445760}

er1645v2Lan2FGVlanIpDB OBJECT-TYPE
   SYNTAX      INTEGER
               {
               disabled (0),
               enabled (1)
               }
   MAX-ACCESS  read-write
   STATUS      current
   DESCRIPTION
      "Path: ethernet2.editConf.vlan.ip.directedBroadcasts

       Possibilities:
               disabled   (0)
               enabled   (1)"
   ::= {er1645v2Lan2FGVlanEntry 51773440}

er1645v2Lan2FGVlanIpIR OBJECT-TYPE
   SYNTAX      INTEGER
               {
               disabled (0),
               enabled (1)
               }
   MAX-ACCESS  read-write
   STATUS      current
   DESCRIPTION
      "Path: ethernet2.editConf.vlan.ip.icmpRedirects

       Possibilities:
               disabled   (0)
               enabled   (1)"
   ::= {er1645v2Lan2FGVlanEntry 52035584}

er1645v2Lan2FGVlanIpIgmp OBJECT-TYPE
   SYNTAX      INTEGER
               {
               disabled (0),
               proxy (1),
               router (2),
               v3Router (5)
               }
   MAX-ACCESS  read-write
   STATUS      current
   DESCRIPTION
      "Path: ethernet2.editConf.vlan.ip.igmp

       Possibilities:
               disabled   (0)
               proxy   (1)
               router   (2)
               v3Router   (5)"
   ::= {er1645v2Lan2FGVlanEntry 52428800}

er1645v2Lan2FGVlanIpNN OBJECT-TYPE
   SYNTAX      DisplayString
   MAX-ACCESS  read-write
   STATUS      current
   DESCRIPTION
      "Path: ethernet2.editConf.vlan.ip.nat"
   ::= {er1645v2Lan2FGVlanEntry 52101120}

er1645v2Lan2FGVlanIpVrrp OBJECT-TYPE
   SYNTAX      INTEGER
               {
               disabled (0),
               enabled (1)
               }
   MAX-ACCESS  read-write
   STATUS      current
   DESCRIPTION
      "Path: ethernet2.editConf.vlan.ip.vrrp

       Possibilities:
               disabled   (0)
               enabled   (1)"
   ::= {er1645v2Lan2FGVlanEntry 53149696}

er1645v2Lan2FGVlanIpPimMode OBJECT-TYPE
   SYNTAX      INTEGER
               {
               disabled (0),
               sparse (1),
               passive (2)
               }
   MAX-ACCESS  read-write
   STATUS      current
   DESCRIPTION
      "Path: ethernet2.editConf.vlan.ip.pim.mode

       Possibilities:
               disabled   (0)
               sparse   (1)
               passive   (2)"
   ::= {er1645v2Lan2FGVlanEntry 53346560}

er1645v2Lan2FGVlanIpPimDrPriority OBJECT-TYPE
   SYNTAX      Counter32
   MAX-ACCESS  read-write
   STATUS      current
   DESCRIPTION
      "Path: ethernet2.editConf.vlan.ip.pim.drPriority

       32 bit unsigned wrappable counter."
   ::= {er1645v2Lan2FGVlanEntry 53346816}

er1645v2Lan2FGVlanIpPimHelloTime OBJECT-TYPE
   SYNTAX      TimeTicks
   MAX-ACCESS  read-write
   STATUS      current
   DESCRIPTION
      "Path: ethernet2.editConf.vlan.ip.pim.helloTime

       Time in centi-second."
   ::= {er1645v2Lan2FGVlanEntry 53347072}

er1645v2Lan2FGVlanIpPimPropagationDelay OBJECT-TYPE
   SYNTAX      TimeTicks
   MAX-ACCESS  read-write
   STATUS      current
   DESCRIPTION
      "Path: ethernet2.editConf.vlan.ip.pim.propagationDelay

       Time in centi-second."
   ::= {er1645v2Lan2FGVlanEntry 53347328}

er1645v2Lan2FGVlanIpPimOverrideInterval OBJECT-TYPE
   SYNTAX      TimeTicks
   MAX-ACCESS  read-write
   STATUS      current
   DESCRIPTION
      "Path: ethernet2.editConf.vlan.ip.pim.overrideInterval

       Time in centi-second."
   ::= {er1645v2Lan2FGVlanEntry 53347584}

er1645v2Lan2FGVlanIpPimBsrBorder OBJECT-TYPE
   SYNTAX      INTEGER
               {
               disabled (0),
               enabled (1)
               }
   MAX-ACCESS  read-write
   STATUS      current
   DESCRIPTION
      "Path: ethernet2.editConf.vlan.ip.pim.bsrBorder

       Possibilities:
               disabled   (0)
               enabled   (1)"
   ::= {er1645v2Lan2FGVlanEntry 53347840}

er1645v2Lan2FGVlanIpPimTtlThreshold OBJECT-TYPE
   SYNTAX      Integer32
   MAX-ACCESS  read-write
   STATUS      current
   DESCRIPTION
      "Path: ethernet2.editConf.vlan.ip.pim.ttlThreshold"
   ::= {er1645v2Lan2FGVlanEntry 53348096}

er1645v2Lan2FGVlanIpIMNetworkUnreachable OBJECT-TYPE
   SYNTAX      INTEGER
               {
               disabled (0),
               enabled (1)
               }
   MAX-ACCESS  read-write
   STATUS      current
   DESCRIPTION
      "Path: ethernet2.editConf.vlan.ip.icmpMessages.networkUnreachable

       Possibilities:
               disabled   (0)
               enabled   (1)"
   ::= {er1645v2Lan2FGVlanEntry 53412096}

er1645v2Lan2FGVlanIpIMHostUnreachable OBJECT-TYPE
   SYNTAX      INTEGER
               {
               disabled (0),
               enabled (1)
               }
   MAX-ACCESS  read-write
   STATUS      current
   DESCRIPTION
      "Path: ethernet2.editConf.vlan.ip.icmpMessages.hostUnreachable

       Possibilities:
               disabled   (0)
               enabled   (1)"
   ::= {er1645v2Lan2FGVlanEntry 53412352}

er1645v2Lan2FGVlanIpIMProtocolUnreachable OBJECT-TYPE
   SYNTAX      INTEGER
               {
               disabled (0),
               enabled (1)
               }
   MAX-ACCESS  read-write
   STATUS      current
   DESCRIPTION
      "Path: ethernet2.editConf.vlan.ip.icmpMessages.protocolUnreachable

       Possibilities:
               disabled   (0)
               enabled   (1)"
   ::= {er1645v2Lan2FGVlanEntry 53412608}

er1645v2Lan2FGVlanIpIMPortUnreachable OBJECT-TYPE
   SYNTAX      INTEGER
               {
               disabled (0),
               enabled (1)
               }
   MAX-ACCESS  read-write
   STATUS      current
   DESCRIPTION
      "Path: ethernet2.editConf.vlan.ip.icmpMessages.portUnreachable

       Possibilities:
               disabled   (0)
               enabled   (1)"
   ::= {er1645v2Lan2FGVlanEntry 53412864}

er1645v2Lan2FGVlanIpIMMtuExceeded OBJECT-TYPE
   SYNTAX      INTEGER
               {
               disabled (0),
               enabled (1)
               }
   MAX-ACCESS  read-write
   STATUS      current
   DESCRIPTION
      "Path: ethernet2.editConf.vlan.ip.icmpMessages.mtuExceeded

       Possibilities:
               disabled   (0)
               enabled   (1)"
   ::= {er1645v2Lan2FGVlanEntry 53413120}

er1645v2Lan2FGVlanIpIMAdminProhibited OBJECT-TYPE
   SYNTAX      INTEGER
               {
               disabled (0),
               enabled (1)
               }
   MAX-ACCESS  read-write
   STATUS      current
   DESCRIPTION
      "Path: ethernet2.editConf.vlan.ip.icmpMessages.adminProhibited

       Possibilities:
               disabled   (0)
               enabled   (1)"
   ::= {er1645v2Lan2FGVlanEntry 53413376}

er1645v2Lan2FGVlanIpIMTtlExceeded OBJECT-TYPE
   SYNTAX      INTEGER
               {
               disabled (0),
               enabled (1)
               }
   MAX-ACCESS  read-write
   STATUS      current
   DESCRIPTION
      "Path: ethernet2.editConf.vlan.ip.icmpMessages.ttlExceeded

       Possibilities:
               disabled   (0)
               enabled   (1)"
   ::= {er1645v2Lan2FGVlanEntry 53413632}

er1645v2Lan2FGVlanIpIMRedirect OBJECT-TYPE
   SYNTAX      INTEGER
               {
               disabled (0),
               enabled (1)
               }
   MAX-ACCESS  read-write
   STATUS      current
   DESCRIPTION
      "Path: ethernet2.editConf.vlan.ip.icmpMessages.redirect

       Possibilities:
               disabled   (0)
               enabled   (1)"
   ::= {er1645v2Lan2FGVlanEntry 53413888}

er1645v2Lan2FGVlanIpV6VrfRouter OBJECT-TYPE
   SYNTAX      DisplayString
   MAX-ACCESS  read-write
   STATUS      current
   DESCRIPTION
      "Path: ethernet2.editConf.vlan.ipV6.vrfRouter"
   ::= {er1645v2Lan2FGVlanEntry 704708608}

er1645v2Lan2FGVlanIpV6AddrAutoConfigNrDupAddrDetects OBJECT-TYPE
   SYNTAX      Integer32
   MAX-ACCESS  read-write
   STATUS      current
   DESCRIPTION
      "Path: ethernet2.editConf.vlan.ipV6.addrAutoConfig.nrDupAddrDetects"
   ::= {er1645v2Lan2FGVlanEntry 704905472}

er1645v2Lan2FGVlanIpV6AddrAutoConfigAcceptRa OBJECT-TYPE
   SYNTAX      INTEGER
               {
               disabled (0),
               enabled (1)
               }
   MAX-ACCESS  read-write
   STATUS      current
   DESCRIPTION
      "Path: ethernet2.editConf.vlan.ipV6.addrAutoConfig.acceptRa

       Possibilities:
               disabled   (0)
               enabled   (1)"
   ::= {er1645v2Lan2FGVlanEntry 704905728}

er1645v2Lan2FGVlanIpV6AddrAutoConfigAcceptRaRdnss OBJECT-TYPE
   SYNTAX      INTEGER
               {
               disabled (0),
               enabled (1)
               }
   MAX-ACCESS  read-write
   STATUS      current
   DESCRIPTION
      "Path: ethernet2.editConf.vlan.ipV6.addrAutoConfig.acceptRaRdnss

       Possibilities:
               disabled   (0)
               enabled   (1)"
   ::= {er1645v2Lan2FGVlanEntry 704905984}

er1645v2Lan2FGVlanIpV6AddrAutoConfigAcceptRaDnssl OBJECT-TYPE
   SYNTAX      INTEGER
               {
               disabled (0),
               enabled (1)
               }
   MAX-ACCESS  read-write
   STATUS      current
   DESCRIPTION
      "Path: ethernet2.editConf.vlan.ipV6.addrAutoConfig.acceptRaDnssl

       Possibilities:
               disabled   (0)
               enabled   (1)"
   ::= {er1645v2Lan2FGVlanEntry 704906240}

er1645v2Lan2FGVlanIpV6DefaultRoute OBJECT-TYPE
   SYNTAX      INTEGER
               {
               disabled (0),
               enabled (1)
               }
   MAX-ACCESS  read-write
   STATUS      current
   DESCRIPTION
      "Path: ethernet2.editConf.vlan.ipV6.defaultRoute

       Possibilities:
               disabled   (0)
               enabled   (1)"
   ::= {er1645v2Lan2FGVlanEntry 704970752}

er1645v2Lan2FGVlanIpV6RaSend OBJECT-TYPE
   SYNTAX      INTEGER
               {
               disabled (0),
               enabled (1)
               }
   MAX-ACCESS  read-write
   STATUS      current
   DESCRIPTION
      "Path: ethernet2.editConf.vlan.ipV6.ra.send

       Possibilities:
               disabled   (0)
               enabled   (1)"
   ::= {er1645v2Lan2FGVlanEntry 705036544}

er1645v2Lan2FGVlanIpV6RaMinInterval OBJECT-TYPE
   SYNTAX      TimeTicks
   MAX-ACCESS  read-write
   STATUS      current
   DESCRIPTION
      "Path: ethernet2.editConf.vlan.ipV6.ra.minInterval

       Time in centi-second."
   ::= {er1645v2Lan2FGVlanEntry 705036800}

er1645v2Lan2FGVlanIpV6RaMaxInterval OBJECT-TYPE
   SYNTAX      TimeTicks
   MAX-ACCESS  read-write
   STATUS      current
   DESCRIPTION
      "Path: ethernet2.editConf.vlan.ipV6.ra.maxInterval

       Time in centi-second."
   ::= {er1645v2Lan2FGVlanEntry 705037056}

er1645v2Lan2FGVlanIpV6RaManagedFlag OBJECT-TYPE
   SYNTAX      INTEGER
               {
               disabled (0),
               enabled (1)
               }
   MAX-ACCESS  read-write
   STATUS      current
   DESCRIPTION
      "Path: ethernet2.editConf.vlan.ipV6.ra.managedFlag

       Possibilities:
               disabled   (0)
               enabled   (1)"
   ::= {er1645v2Lan2FGVlanEntry 705037312}

er1645v2Lan2FGVlanIpV6RaOtherConfFlag OBJECT-TYPE
   SYNTAX      INTEGER
               {
               disabled (0),
               enabled (1)
               }
   MAX-ACCESS  read-write
   STATUS      current
   DESCRIPTION
      "Path: ethernet2.editConf.vlan.ipV6.ra.otherConfFlag

       Possibilities:
               disabled   (0)
               enabled   (1)"
   ::= {er1645v2Lan2FGVlanEntry 705037568}

er1645v2Lan2FGVlanIpV6RaLinkMtu OBJECT-TYPE
   SYNTAX      Integer32
   MAX-ACCESS  read-write
   STATUS      current
   DESCRIPTION
      "Path: ethernet2.editConf.vlan.ipV6.ra.linkMtu"
   ::= {er1645v2Lan2FGVlanEntry 705037824}

er1645v2Lan2FGVlanIpV6RaReachableTime OBJECT-TYPE
   SYNTAX      TimeTicks
   MAX-ACCESS  read-write
   STATUS      current
   DESCRIPTION
      "Path: ethernet2.editConf.vlan.ipV6.ra.reachableTime

       Time in centi-second."
   ::= {er1645v2Lan2FGVlanEntry 705038080}

er1645v2Lan2FGVlanIpV6RaRetransmitTime OBJECT-TYPE
   SYNTAX      TimeTicks
   MAX-ACCESS  read-write
   STATUS      current
   DESCRIPTION
      "Path: ethernet2.editConf.vlan.ipV6.ra.retransmitTime

       Time in centi-second."
   ::= {er1645v2Lan2FGVlanEntry 705038336}

er1645v2Lan2FGVlanIpV6RaHopLimit OBJECT-TYPE
   SYNTAX      Integer32
   MAX-ACCESS  read-write
   STATUS      current
   DESCRIPTION
      "Path: ethernet2.editConf.vlan.ipV6.ra.hopLimit"
   ::= {er1645v2Lan2FGVlanEntry 705038592}

er1645v2Lan2FGVlanIpV6RaDefaultLifeTime OBJECT-TYPE
   SYNTAX      TimeTicks
   MAX-ACCESS  read-write
   STATUS      current
   DESCRIPTION
      "Path: ethernet2.editConf.vlan.ipV6.ra.defaultLifeTime

       Time in centi-second."
   ::= {er1645v2Lan2FGVlanEntry 705038848}

er1645v2Lan2FGVlanIpV6RaDnsOptionsRdnssLifeTime OBJECT-TYPE
   SYNTAX      TimeTicks
   MAX-ACCESS  read-write
   STATUS      current
   DESCRIPTION
      "Path: ethernet2.editConf.vlan.ipV6.ra.dnsOptions.rdnss.lifeTime

       Time in centi-second."
   ::= {er1645v2Lan2FGVlanEntry 705039140}

er1645v2Lan2FGVlanIpV6RaDnsOptionsRdnssImportServers OBJECT-TYPE
   SYNTAX      INTEGER
               {
               disabled (0),
               enabled (1)
               }
   MAX-ACCESS  read-write
   STATUS      current
   DESCRIPTION
      "Path: ethernet2.editConf.vlan.ipV6.ra.dnsOptions.rdnss.importServers

       Possibilities:
               disabled   (0)
               enabled   (1)"
   ::= {er1645v2Lan2FGVlanEntry 705039148}

er1645v2Lan2FGVlanIpV6RaDnsOptionsDnsslLifeTime OBJECT-TYPE
   SYNTAX      TimeTicks
   MAX-ACCESS  read-write
   STATUS      current
   DESCRIPTION
      "Path: ethernet2.editConf.vlan.ipV6.ra.dnsOptions.dnssl.lifeTime

       Time in centi-second."
   ::= {er1645v2Lan2FGVlanEntry 705039172}

er1645v2Lan2FGVlanIpV6RaDnsOptionsDnsslImportDomains OBJECT-TYPE
   SYNTAX      INTEGER
               {
               disabled (0),
               enabled (1)
               }
   MAX-ACCESS  read-write
   STATUS      current
   DESCRIPTION
      "Path: ethernet2.editConf.vlan.ipV6.ra.dnsOptions.dnssl.importDomains

       Possibilities:
               disabled   (0)
               enabled   (1)"
   ::= {er1645v2Lan2FGVlanEntry 705039180}

er1645v2Lan2FGVlanIpV6RsSend OBJECT-TYPE
   SYNTAX      INTEGER
               {
               disabled (0),
               enabled (1)
               }
   MAX-ACCESS  read-write
   STATUS      current
   DESCRIPTION
      "Path: ethernet2.editConf.vlan.ipV6.rs.send

       Possibilities:
               disabled   (0)
               enabled   (1)"
   ::= {er1645v2Lan2FGVlanEntry 705954048}

er1645v2Lan2FGVlanIpV6RsMaxRandomDelay OBJECT-TYPE
   SYNTAX      TimeTicks
   MAX-ACCESS  read-write
   STATUS      current
   DESCRIPTION
      "Path: ethernet2.editConf.vlan.ipV6.rs.maxRandomDelay

       Time in centi-second."
   ::= {er1645v2Lan2FGVlanEntry 705954304}

er1645v2Lan2FGVlanIpV6RsInterval OBJECT-TYPE
   SYNTAX      TimeTicks
   MAX-ACCESS  read-write
   STATUS      current
   DESCRIPTION
      "Path: ethernet2.editConf.vlan.ipV6.rs.interval

       Time in centi-second."
   ::= {er1645v2Lan2FGVlanEntry 705954560}

er1645v2Lan2FGVlanIpV6RsMaxSolicitations OBJECT-TYPE
   SYNTAX      Integer32
   MAX-ACCESS  read-write
   STATUS      current
   DESCRIPTION
      "Path: ethernet2.editConf.vlan.ipV6.rs.maxSolicitations"
   ::= {er1645v2Lan2FGVlanEntry 705954816}

er1645v2Lan2FGVlanIpV6TrafficPolicyInbound OBJECT-TYPE
   SYNTAX      DisplayString
   MAX-ACCESS  read-write
   STATUS      current
   DESCRIPTION
      "Path: ethernet2.editConf.vlan.ipV6.trafficPolicy.inbound"
   ::= {er1645v2Lan2FGVlanEntry 705364224}

er1645v2Lan2FGVlanIpV6TrafficPolicyOutbound OBJECT-TYPE
   SYNTAX      DisplayString
   MAX-ACCESS  read-write
   STATUS      current
   DESCRIPTION
      "Path: ethernet2.editConf.vlan.ipV6.trafficPolicy.outbound"
   ::= {er1645v2Lan2FGVlanEntry 705364480}

er1645v2Lan2FGVlanIpV6FirewallZone OBJECT-TYPE
   SYNTAX      DisplayString
   MAX-ACCESS  read-write
   STATUS      current
   DESCRIPTION
      "Path: ethernet2.editConf.vlan.ipV6.firewall.zone"
   ::= {er1645v2Lan2FGVlanEntry 705429760}

er1645v2Lan2FGVlanIpV6DhcpClientAddrAC OBJECT-TYPE
   SYNTAX      INTEGER
               {
               disabled (0),
               enabled (1)
               }
   MAX-ACCESS  read-write
   STATUS      current
   DESCRIPTION
      "Path: ethernet2.editConf.vlan.ipV6.dhcp.client.addrAutoConfig

       Possibilities:
               disabled   (0)
               enabled   (1)"
   ::= {er1645v2Lan2FGVlanEntry 705307648}

er1645v2Lan2FGVlanIpV6DhcpClientPrDelMode OBJECT-TYPE
   SYNTAX      INTEGER
               {
               disabled (0),
               enabled (1)
               }
   MAX-ACCESS  read-write
   STATUS      current
   DESCRIPTION
      "Path: ethernet2.editConf.vlan.ipV6.dhcp.client.pd.mode

       Possibilities:
               disabled   (0)
               enabled   (1)"
   ::= {er1645v2Lan2FGVlanEntry 705308676}

er1645v2Lan2FGVlanIpV6DhcpClientPrDelPool OBJECT-TYPE
   SYNTAX      DisplayString
   MAX-ACCESS  read-write
   STATUS      current
   DESCRIPTION
      "Path: ethernet2.editConf.vlan.ipV6.dhcp.client.pd.pool"
   ::= {er1645v2Lan2FGVlanEntry 705308680}

er1645v2Lan2FGVlanIpV6DhcpClientPrDelPdExclOpt OBJECT-TYPE
   SYNTAX      INTEGER
               {
               disabled (0),
               enabled (1)
               }
   MAX-ACCESS  read-write
   STATUS      current
   DESCRIPTION
      "Path: ethernet2.editConf.vlan.ipV6.dhcp.client.pd.pdExclOpt

       Possibilities:
               disabled   (0)
               enabled   (1)"
   ::= {er1645v2Lan2FGVlanEntry 705308684}

er1645v2Lan2FGVlanIpV6DhcpClientDnsServerPref OBJECT-TYPE
   SYNTAX      Integer32
   MAX-ACCESS  read-write
   STATUS      current
   DESCRIPTION
      "Path: ethernet2.editConf.vlan.ipV6.dhcp.client.dns.serverPref"
   ::= {er1645v2Lan2FGVlanEntry 705310724}

er1645v2Lan2FGVlanIpV6DhcpClientRapidCommit OBJECT-TYPE
   SYNTAX      INTEGER
               {
               disabled (0),
               enabled (1)
               }
   MAX-ACCESS  read-write
   STATUS      current
   DESCRIPTION
      "Path: ethernet2.editConf.vlan.ipV6.dhcp.client.rapidCommit

       Possibilities:
               disabled   (0)
               enabled   (1)"
   ::= {er1645v2Lan2FGVlanEntry 705309696}

er1645v2Lan2FGVlanIpV6DhcpClientTimersSolTimeOut OBJECT-TYPE
   SYNTAX      TimeTicks
   MAX-ACCESS  read-write
   STATUS      current
   DESCRIPTION
      "Path: ethernet2.editConf.vlan.ipV6.dhcp.client.timers.solTimeOut

       Time in centi-second."
   ::= {er1645v2Lan2FGVlanEntry 705311748}

er1645v2Lan2FGVlanIpV6DhcpClientTimersSolMaxRt OBJECT-TYPE
   SYNTAX      TimeTicks
   MAX-ACCESS  read-write
   STATUS      current
   DESCRIPTION
      "Path: ethernet2.editConf.vlan.ipV6.dhcp.client.timers.solMaxRt

       Time in centi-second."
   ::= {er1645v2Lan2FGVlanEntry 705311752}

er1645v2Lan2FGVlanIpV6DhcpClientTimersInfoRefresh OBJECT-TYPE
   SYNTAX      TimeTicks
   MAX-ACCESS  read-write
   STATUS      current
   DESCRIPTION
      "Path: ethernet2.editConf.vlan.ipV6.dhcp.client.timers.infoRefresh

       Time in centi-second."
   ::= {er1645v2Lan2FGVlanEntry 705311756}

er1645v2Lan2FGVlanIpV6DhcpServerMode OBJECT-TYPE
   SYNTAX      INTEGER
               {
               disabled (0),
               enabled (1)
               }
   MAX-ACCESS  read-write
   STATUS      current
   DESCRIPTION
      "Path: ethernet2.editConf.vlan.ipV6.dhcp.server.mode

       Possibilities:
               disabled   (0)
               enabled   (1)"
   ::= {er1645v2Lan2FGVlanEntry 705315840}

er1645v2Lan2FGVlanIpV6DhcpServerPreference OBJECT-TYPE
   SYNTAX      Integer32
   MAX-ACCESS  read-write
   STATUS      current
   DESCRIPTION
      "Path: ethernet2.editConf.vlan.ipV6.dhcp.server.preference"
   ::= {er1645v2Lan2FGVlanEntry 705316864}

er1645v2Lan2FGVlanIpV6DhcpServerPool OBJECT-TYPE
   SYNTAX      DisplayString
   MAX-ACCESS  read-write
   STATUS      current
   DESCRIPTION
      "Path: ethernet2.editConf.vlan.ipV6.dhcp.server.pool"
   ::= {er1645v2Lan2FGVlanEntry 705317888}

er1645v2Lan2FGVlanIpV6DhcpServerRapidCommit OBJECT-TYPE
   SYNTAX      INTEGER
               {
               disabled (0),
               enabled (1)
               }
   MAX-ACCESS  read-write
   STATUS      current
   DESCRIPTION
      "Path: ethernet2.editConf.vlan.ipV6.dhcp.server.rapidCommit

       Possibilities:
               disabled   (0)
               enabled   (1)"
   ::= {er1645v2Lan2FGVlanEntry 705318912}

er1645v2Lan2FGVlanIpV6DhcpServerTimersInfoRefresh OBJECT-TYPE
   SYNTAX      TimeTicks
   MAX-ACCESS  read-write
   STATUS      current
   DESCRIPTION
      "Path: ethernet2.editConf.vlan.ipV6.dhcp.server.timers.infoRefresh

       Time in centi-second."
   ::= {er1645v2Lan2FGVlanEntry 705319940}

er1645v2Lan2FGVlanIpV6DhcpRelayMode OBJECT-TYPE
   SYNTAX      INTEGER
               {
               disabled (0),
               enabled (1)
               }
   MAX-ACCESS  read-write
   STATUS      current
   DESCRIPTION
      "Path: ethernet2.editConf.vlan.ipV6.dhcp.relay.mode

       Possibilities:
               disabled   (0)
               enabled   (1)"
   ::= {er1645v2Lan2FGVlanEntry 705323040}

er1645v2Lan2FGVlanIpV6SendRedirect OBJECT-TYPE
   SYNTAX      INTEGER
               {
               disabled (0),
               enabled (1)
               }
   MAX-ACCESS  read-write
   STATUS      current
   DESCRIPTION
      "Path: ethernet2.editConf.vlan.ipV6.sendRedirect

       Possibilities:
               disabled   (0)
               enabled   (1)"
   ::= {er1645v2Lan2FGVlanEntry 705101824}

er1645v2Lan2FGVlanIpV6LinkMtu OBJECT-TYPE
   SYNTAX      Integer32
   MAX-ACCESS  read-write
   STATUS      current
   DESCRIPTION
      "Path: ethernet2.editConf.vlan.ipV6.linkMtu"
   ::= {er1645v2Lan2FGVlanEntry 705167360}

er1645v2Lan2FGVlanIpV6InterfaceId OBJECT-TYPE
   SYNTAX      OCTET STRING
   MAX-ACCESS  read-write
   STATUS      current
   DESCRIPTION
      "Path: ethernet2.editConf.vlan.ipV6.interfaceId"
   ::= {er1645v2Lan2FGVlanEntry 705232896}

er1645v2Lan2FGVlanIpV6MF OBJECT-TYPE
   SYNTAX      Integer32
   MAX-ACCESS  read-write
   STATUS      current
   DESCRIPTION
      "Path: ethernet2.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2FGVlanEntry 705757184}

er1645v2Lan2FGVlanIpV6IcmpMessagesNoRoute OBJECT-TYPE
   SYNTAX      INTEGER
               {
               disabled (0),
               enabled (1)
               }
   MAX-ACCESS  read-write
   STATUS      current
   DESCRIPTION
      "Path: ethernet2.editConf.vlan.ipV6.icmpMessages.noRoute

       Possibilities:
               disabled   (0)
               enabled   (1)"
   ::= {er1645v2Lan2FGVlanEntry 705822976}

er1645v2Lan2FGVlanIpV6IcmpMessagesBeyondScope OBJECT-TYPE
   SYNTAX      INTEGER
               {
               disabled (0),
               enabled (1)
               }
   MAX-ACCESS  read-write
   STATUS      current
   DESCRIPTION
      "Path: ethernet2.editConf.vlan.ipV6.icmpMessages.beyondScope

       Possibilities:
               disabled   (0)
               enabled   (1)"
   ::= {er1645v2Lan2FGVlanEntry 705823488}

er1645v2Lan2FGVlanIpV6IcmpMessagesAddressUnreachable OBJECT-TYPE
   SYNTAX      INTEGER
               {
               disabled (0),
               enabled (1)
               }
   MAX-ACCESS  read-write
   STATUS      current
   DESCRIPTION
      "Path: ethernet2.editConf.vlan.ipV6.icmpMessages.addressUnreachable

       Possibilities:
               disabled   (0)
               enabled   (1)"
   ::= {er1645v2Lan2FGVlanEntry 705823744}

er1645v2Lan2FGVlanIpV6IcmpMessagesPortUnreachable OBJECT-TYPE
   SYNTAX      INTEGER
               {
               disabled (0),
               enabled (1)
               }
   MAX-ACCESS  read-write
   STATUS      current
   DESCRIPTION
      "Path: ethernet2.editConf.vlan.ipV6.icmpMessages.portUnreachable

       Possibilities:
               disabled   (0)
               enabled   (1)"
   ::= {er1645v2Lan2FGVlanEntry 705824000}

er1645v2Lan2FGVlanIpV6IcmpMessagesPacketTooBig OBJECT-TYPE
   SYNTAX      INTEGER
               {
               disabled (0),
               enabled (1)
               }
   MAX-ACCESS  read-write
   STATUS      current
   DESCRIPTION
      "Path: ethernet2.editConf.vlan.ipV6.icmpMessages.packetTooBig

       Possibilities:
               disabled   (0)
               enabled   (1)"
   ::= {er1645v2Lan2FGVlanEntry 705825280}

er1645v2Lan2FGVlanIpV6IcmpMessagesHopLimitExceeded OBJECT-TYPE
   SYNTAX      INTEGER
               {
               disabled (0),
               enabled (1)
               }
   MAX-ACCESS  read-write
   STATUS      current
   DESCRIPTION
      "Path: ethernet2.editConf.vlan.ipV6.icmpMessages.hopLimitExceeded

       Possibilities:
               disabled   (0)
               enabled   (1)"
   ::= {er1645v2Lan2FGVlanEntry 705827840}

er1645v2Lan2FGVlanIpV6IcmpMessagesFragTimeExceeded OBJECT-TYPE
   SYNTAX      INTEGER
               {
               disabled (0),
               enabled (1)
               }
   MAX-ACCESS  read-write
   STATUS      current
   DESCRIPTION
      "Path: ethernet2.editConf.vlan.ipV6.icmpMessages.fragTimeExceeded

       Possibilities:
               disabled   (0)
               enabled   (1)"
   ::= {er1645v2Lan2FGVlanEntry 705828096}

er1645v2Lan2FGVlanIpV6IcmpMessagesHeaderFieldErr OBJECT-TYPE
   SYNTAX      INTEGER
               {
               disabled (0),
               enabled (1)
               }
   MAX-ACCESS  read-write
   STATUS      current
   DESCRIPTION
      "Path: ethernet2.editConf.vlan.ipV6.icmpMessages.headerFieldErr

       Possibilities:
               disabled   (0)
               enabled   (1)"
   ::= {er1645v2Lan2FGVlanEntry 705830400}

er1645v2Lan2FGVlanIpV6IcmpMessagesOptionUnrecognized OBJECT-TYPE
   SYNTAX      INTEGER
               {
               disabled (0),
               enabled (1)
               }
   MAX-ACCESS  read-write
   STATUS      current
   DESCRIPTION
      "Path: ethernet2.editConf.vlan.ipV6.icmpMessages.optionUnrecognized

       Possibilities:
               disabled   (0)
               enabled   (1)"
   ::= {er1645v2Lan2FGVlanEntry 705830912}

er1645v2Lan2FGVlanIpV6IcmpMessagesRedirect OBJECT-TYPE
   SYNTAX      INTEGER
               {
               disabled (0),
               enabled (1)
               }
   MAX-ACCESS  read-write
   STATUS      current
   DESCRIPTION
      "Path: ethernet2.editConf.vlan.ipV6.icmpMessages.redirect

       Possibilities:
               disabled   (0)
               enabled   (1)"
   ::= {er1645v2Lan2FGVlanEntry 705832960}

er1645v2Lan2FGVlanBridgingAccList OBJECT-TYPE
   SYNTAX      DisplayString
   MAX-ACCESS  read-write
   STATUS      current
   DESCRIPTION
      "Path: ethernet2.editConf.vlan.bridging.accessList"
   ::= {er1645v2Lan2FGVlanEntry 453246976}

er1645v2Lan2FGVlanBridgingInACL OBJECT-TYPE
   SYNTAX      DisplayString
   MAX-ACCESS  read-write
   STATUS      current
   DESCRIPTION
      "Path: ethernet2.editConf.vlan.bridging.inAccessList"
   ::= {er1645v2Lan2FGVlanEntry 456916992}

er1645v2Lan2FGVlanBridgingTp OBJECT-TYPE
   SYNTAX      DisplayString
   MAX-ACCESS  read-write
   STATUS      current
   DESCRIPTION
      "Path: ethernet2.editConf.vlan.bridging.trafficPolicy"
   ::= {er1645v2Lan2FGVlanEntry 454295552}

er1645v2Lan2FGVlanBridgingBrGrp OBJECT-TYPE
   SYNTAX      DisplayString
   MAX-ACCESS  read-write
   STATUS      current
   DESCRIPTION
      "Path: ethernet2.editConf.vlan.bridging.bridgeGroup"
   ::= {er1645v2Lan2FGVlanEntry 454819840}

er1645v2Lan2FGVlanBridgingLimBC OBJECT-TYPE
   SYNTAX      INTEGER
               {
               disabled (0),
               enabled (1)
               }
   MAX-ACCESS  read-write
   STATUS      current
   DESCRIPTION
      "Path: ethernet2.editConf.vlan.bridging.limitBroadcasts

       Possibilities:
               disabled   (0)
               enabled   (1)"
   ::= {er1645v2Lan2FGVlanEntry 455081984}

er1645v2Lan2FGVlanBridgingPrivateMode OBJECT-TYPE
   SYNTAX      INTEGER
               {
               disabled (0),
               enabled (1)
               }
   MAX-ACCESS  read-write
   STATUS      current
   DESCRIPTION
      "Path: ethernet2.editConf.vlan.bridging.privateMode

       Possibilities:
               disabled   (0)
               enabled   (1)"
   ::= {er1645v2Lan2FGVlanEntry 459538432}

er1645v2Lan2FGVlanBridgingLearning OBJECT-TYPE
   SYNTAX      INTEGER
               {
               disabled (0),
               enabled (1)
               }
   MAX-ACCESS  read-write
   STATUS      current
   DESCRIPTION
      "Path: ethernet2.editConf.vlan.bridging.learning

       Possibilities:
               disabled   (0)
               enabled   (1)"
   ::= {er1645v2Lan2FGVlanEntry 456130560}

er1645v2Lan2FGVlanBridgingMaxCacheSize OBJECT-TYPE
   SYNTAX      INTEGER
               {
               unlimited (0)
               }
   MAX-ACCESS  read-write
   STATUS      current
   DESCRIPTION
      "Path: ethernet2.editConf.vlan.bridging.maxCacheSize

       Possibilities:
               unlimited   (0)"
   ::= {er1645v2Lan2FGVlanEntry 456392704}

er1645v2Lan2FGVlanBridgingRelearnDropOnRelearn OBJECT-TYPE
   SYNTAX      INTEGER
               {
               disabled (0),
               enabled (1)
               }
   MAX-ACCESS  read-write
   STATUS      current
   DESCRIPTION
      "Path: ethernet2.editConf.vlan.bridging.relearn.dropOnRelearn

       Possibilities:
               disabled   (0)
               enabled   (1)"
   ::= {er1645v2Lan2FGVlanEntry 456655872}

er1645v2Lan2FGVlanBridgingRelearnShutdownThreshold OBJECT-TYPE
   SYNTAX      Integer32
   MAX-ACCESS  read-write
   STATUS      current
   DESCRIPTION
      "Path: ethernet2.editConf.vlan.bridging.relearn.shutdownThreshold"
   ::= {er1645v2Lan2FGVlanEntry 456656896}

er1645v2Lan2FGVlanBridgingRelearnShutdownTime OBJECT-TYPE
   SYNTAX      TimeTicks
   MAX-ACCESS  read-write
   STATUS      current
   DESCRIPTION
      "Path: ethernet2.editConf.vlan.bridging.relearn.shutdownTime

       Time in centi-second."
   ::= {er1645v2Lan2FGVlanEntry 456657920}

er1645v2Lan2FGVlanBridgingRelearnLoopDetection OBJECT-TYPE
   SYNTAX      INTEGER
               {
               disabled (0),
               passive (1),
               active (2)
               }
   MAX-ACCESS  read-write
   STATUS      current
   DESCRIPTION
      "Path: ethernet2.editConf.vlan.bridging.relearn.loopDetection

       Possibilities:
               disabled   (0)
               passive   (1)
               active   (2)"
   ::= {er1645v2Lan2FGVlanEntry 456658944}

er1645v2Lan2FGVlanBridgingRelearnLoopDetectionInterval OBJECT-TYPE
   SYNTAX      TimeTicks
   MAX-ACCESS  read-write
   STATUS      current
   DESCRIPTION
      "Path: ethernet2.editConf.vlan.bridging.relearn.loopDetectionInterval

       Time in centi-second."
   ::= {er1645v2Lan2FGVlanEntry 456659968}

er1645v2Lan2FGVlanBridgingVlanMemberShip OBJECT-TYPE
   SYNTAX      INTEGER
               {
               all (0),
               none (1),
               grouped (2)
               }
   MAX-ACCESS  read-write
   STATUS      current
   DESCRIPTION
      "Path: ethernet2.editConf.vlan.bridging.vlanMemberShip

       Possibilities:
               all   (0)
               none   (1)
               grouped   (2)"
   ::= {er1645v2Lan2FGVlanEntry 457965568}

er1645v2Lan2FGVlanBridgingVlTUntaggedAction OBJECT-TYPE
   SYNTAX      INTEGER
               {
               discard (0),
               accept (1),
               tag (2)
               }
   MAX-ACCESS  read-write
   STATUS      current
   DESCRIPTION
      "Path: ethernet2.editConf.vlan.bridging.vlanTagging.untagged.action

       Possibilities:
               discard   (0)
               accept   (1)
               tag   (2)"
   ::= {er1645v2Lan2FGVlanEntry 459055104}

er1645v2Lan2FGVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.untagged.tagInfo.tpid

       Possibilities:
               dot1Q   (33024)
               dot1ad   (34984)
               0x9100   (37120)
               0x9200   (37376)
               0x9300   (37632)"
   ::= {er1645v2Lan2FGVlanEntry 459059712}

er1645v2Lan2FGVlanBridgingVlTUntaggedTagInfoVid OBJECT-TYPE
   SYNTAX      Integer32
   MAX-ACCESS  read-write
   STATUS      current
   DESCRIPTION
      "Path: ethernet2.editConf.vlan.bridging.vlanTagging.untagged.tagInfo.vid"
   ::= {er1645v2Lan2FGVlanEntry 459060224}

er1645v2Lan2FGVlanBridgingVlTUnknownVlansAction OBJECT-TYPE
   SYNTAX      INTEGER
               {
               discard (0),
               accept (1),
               tag (2)
               }
   MAX-ACCESS  read-write
   STATUS      current
   DESCRIPTION
      "Path: ethernet2.editConf.vlan.bridging.vlanTagging.unknownVlans.action

       Possibilities:
               discard   (0)
               accept   (1)
               tag   (2)"
   ::= {er1645v2Lan2FGVlanEntry 459120640}

er1645v2Lan2FGVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.unknownVlans.tagInfo.tpid

       Possibilities:
               dot1Q   (33024)
               dot1ad   (34984)
               0x9100   (37120)
               0x9200   (37376)
               0x9300   (37632)"
   ::= {er1645v2Lan2FGVlanEntry 459125248}

er1645v2Lan2FGVlanBridgingVlTUnknownVlansTagInfoVid OBJECT-TYPE
   SYNTAX      Integer32
   MAX-ACCESS  read-write
   STATUS      current
   DESCRIPTION
      "Path: ethernet2.editConf.vlan.bridging.vlanTagging.unknownVlans.tagInfo.vid"
   ::= {er1645v2Lan2FGVlanEntry 459125760}

er1645v2Lan2FGVlanBridgingDot1adType OBJECT-TYPE
   SYNTAX      INTEGER
               {
               slOPTg (0),
               cPort (4),
               sPort (1),
               nni (2)
               }
   MAX-ACCESS  read-write
   STATUS      current
   DESCRIPTION
      "Path: ethernet2.editConf.vlan.bridging.dot1ad.type

       Possibilities:
               <OPT>   (0)
               cPort   (4)
               sPort   (1)
               nni   (2)"
   ::= {er1645v2Lan2FGVlanEntry 460850176}

er1645v2Lan2FGVlanBridgingPriority OBJECT-TYPE
   SYNTAX      Integer32
   MAX-ACCESS  read-write
   STATUS      current
   DESCRIPTION
      "Path: ethernet2.editConf.vlan.bridging.priority"
   ::= {er1645v2Lan2FGVlanEntry 453509120}

er1645v2Lan2FGVlanBridgingPathCost OBJECT-TYPE
   SYNTAX      Integer32
   MAX-ACCESS  read-write
   STATUS      current
   DESCRIPTION
      "Path: ethernet2.editConf.vlan.bridging.pathCost"
   ::= {er1645v2Lan2FGVlanEntry 453771264}

er1645v2Lan2FGVlanBridgingInternalPathCost OBJECT-TYPE
   SYNTAX      Integer32
   MAX-ACCESS  read-write
   STATUS      current
   DESCRIPTION
      "Path: ethernet2.editConf.vlan.bridging.internalPathCost"
   ::= {er1645v2Lan2FGVlanEntry 457703424}

er1645v2Lan2FGVlanBridgingTCD OBJECT-TYPE
   SYNTAX      INTEGER
               {
               disabled (0),
               enabled (1)
               }
   MAX-ACCESS  read-write
   STATUS      current
   DESCRIPTION
      "Path: ethernet2.editConf.vlan.bridging.topologyChangeDetection

       Possibilities:
               disabled   (0)
               enabled   (1)"
   ::= {er1645v2Lan2FGVlanEntry 454033408}

er1645v2Lan2FGVlanBridgingRestrictedRole OBJECT-TYPE
   SYNTAX      INTEGER
               {
               disabled (0),
               enabled (1)
               }
   MAX-ACCESS  read-write
   STATUS      current
   DESCRIPTION
      "Path: ethernet2.editConf.vlan.bridging.restrictedRole

       Possibilities:
               disabled   (0)
               enabled   (1)"
   ::= {er1645v2Lan2FGVlanEntry 458227712}

er1645v2Lan2FGVlanBridgingAdminEdge OBJECT-TYPE
   SYNTAX      INTEGER
               {
               disabled (0),
               enabled (1)
               }
   MAX-ACCESS  read-write
   STATUS      current
   DESCRIPTION
      "Path: ethernet2.editConf.vlan.bridging.adminEdge

       Possibilities:
               disabled   (0)
               enabled   (1)"
   ::= {er1645v2Lan2FGVlanEntry 457179136}

er1645v2Lan2FGVlanBridgingOamMacDeviceMac OBJECT-TYPE
   SYNTAX      DisplayString
   MAX-ACCESS  read-write
   STATUS      current
   DESCRIPTION
      "Path: ethernet2.editConf.vlan.bridging.ethOam.macAddress.deviceMac"
   ::= {er1645v2Lan2FGVlanEntry 458506496}

er1645v2Lan2FGVlanBridgingOamMacUserMac OBJECT-TYPE
   SYNTAX      OCTET STRING
   MAX-ACCESS  read-write
   STATUS      current
   DESCRIPTION
      "Path: ethernet2.editConf.vlan.bridging.ethOam.macAddress.userMac

       MAC address."
   ::= {er1645v2Lan2FGVlanEntry 458506368}

er1645v2Lan2FGVlanBridgingOamMacBridgeMac OBJECT-TYPE
   SYNTAX      DisplayString
   MAX-ACCESS  read-write
   STATUS      current
   DESCRIPTION
      "Path: ethernet2.editConf.vlan.bridging.ethOam.macAddress.bridgeMac"
   ::= {er1645v2Lan2FGVlanEntry 458506432}

er1645v2Lan2FGVlanBridgingMgmtInline OBJECT-TYPE
   SYNTAX      INTEGER
               {
               disabled (0),
               enabled (1)
               }
   MAX-ACCESS  read-write
   STATUS      current
   DESCRIPTION
      "Path: ethernet2.editConf.vlan.bridging.mgmtInline

       Possibilities:
               disabled   (0)
               enabled   (1)"
   ::= {er1645v2Lan2FGVlanEntry 458752000}

er1645v2Lan2FGVlanBridgingL2ptMode OBJECT-TYPE
   SYNTAX      INTEGER
               {
               disabled (0),
               enabled (1)
               }
   MAX-ACCESS  read-write
   STATUS      current
   DESCRIPTION
      "Path: ethernet2.editConf.vlan.bridging.l2ProtTunnel.mode

       Possibilities:
               disabled   (0)
               enabled   (1)"
   ::= {er1645v2Lan2FGVlanEntry 459292672}

er1645v2Lan2FGVlanBridgingL2ptProtocols OBJECT-TYPE
   SYNTAX      Integer32
   MAX-ACCESS  read-write
   STATUS      current
   DESCRIPTION
      "Path: ethernet2.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan2FGVlanEntry 459309056}

er1645v2Lan2FGVlanBridgingL2ptDestMac OBJECT-TYPE
   SYNTAX      OCTET STRING
   MAX-ACCESS  read-write
   STATUS      current
   DESCRIPTION
      "Path: ethernet2.editConf.vlan.bridging.l2ProtTunnel.destinationMac

       MAC address."
   ::= {er1645v2Lan2FGVlanEntry 459325440}

er1645v2Lan2FGVlanBridgingL2ptCos OBJECT-TYPE
   SYNTAX      INTEGER
               {
               unchanged (255)
               }
   MAX-ACCESS  read-write
   STATUS      current
   DESCRIPTION
      "Path: ethernet2.editConf.vlan.bridging.l2ProtTunnel.cos

       Possibilities:
               unchanged   (255)"
   ::= {er1645v2Lan2FGVlanEntry 459341824}

er1645v2Lan2FGVlanBridgingL2ptDropThrStp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.stp

       unit name = packets/sec

       Possibilities:
               unlimited   (0)"
   ::= {er1645v2Lan2FGVlanEntry 459358272}

er1645v2Lan2FGVlanBridgingL2ptDropThrLldp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.lldp

       unit name = packets/sec

       Possibilities:
               unlimited   (0)"
   ::= {er1645v2Lan2FGVlanEntry 459358336}

er1645v2Lan2FGVlanBridgingL2ptDropThrOam OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.oam

       unit name = packets/sec

       Possibilities:
               unlimited   (0)"
   ::= {er1645v2Lan2FGVlanEntry 459358400}

er1645v2Lan2FGVlanBridgingL2ptDropThrCdp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.cdp

       unit name = packets/sec

       Possibilities:
               unlimited   (0)"
   ::= {er1645v2Lan2FGVlanEntry 459358464}

er1645v2Lan2FGVlanBridgingL2ptDropThrVtp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.vtp

       unit name = packets/sec

       Possibilities:
               unlimited   (0)"
   ::= {er1645v2Lan2FGVlanEntry 459358528}

er1645v2Lan2FGVlanBridgingL2ptDropThrLacp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.lacp

       unit name = packets/sec

       Possibilities:
               unlimited   (0)"
   ::= {er1645v2Lan2FGVlanEntry 459358592}

er1645v2Lan2FGVlanBridgingL2ptDropThrEfmOam OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.efmOam

       unit name = packets/sec

       Possibilities:
               unlimited   (0)"
   ::= {er1645v2Lan2FGVlanEntry 459358656}

er1645v2Lan2FGVlanBridgingL2ptDropThrPvst OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.pvst

       unit name = packets/sec

       Possibilities:
               unlimited   (0)"
   ::= {er1645v2Lan2FGVlanEntry 459358720}

er1645v2Lan2FGVlanBridgingL2ptDropThrMmrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.mmrp

       unit name = packets/sec

       Possibilities:
               unlimited   (0)"
   ::= {er1645v2Lan2FGVlanEntry 459358784}

er1645v2Lan2FGVlanBridgingL2ptDropThrMvrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.mvrp

       unit name = packets/sec

       Possibilities:
               unlimited   (0)"
   ::= {er1645v2Lan2FGVlanEntry 459358848}

er1645v2Lan2FGVlanBridgingL2ptDropThrGvrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.gvrp

       unit name = packets/sec

       Possibilities:
               unlimited   (0)"
   ::= {er1645v2Lan2FGVlanEntry 459358912}

er1645v2Lan2FGVlanBridgingL2ptDropThrGmrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.gmrp

       unit name = packets/sec

       Possibilities:
               unlimited   (0)"
   ::= {er1645v2Lan2FGVlanEntry 459358976}

er1645v2Lan2FGVlanBridgingL2ptDropThrDtp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.dtp

       unit name = packets/sec

       Possibilities:
               unlimited   (0)"
   ::= {er1645v2Lan2FGVlanEntry 459359040}

er1645v2Lan2FGVlanBridgingL2ptDropThrPagp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.pagp

       unit name = packets/sec

       Possibilities:
               unlimited   (0)"
   ::= {er1645v2Lan2FGVlanEntry 459359104}

er1645v2Lan2FGVlanBridgingL2ptDropThrUdld OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.udld

       unit name = packets/sec

       Possibilities:
               unlimited   (0)"
   ::= {er1645v2Lan2FGVlanEntry 459359168}

er1645v2Lan2FGVlanVlanVid OBJECT-TYPE
   SYNTAX      INTEGER
               {
               untagged (0),
               prioTagged (4096),
               notUsed (4097)
               }
   MAX-ACCESS  read-write
   STATUS      current
   DESCRIPTION
      "Path: ethernet2.editConf.vlan.vlan.vid

       Possibilities:
               untagged   (0)
               prioTagged   (4096)
               notUsed   (4097)"
   ::= {er1645v2Lan2FGVlanEntry 234946560}

er1645v2Lan2FGVlanVlanVidExtensionSingle OBJECT-TYPE
   SYNTAX      OCTET STRING
   MAX-ACCESS  read-write
   STATUS      current
   DESCRIPTION
      "Path: ethernet2.editConf.vlan.vlan.vidExtension.single"
   ::= {er1645v2Lan2FGVlanEntry 235340032}

er1645v2Lan2FGVlanVlanVidExtensionEndVid OBJECT-TYPE
   SYNTAX      Integer32
   MAX-ACCESS  read-write
   STATUS      current
   DESCRIPTION
      "Path: ethernet2.editConf.vlan.vlan.vidExtension.endVid"
   ::= {er1645v2Lan2FGVlanEntry 235340288}

er1645v2Lan2FGVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.tpid

       Possibilities:
               dot1Q   (33024)
               dot1ad   (34984)
               0x9100   (37120)
               0x9200   (37376)
               0x9300   (37632)"
   ::= {er1645v2Lan2FGVlanEntry 241238016}

er1645v2Lan2FGVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: ethernet2.editConf.vlan.vlan.tagSignificance

       Possibilities:
               global   (0)
               local   (1)
               sVlan   (2)
               sVlanGlobal   (6)
               cVlan   (3)
               scVlan   (5)
               cVlanLocal   (4)"
   ::= {er1645v2Lan2FGVlanEntry 235012096}

er1645v2Lan2FGVlanVlanChTos OBJECT-TYPE
   SYNTAX      INTEGER
               {
               disabled (0),
               enabled (1)
               }
   MAX-ACCESS  read-write
   STATUS      current
   DESCRIPTION
      "Path: ethernet2.editConf.vlan.vlan.changeTos

       Possibilities:
               disabled   (0)
               enabled   (1)"
   ::= {er1645v2Lan2FGVlanEntry 235208704}

er1645v2Lan2FGVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGVlanEntry 235143424}

er1645v2Lan2FGVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGVlanEntry 235143680}

er1645v2Lan2FGVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGVlanEntry 235143936}

er1645v2Lan2FGVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGVlanEntry 235144192}

er1645v2Lan2FGVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGVlanEntry 235144448}

er1645v2Lan2FGVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGVlanEntry 235144704}

er1645v2Lan2FGVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGVlanEntry 235144960}

er1645v2Lan2FGVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2FGVlanEntry 235145216}

er1645v2Lan2FGVlanVlanTxCos OBJECT-TYPE
   SYNTAX      INTEGER
               {
               tosCosMap (8),
               queueCosMap (16)
               }
   MAX-ACCESS  read-write
   STATUS      current
   DESCRIPTION
      "Path: ethernet2.editConf.vlan.vlan.txCos

       Possibilities:
               tosCosMap   (8)
               queueCosMap   (16)"
   ::= {er1645v2Lan2FGVlanEntry 235077632}

er1645v2Lan2FGVlanVlanCCMapP0 OBJECT-TYPE
   SYNTAX      Integer32
   MAX-ACCESS  read-write
   STATUS      current
   DESCRIPTION
      "Path: ethernet2.editConf.vlan.vlan.cosCosMap.p0"
   ::= {er1645v2Lan2FGVlanEntry 241303808}

er1645v2Lan2FGVlanVlanCCMapP1 OBJECT-TYPE
   SYNTAX      Integer32
   MAX-ACCESS  read-write
   STATUS      current
   DESCRIPTION
      "Path: ethernet2.editConf.vlan.vlan.cosCosMap.p1"
   ::= {er1645v2Lan2FGVlanEntry 241304064}

er1645v2Lan2FGVlanVlanCCMapP2 OBJECT-TYPE
   SYNTAX      Integer32
   MAX-ACCESS  read-write
   STATUS      current
   DESCRIPTION
      "Path: ethernet2.editConf.vlan.vlan.cosCosMap.p2"
   ::= {er1645v2Lan2FGVlanEntry 241304320}

er1645v2Lan2FGVlanVlanCCMapP3 OBJECT-TYPE
   SYNTAX      Integer32
   MAX-ACCESS  read-write
   STATUS      current
   DESCRIPTION
      "Path: ethernet2.editConf.vlan.vlan.cosCosMap.p3"
   ::= {er1645v2Lan2FGVlanEntry 241304576}

er1645v2Lan2FGVlanVlanCCMapP4 OBJECT-TYPE
   SYNTAX      Integer32
   MAX-ACCESS  read-write
   STATUS      current
   DESCRIPTION
      "Path: ethernet2.editConf.vlan.vlan.cosCosMap.p4"
   ::= {er1645v2Lan2FGVlanEntry 241304832}

er1645v2Lan2FGVlanVlanCCMapP5 OBJECT-TYPE
   SYNTAX      Integer32
   MAX-ACCESS  read-write
   STATUS      current
   DESCRIPTION
      "Path: ethernet2.editConf.vlan.vlan.cosCosMap.p5"
   ::= {er1645v2Lan2FGVlanEntry 241305088}

er1645v2Lan2FGVlanVlanCCMapP6 OBJECT-TYPE
   SYNTAX      Integer32
   MAX-ACCESS  read-write
   STATUS      current
   DESCRIPTION
      "Path: ethernet2.editConf.vlan.vlan.cosCosMap.p6"
   ::= {er1645v2Lan2FGVlanEntry 241305344}

er1645v2Lan2FGVlanVlanCCMapP7 OBJECT-TYPE
   SYNTAX      Integer32
   MAX-ACCESS  read-write
   STATUS      current
   DESCRIPTION
      "Path: ethernet2.editConf.vlan.vlan.cosCosMap.p7"
   ::= {er1645v2Lan2FGVlanEntry 241305600}

er1645v2Lan2FGVlanVlanQCMapQueue1 OBJECT-TYPE
   SYNTAX      Integer32
   MAX-ACCESS  read-write
   STATUS      current
   DESCRIPTION
      "Path: ethernet2.editConf.vlan.vlan.queueCosMap.queue1"
   ::= {er1645v2Lan2FGVlanEntry 241434880}

er1645v2Lan2FGVlanVlanQCMapQueue2 OBJECT-TYPE
   SYNTAX      Integer32
   MAX-ACCESS  read-write
   STATUS      current
   DESCRIPTION
      "Path: ethernet2.editConf.vlan.vlan.queueCosMap.queue2"
   ::= {er1645v2Lan2FGVlanEntry 241435136}

er1645v2Lan2FGVlanVlanQCMapQueue3 OBJECT-TYPE
   SYNTAX      Integer32
   MAX-ACCESS  read-write
   STATUS      current
   DESCRIPTION
      "Path: ethernet2.editConf.vlan.vlan.queueCosMap.queue3"
   ::= {er1645v2Lan2FGVlanEntry 241435392}

er1645v2Lan2FGVlanVlanQCMapQueue4 OBJECT-TYPE
   SYNTAX      Integer32
   MAX-ACCESS  read-write
   STATUS      current
   DESCRIPTION
      "Path: ethernet2.editConf.vlan.vlan.queueCosMap.queue4"
   ::= {er1645v2Lan2FGVlanEntry 241435648}

er1645v2Lan2FGVlanVlanQCMapQueue5 OBJECT-TYPE
   SYNTAX      Integer32
   MAX-ACCESS  read-write
   STATUS      current
   DESCRIPTION
      "Path: ethernet2.editConf.vlan.vlan.queueCosMap.queue5"
   ::= {er1645v2Lan2FGVlanEntry 241435904}

er1645v2Lan2FGVlanVlanQCMapLowDelayQueue OBJECT-TYPE
   SYNTAX      Integer32
   MAX-ACCESS  read-write
   STATUS      current
   DESCRIPTION
      "Path: ethernet2.editConf.vlan.vlan.queueCosMap.lowDelayQueue"
   ::= {er1645v2Lan2FGVlanEntry 241436160}

er1645v2Lan2FGVlanVlanQCMapLowDelay2Queue OBJECT-TYPE
   SYNTAX      Integer32
   MAX-ACCESS  read-write
   STATUS      current
   DESCRIPTION
      "Path: ethernet2.editConf.vlan.vlan.queueCosMap.lowDelay2Queue"
   ::= {er1645v2Lan2FGVlanEntry 241436416}

er1645v2Lan2FGVlanVlanQCMapSystemQueue OBJECT-TYPE
   SYNTAX      Integer32
   MAX-ACCESS  read-write
   STATUS      current
   DESCRIPTION
      "Path: ethernet2.editConf.vlan.vlan.queueCosMap.systemQueue"
   ::= {er1645v2Lan2FGVlanEntry 241436672}

er1645v2Lan2FGVlanVlanQinQSVid OBJECT-TYPE
   SYNTAX      Integer32
   MAX-ACCESS  read-write
   STATUS      current
   DESCRIPTION
      "Path: ethernet2.editConf.vlan.vlan.tunnel.sVid"
   ::= {er1645v2Lan2FGVlanEntry 241172736}

er1645v2Lan2FGVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.tunnel.sTpid

       Possibilities:
               dot1Q   (33024)
               dot1ad   (34984)
               0x9100   (37120)
               0x9200   (37376)
               0x9300   (37632)"
   ::= {er1645v2Lan2FGVlanEntry 241172992}

er1645v2Lan2FGVlanVlanArpTimeOut OBJECT-TYPE
   SYNTAX      TimeTicks
   MAX-ACCESS  read-write
   STATUS      current
   DESCRIPTION
      "Path: ethernet2.editConf.vlan.vlan.arp.timeOut

       Time in centi-second."
   ::= {er1645v2Lan2FGVlanEntry 235277312}

er1645v2Lan2FGVlanVlanArpProxyArp OBJECT-TYPE
   SYNTAX      INTEGER
               {
               disabled (0),
               enabled (1)
               }
   MAX-ACCESS  read-write
   STATUS      current
   DESCRIPTION
      "Path: ethernet2.editConf.vlan.vlan.arp.proxyArp

       Possibilities:
               disabled   (0)
               enabled   (1)"
   ::= {er1645v2Lan2FGVlanEntry 235287040}

er1645v2Lan2FGVlanBandwidthMode OBJECT-TYPE
   SYNTAX      INTEGER
               {
               reshaping (1),
               policing (2),
               policingReshape (3)
               }
   MAX-ACCESS  read-write
   STATUS      current
   DESCRIPTION
      "Path: ethernet2.editConf.vlan.bandwidth.mode

       Possibilities:
               reshaping   (1)
               policing   (2)
               policingReshape   (3)"
   ::= {er1645v2Lan2FGVlanEntry 148897792}

er1645v2Lan2FGVlanBandwidthCir OBJECT-TYPE
   SYNTAX      Integer32
   MAX-ACCESS  read-write
   STATUS      current
   DESCRIPTION
      "Path: ethernet2.editConf.vlan.bandwidth.cir"
   ::= {er1645v2Lan2FGVlanEntry 135266304}

er1645v2Lan2FGVlanBandwidthEir OBJECT-TYPE
   SYNTAX      Integer32
   MAX-ACCESS  read-write
   STATUS      current
   DESCRIPTION
      "Path: ethernet2.editConf.vlan.bandwidth.eir"
   ::= {er1645v2Lan2FGVlanEntry 141557760}

er1645v2Lan2FGVlanBandwidthUnit OBJECT-TYPE
   SYNTAX      INTEGER
               {
               bitssec (1),
               percent (2)
               }
   MAX-ACCESS  read-write
   STATUS      current
   DESCRIPTION
      "Path: ethernet2.editConf.vlan.bandwidth.unit

       Possibilities:
               bits/sec   (1)
               percent   (2)"
   ::= {er1645v2Lan2FGVlanEntry 139460608}

er1645v2Lan2FGVlanBandwidthTc OBJECT-TYPE
   SYNTAX      INTEGER
               {
               auto (0)
               }
   MAX-ACCESS  read-write
   STATUS      current
   DESCRIPTION
      "Path: ethernet2.editConf.vlan.bandwidth.tc

       Possibilities:
               auto   (0)"
   ::= {er1645v2Lan2FGVlanEntry 140509184}

er1645v2Lan2FGVlanBandwidthTcFactor OBJECT-TYPE
   SYNTAX      INTEGER
               {
               ms (10),
               s100us (1)
               }
   MAX-ACCESS  read-write
   STATUS      current
   DESCRIPTION
      "Path: ethernet2.editConf.vlan.bandwidth.tcFactor

       Possibilities:
               ms   (10)
               *100us   (1)"
   ::= {er1645v2Lan2FGVlanEntry 142606336}

er1645v2Lan2FGVlanBandwidthCorrType OBJECT-TYPE
   SYNTAX      INTEGER
               {
               noCorrection (0),
               predefined (1),
               manual (2)
               }
   MAX-ACCESS  read-write
   STATUS      current
   DESCRIPTION
      "Path: ethernet2.editConf.vlan.bandwidth.correction.type

       Possibilities:
               noCorrection   (0)
               predefined   (1)
               manual   (2)"
   ::= {er1645v2Lan2FGVlanEntry 136445952}

er1645v2Lan2FGVlanBandwidthCorrPredefEncapsFrameRelay OBJECT-TYPE
   SYNTAX      DisplayString
   MAX-ACCESS  read-write
   STATUS      current
   DESCRIPTION
      "Path: ethernet2.editConf.vlan.bandwidth.correction.predefined.encapsulation.frameRelay"
   ::= {er1645v2Lan2FGVlanEntry 136594432}

er1645v2Lan2FGVlanBandwidthCorrPredefEncapsPpp OBJECT-TYPE
   SYNTAX      DisplayString
   MAX-ACCESS  read-write
   STATUS      current
   DESCRIPTION
      "Path: ethernet2.editConf.vlan.bandwidth.correction.predefined.encapsulation.ppp"
   ::= {er1645v2Lan2FGVlanEntry 136595456}

er1645v2Lan2FGVlanBandwidthCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.vlan.bandwidth.correction.predefined.encapsulation.atm.higherLayer

       Possibilities:
               rfc2684   (0)
               ppp   (1)
               pppOverEthernet   (2)"
   ::= {er1645v2Lan2FGVlanEntry 136596608}

er1645v2Lan2FGVlanBandwidthCorrPredefEncapsAtmMp OBJECT-TYPE
   SYNTAX      INTEGER
               {
               llcEncapsulation (0),
               vcMultiplexing (1)
               }
   MAX-ACCESS  read-write
   STATUS      current
   DESCRIPTION
      "Path: ethernet2.editConf.vlan.bandwidth.correction.predefined.encapsulation.atm.multiProtocol

       Possibilities:
               llcEncapsulation   (0)
               vcMultiplexing   (1)"
   ::= {er1645v2Lan2FGVlanEntry 136596736}

er1645v2Lan2FGVlanBandwidthCorrPredefEncapsHdlc OBJECT-TYPE
   SYNTAX      DisplayString
   MAX-ACCESS  read-write
   STATUS      current
   DESCRIPTION
      "Path: ethernet2.editConf.vlan.bandwidth.correction.predefined.encapsulation.hdlc"
   ::= {er1645v2Lan2FGVlanEntry 136597504}

er1645v2Lan2FGVlanBandwidthCorrPredefEncapsEfmFs OBJECT-TYPE
   SYNTAX      Integer32
   MAX-ACCESS  read-write
   STATUS      current
   DESCRIPTION
      "Path: ethernet2.editConf.vlan.bandwidth.correction.predefined.encapsulation.efm.fragmentSize"
   ::= {er1645v2Lan2FGVlanEntry 136598656}

er1645v2Lan2FGVlanBandwidthCorrPredefEncapsEfmIb OBJECT-TYPE
   SYNTAX      Integer32
   MAX-ACCESS  read-write
   STATUS      current
   DESCRIPTION
      "Path: ethernet2.editConf.vlan.bandwidth.correction.predefined.encapsulation.efm.idleBytes"
   ::= {er1645v2Lan2FGVlanEntry 136598784}

er1645v2Lan2FGVlanBandwidthCorrPredefMode OBJECT-TYPE
   SYNTAX      INTEGER
               {
               routing (0),
               bridging (1)
               }
   MAX-ACCESS  read-write
   STATUS      current
   DESCRIPTION
      "Path: ethernet2.editConf.vlan.bandwidth.correction.predefined.mode

       Possibilities:
               routing   (0)
               bridging   (1)"
   ::= {er1645v2Lan2FGVlanEntry 136609792}

er1645v2Lan2FGVlanBandwidthCorrManualOverhead OBJECT-TYPE
   SYNTAX      Integer32
   MAX-ACCESS  read-write
   STATUS      current
   DESCRIPTION
      "Path: ethernet2.editConf.vlan.bandwidth.correction.manual.overhead"
   ::= {er1645v2Lan2FGVlanEntry 136708608}

er1645v2Lan2FGVlanBandwidthCorrManualFrameData OBJECT-TYPE
   SYNTAX      Counter32
   MAX-ACCESS  read-write
   STATUS      current
   DESCRIPTION
      "Path: ethernet2.editConf.vlan.bandwidth.correction.manual.frameData

       32 bit unsigned wrappable counter."
   ::= {er1645v2Lan2FGVlanEntry 136709120}

er1645v2Lan2FGVlanBandwidthCorrManualFrameHeader OBJECT-TYPE
   SYNTAX      Counter32
   MAX-ACCESS  read-write
   STATUS      current
   DESCRIPTION
      "Path: ethernet2.editConf.vlan.bandwidth.correction.manual.frameHeader

       32 bit unsigned wrappable counter."
   ::= {er1645v2Lan2FGVlanEntry 136709632}

er1645v2Lan2FGVlanBandwidthMaxFifoQLen OBJECT-TYPE
   SYNTAX      Integer32
   MAX-ACCESS  read-write
   STATUS      current
   DESCRIPTION
      "Path: ethernet2.editConf.vlan.bandwidth.maxFifoQLen"
   ::= {er1645v2Lan2FGVlanEntry 137363456}

er1645v2Lan2FGVlanBandwidthDeFlagCir OBJECT-TYPE
   SYNTAX      INTEGER
               {
               allowed (1),
               notAllowed (2)
               }
   MAX-ACCESS  read-write
   STATUS      current
   DESCRIPTION
      "Path: ethernet2.editConf.vlan.bandwidth.deFlag.cir

       Possibilities:
               allowed   (1)
               notAllowed   (2)"
   ::= {er1645v2Lan2FGVlanEntry 147853312}

er1645v2Lan2FGVlanBandwidthDeFlagEir OBJECT-TYPE
   SYNTAX      INTEGER
               {
               allowed (1),
               notAllowed (2)
               }
   MAX-ACCESS  read-write
   STATUS      current
   DESCRIPTION
      "Path: ethernet2.editConf.vlan.bandwidth.deFlag.eir

       Possibilities:
               allowed   (1)
               notAllowed   (2)"
   ::= {er1645v2Lan2FGVlanEntry 147857408}

er1645v2Lan2FGVlanBandwidthDeFlagViolate OBJECT-TYPE
   SYNTAX      INTEGER
               {
               allowed (1),
               notAllowed (2)
               }
   MAX-ACCESS  read-write
   STATUS      current
   DESCRIPTION
      "Path: ethernet2.editConf.vlan.bandwidth.deFlag.violate

       Possibilities:
               allowed   (1)
               notAllowed   (2)"
   ::= {er1645v2Lan2FGVlanEntry 147861504}

er1645v2Lan2FGVlanBandwidthActCirActNone OBJECT-TYPE
   SYNTAX      OCTET STRING
   MAX-ACCESS  read-write
   STATUS      current
   DESCRIPTION
      "Path: ethernet2.editConf.vlan.bandwidth.action.cirAction.none"
   ::= {er1645v2Lan2FGVlanEntry 150085632}

er1645v2Lan2FGVlanBandwidthActCirActEthCos1 OBJECT-TYPE
   SYNTAX      INTEGER
               {
               unchanged (256)
               }
   MAX-ACCESS  read-write
   STATUS      current
   DESCRIPTION
      "Path: ethernet2.editConf.vlan.bandwidth.action.cirAction.ethernet.cosDepth1

       Possibilities:
               unchanged   (256)"
   ::= {er1645v2Lan2FGVlanEntry 150094080}

er1645v2Lan2FGVlanBandwidthActCirActEthDei1 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth1

       Possibilities:
               unchanged   (255)
               clear   (0)
               set   (1)"
   ::= {er1645v2Lan2FGVlanEntry 150099200}

er1645v2Lan2FGVlanBandwidthActCirActEthCos2 OBJECT-TYPE
   SYNTAX      INTEGER
               {
               unchanged (256)
               }
   MAX-ACCESS  read-write
   STATUS      current
   DESCRIPTION
      "Path: ethernet2.editConf.vlan.bandwidth.action.cirAction.ethernet.cosDepth2

       Possibilities:
               unchanged   (256)"
   ::= {er1645v2Lan2FGVlanEntry 150094336}

er1645v2Lan2FGVlanBandwidthActCirActEthDei2 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth2

       Possibilities:
               unchanged   (255)
               clear   (0)
               set   (1)"
   ::= {er1645v2Lan2FGVlanEntry 150099456}

er1645v2Lan2FGVlanBandwidthActCirActEthCos3 OBJECT-TYPE
   SYNTAX      INTEGER
               {
               unchanged (256)
               }
   MAX-ACCESS  read-write
   STATUS      current
   DESCRIPTION
      "Path: ethernet2.editConf.vlan.bandwidth.action.cirAction.ethernet.cosDepth3

       Possibilities:
               unchanged   (256)"
   ::= {er1645v2Lan2FGVlanEntry 150094592}

er1645v2Lan2FGVlanBandwidthActCirActEthDei3 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth3

       Possibilities:
               unchanged   (255)
               clear   (0)
               set   (1)"
   ::= {er1645v2Lan2FGVlanEntry 150099712}

er1645v2Lan2FGVlanBandwidthActCirActEthCos4 OBJECT-TYPE
   SYNTAX      INTEGER
               {
               unchanged (256)
               }
   MAX-ACCESS  read-write
   STATUS      current
   DESCRIPTION
      "Path: ethernet2.editConf.vlan.bandwidth.action.cirAction.ethernet.cosDepth4

       Possibilities:
               unchanged   (256)"
   ::= {er1645v2Lan2FGVlanEntry 150094848}

er1645v2Lan2FGVlanBandwidthActCirActEthDei4 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth4

       Possibilities:
               unchanged   (255)
               clear   (0)
               set   (1)"
   ::= {er1645v2Lan2FGVlanEntry 150099968}

er1645v2Lan2FGVlanBandwidthActCirActEthCos5 OBJECT-TYPE
   SYNTAX      INTEGER
               {
               unchanged (256)
               }
   MAX-ACCESS  read-write
   STATUS      current
   DESCRIPTION
      "Path: ethernet2.editConf.vlan.bandwidth.action.cirAction.ethernet.cosDepth5

       Possibilities:
               unchanged   (256)"
   ::= {er1645v2Lan2FGVlanEntry 150095104}

er1645v2Lan2FGVlanBandwidthActCirActEthDei5 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth5

       Possibilities:
               unchanged   (255)
               clear   (0)
               set   (1)"
   ::= {er1645v2Lan2FGVlanEntry 150100224}

er1645v2Lan2FGVlanBandwidthActCirActEthCos6 OBJECT-TYPE
   SYNTAX      INTEGER
               {
               unchanged (256)
               }
   MAX-ACCESS  read-write
   STATUS      current
   DESCRIPTION
      "Path: ethernet2.editConf.vlan.bandwidth.action.cirAction.ethernet.cosDepth6

       Possibilities:
               unchanged   (256)"
   ::= {er1645v2Lan2FGVlanEntry 150095360}

er1645v2Lan2FGVlanBandwidthActCirActEthDei6 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth6

       Possibilities:
               unchanged   (255)
               clear   (0)
               set   (1)"
   ::= {er1645v2Lan2FGVlanEntry 150100480}

er1645v2Lan2FGVlanBandwidthActCirActEthCos7 OBJECT-TYPE
   SYNTAX      INTEGER
               {
               unchanged (256)
               }
   MAX-ACCESS  read-write
   STATUS      current
   DESCRIPTION
      "Path: ethernet2.editConf.vlan.bandwidth.action.cirAction.ethernet.cosDepth7

       Possibilities:
               unchanged   (256)"
   ::= {er1645v2Lan2FGVlanEntry 150095616}

er1645v2Lan2FGVlanBandwidthActCirActEthDei7 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth7

       Possibilities:
               unchanged   (255)
               clear   (0)
               set   (1)"
   ::= {er1645v2Lan2FGVlanEntry 150100736}

er1645v2Lan2FGVlanBandwidthActCirActEthCos8 OBJECT-TYPE
   SYNTAX      INTEGER
               {
               unchanged (256)
               }
   MAX-ACCESS  read-write
   STATUS      current
   DESCRIPTION
      "Path: ethernet2.editConf.vlan.bandwidth.action.cirAction.ethernet.cosDepth8

       Possibilities:
               unchanged   (256)"
   ::= {er1645v2Lan2FGVlanEntry 150095872}

er1645v2Lan2FGVlanBandwidthActCirActEthDei8 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth8

       Possibilities:
               unchanged   (255)
               clear   (0)
               set   (1)"
   ::= {er1645v2Lan2FGVlanEntry 150100992}

er1645v2Lan2FGVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 150096128}

er1645v2Lan2FGVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 150096384}

er1645v2Lan2FGVlanBandwidthActCirActEthDrpLev OBJECT-TYPE
   SYNTAX      INTEGER
               {
               unchanged (0)
               }
   MAX-ACCESS  read-write
   STATUS      current
   DESCRIPTION
      "Path: ethernet2.editConf.vlan.bandwidth.action.cirAction.ethernet.dropLevel

       Possibilities:
               unchanged   (0)"
   ::= {er1645v2Lan2FGVlanEntry 150096640}

er1645v2Lan2FGVlanBandwidthActCirActEthDeFlag OBJECT-TYPE
   SYNTAX      INTEGER
               {
               unchanged (255),
               clear (0),
               set (1)
               }
   MAX-ACCESS  read-write
   STATUS      current
   DESCRIPTION
      "Path: ethernet2.editConf.vlan.bandwidth.action.cirAction.ethernet.deFlag

       Possibilities:
               unchanged   (255)
               clear   (0)
               set   (1)"
   ::= {er1645v2Lan2FGVlanEntry 150097408}

er1645v2Lan2FGVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 150120704}

er1645v2Lan2FGVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 150120960}

er1645v2Lan2FGVlanBandwidthActCirActIpDrpLev OBJECT-TYPE
   SYNTAX      INTEGER
               {
               unchanged (0)
               }
   MAX-ACCESS  read-write
   STATUS      current
   DESCRIPTION
      "Path: ethernet2.editConf.vlan.bandwidth.action.cirAction.ip.dropLevel

       Possibilities:
               unchanged   (0)"
   ::= {er1645v2Lan2FGVlanEntry 150121216}

er1645v2Lan2FGVlanBandwidthActCirActIpDeFlag OBJECT-TYPE
   SYNTAX      INTEGER
               {
               unchanged (255),
               clear (0),
               set (1)
               }
   MAX-ACCESS  read-write
   STATUS      current
   DESCRIPTION
      "Path: ethernet2.editConf.vlan.bandwidth.action.cirAction.ip.deFlag

       Possibilities:
               unchanged   (255)
               clear   (0)
               set   (1)"
   ::= {er1645v2Lan2FGVlanEntry 150121984}

er1645v2Lan2FGVlanBandwidthActEirActNone OBJECT-TYPE
   SYNTAX      OCTET STRING
   MAX-ACCESS  read-write
   STATUS      current
   DESCRIPTION
      "Path: ethernet2.editConf.vlan.bandwidth.action.eirAction.none"
   ::= {er1645v2Lan2FGVlanEntry 150216704}

er1645v2Lan2FGVlanBandwidthActEirActEthCos1 OBJECT-TYPE
   SYNTAX      INTEGER
               {
               unchanged (256)
               }
   MAX-ACCESS  read-write
   STATUS      current
   DESCRIPTION
      "Path: ethernet2.editConf.vlan.bandwidth.action.eirAction.ethernet.cosDepth1

       Possibilities:
               unchanged   (256)"
   ::= {er1645v2Lan2FGVlanEntry 150225152}

er1645v2Lan2FGVlanBandwidthActEirActEthDei1 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth1

       Possibilities:
               unchanged   (255)
               clear   (0)
               set   (1)"
   ::= {er1645v2Lan2FGVlanEntry 150230272}

er1645v2Lan2FGVlanBandwidthActEirActEthCos2 OBJECT-TYPE
   SYNTAX      INTEGER
               {
               unchanged (256)
               }
   MAX-ACCESS  read-write
   STATUS      current
   DESCRIPTION
      "Path: ethernet2.editConf.vlan.bandwidth.action.eirAction.ethernet.cosDepth2

       Possibilities:
               unchanged   (256)"
   ::= {er1645v2Lan2FGVlanEntry 150225408}

er1645v2Lan2FGVlanBandwidthActEirActEthDei2 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth2

       Possibilities:
               unchanged   (255)
               clear   (0)
               set   (1)"
   ::= {er1645v2Lan2FGVlanEntry 150230528}

er1645v2Lan2FGVlanBandwidthActEirActEthCos3 OBJECT-TYPE
   SYNTAX      INTEGER
               {
               unchanged (256)
               }
   MAX-ACCESS  read-write
   STATUS      current
   DESCRIPTION
      "Path: ethernet2.editConf.vlan.bandwidth.action.eirAction.ethernet.cosDepth3

       Possibilities:
               unchanged   (256)"
   ::= {er1645v2Lan2FGVlanEntry 150225664}

er1645v2Lan2FGVlanBandwidthActEirActEthDei3 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth3

       Possibilities:
               unchanged   (255)
               clear   (0)
               set   (1)"
   ::= {er1645v2Lan2FGVlanEntry 150230784}

er1645v2Lan2FGVlanBandwidthActEirActEthCos4 OBJECT-TYPE
   SYNTAX      INTEGER
               {
               unchanged (256)
               }
   MAX-ACCESS  read-write
   STATUS      current
   DESCRIPTION
      "Path: ethernet2.editConf.vlan.bandwidth.action.eirAction.ethernet.cosDepth4

       Possibilities:
               unchanged   (256)"
   ::= {er1645v2Lan2FGVlanEntry 150225920}

er1645v2Lan2FGVlanBandwidthActEirActEthDei4 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth4

       Possibilities:
               unchanged   (255)
               clear   (0)
               set   (1)"
   ::= {er1645v2Lan2FGVlanEntry 150231040}

er1645v2Lan2FGVlanBandwidthActEirActEthCos5 OBJECT-TYPE
   SYNTAX      INTEGER
               {
               unchanged (256)
               }
   MAX-ACCESS  read-write
   STATUS      current
   DESCRIPTION
      "Path: ethernet2.editConf.vlan.bandwidth.action.eirAction.ethernet.cosDepth5

       Possibilities:
               unchanged   (256)"
   ::= {er1645v2Lan2FGVlanEntry 150226176}

er1645v2Lan2FGVlanBandwidthActEirActEthDei5 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth5

       Possibilities:
               unchanged   (255)
               clear   (0)
               set   (1)"
   ::= {er1645v2Lan2FGVlanEntry 150231296}

er1645v2Lan2FGVlanBandwidthActEirActEthCos6 OBJECT-TYPE
   SYNTAX      INTEGER
               {
               unchanged (256)
               }
   MAX-ACCESS  read-write
   STATUS      current
   DESCRIPTION
      "Path: ethernet2.editConf.vlan.bandwidth.action.eirAction.ethernet.cosDepth6

       Possibilities:
               unchanged   (256)"
   ::= {er1645v2Lan2FGVlanEntry 150226432}

er1645v2Lan2FGVlanBandwidthActEirActEthDei6 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth6

       Possibilities:
               unchanged   (255)
               clear   (0)
               set   (1)"
   ::= {er1645v2Lan2FGVlanEntry 150231552}

er1645v2Lan2FGVlanBandwidthActEirActEthCos7 OBJECT-TYPE
   SYNTAX      INTEGER
               {
               unchanged (256)
               }
   MAX-ACCESS  read-write
   STATUS      current
   DESCRIPTION
      "Path: ethernet2.editConf.vlan.bandwidth.action.eirAction.ethernet.cosDepth7

       Possibilities:
               unchanged   (256)"
   ::= {er1645v2Lan2FGVlanEntry 150226688}

er1645v2Lan2FGVlanBandwidthActEirActEthDei7 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth7

       Possibilities:
               unchanged   (255)
               clear   (0)
               set   (1)"
   ::= {er1645v2Lan2FGVlanEntry 150231808}

er1645v2Lan2FGVlanBandwidthActEirActEthCos8 OBJECT-TYPE
   SYNTAX      INTEGER
               {
               unchanged (256)
               }
   MAX-ACCESS  read-write
   STATUS      current
   DESCRIPTION
      "Path: ethernet2.editConf.vlan.bandwidth.action.eirAction.ethernet.cosDepth8

       Possibilities:
               unchanged   (256)"
   ::= {er1645v2Lan2FGVlanEntry 150226944}

er1645v2Lan2FGVlanBandwidthActEirActEthDei8 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth8

       Possibilities:
               unchanged   (255)
               clear   (0)
               set   (1)"
   ::= {er1645v2Lan2FGVlanEntry 150232064}

er1645v2Lan2FGVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 150227200}

er1645v2Lan2FGVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 150227456}

er1645v2Lan2FGVlanBandwidthActEirActEthDrpLev OBJECT-TYPE
   SYNTAX      INTEGER
               {
               unchanged (0)
               }
   MAX-ACCESS  read-write
   STATUS      current
   DESCRIPTION
      "Path: ethernet2.editConf.vlan.bandwidth.action.eirAction.ethernet.dropLevel

       Possibilities:
               unchanged   (0)"
   ::= {er1645v2Lan2FGVlanEntry 150227712}

er1645v2Lan2FGVlanBandwidthActEirActEthDeFlag OBJECT-TYPE
   SYNTAX      INTEGER
               {
               unchanged (255),
               clear (0),
               set (1)
               }
   MAX-ACCESS  read-write
   STATUS      current
   DESCRIPTION
      "Path: ethernet2.editConf.vlan.bandwidth.action.eirAction.ethernet.deFlag

       Possibilities:
               unchanged   (255)
               clear   (0)
               set   (1)"
   ::= {er1645v2Lan2FGVlanEntry 150228480}

er1645v2Lan2FGVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 150251776}

er1645v2Lan2FGVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 150252032}

er1645v2Lan2FGVlanBandwidthActEirActIpDrpLev OBJECT-TYPE
   SYNTAX      INTEGER
               {
               unchanged (0)
               }
   MAX-ACCESS  read-write
   STATUS      current
   DESCRIPTION
      "Path: ethernet2.editConf.vlan.bandwidth.action.eirAction.ip.dropLevel

       Possibilities:
               unchanged   (0)"
   ::= {er1645v2Lan2FGVlanEntry 150252288}

er1645v2Lan2FGVlanBandwidthActEirActIpDeFlag OBJECT-TYPE
   SYNTAX      INTEGER
               {
               unchanged (255),
               clear (0),
               set (1)
               }
   MAX-ACCESS  read-write
   STATUS      current
   DESCRIPTION
      "Path: ethernet2.editConf.vlan.bandwidth.action.eirAction.ip.deFlag

       Possibilities:
               unchanged   (255)
               clear   (0)
               set   (1)"
   ::= {er1645v2Lan2FGVlanEntry 150253056}

er1645v2Lan2FGVlanBandwidthActViolActNone OBJECT-TYPE
   SYNTAX      OCTET STRING
   MAX-ACCESS  read-write
   STATUS      current
   DESCRIPTION
      "Path: ethernet2.editConf.vlan.bandwidth.action.violateAction.none"
   ::= {er1645v2Lan2FGVlanEntry 150347776}

er1645v2Lan2FGVlanBandwidthActViolActDrop OBJECT-TYPE
   SYNTAX      OCTET STRING
   MAX-ACCESS  read-write
   STATUS      current
   DESCRIPTION
      "Path: ethernet2.editConf.vlan.bandwidth.action.violateAction.drop"
   ::= {er1645v2Lan2FGVlanEntry 150364160}

er1645v2Lan2FGVlanBandwidthActViolActEthCos1 OBJECT-TYPE
   SYNTAX      INTEGER
               {
               unchanged (256)
               }
   MAX-ACCESS  read-write
   STATUS      current
   DESCRIPTION
      "Path: ethernet2.editConf.vlan.bandwidth.action.violateAction.ethernet.cosDepth1

       Possibilities:
               unchanged   (256)"
   ::= {er1645v2Lan2FGVlanEntry 150356224}

er1645v2Lan2FGVlanBandwidthActViolActEthDei1 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth1

       Possibilities:
               unchanged   (255)
               clear   (0)
               set   (1)"
   ::= {er1645v2Lan2FGVlanEntry 150361344}

er1645v2Lan2FGVlanBandwidthActViolActEthCos2 OBJECT-TYPE
   SYNTAX      INTEGER
               {
               unchanged (256)
               }
   MAX-ACCESS  read-write
   STATUS      current
   DESCRIPTION
      "Path: ethernet2.editConf.vlan.bandwidth.action.violateAction.ethernet.cosDepth2

       Possibilities:
               unchanged   (256)"
   ::= {er1645v2Lan2FGVlanEntry 150356480}

er1645v2Lan2FGVlanBandwidthActViolActEthDei2 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth2

       Possibilities:
               unchanged   (255)
               clear   (0)
               set   (1)"
   ::= {er1645v2Lan2FGVlanEntry 150361600}

er1645v2Lan2FGVlanBandwidthActViolActEthCos3 OBJECT-TYPE
   SYNTAX      INTEGER
               {
               unchanged (256)
               }
   MAX-ACCESS  read-write
   STATUS      current
   DESCRIPTION
      "Path: ethernet2.editConf.vlan.bandwidth.action.violateAction.ethernet.cosDepth3

       Possibilities:
               unchanged   (256)"
   ::= {er1645v2Lan2FGVlanEntry 150356736}

er1645v2Lan2FGVlanBandwidthActViolActEthDei3 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth3

       Possibilities:
               unchanged   (255)
               clear   (0)
               set   (1)"
   ::= {er1645v2Lan2FGVlanEntry 150361856}

er1645v2Lan2FGVlanBandwidthActViolActEthCos4 OBJECT-TYPE
   SYNTAX      INTEGER
               {
               unchanged (256)
               }
   MAX-ACCESS  read-write
   STATUS      current
   DESCRIPTION
      "Path: ethernet2.editConf.vlan.bandwidth.action.violateAction.ethernet.cosDepth4

       Possibilities:
               unchanged   (256)"
   ::= {er1645v2Lan2FGVlanEntry 150356992}

er1645v2Lan2FGVlanBandwidthActViolActEthDei4 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth4

       Possibilities:
               unchanged   (255)
               clear   (0)
               set   (1)"
   ::= {er1645v2Lan2FGVlanEntry 150362112}

er1645v2Lan2FGVlanBandwidthActViolActEthCos5 OBJECT-TYPE
   SYNTAX      INTEGER
               {
               unchanged (256)
               }
   MAX-ACCESS  read-write
   STATUS      current
   DESCRIPTION
      "Path: ethernet2.editConf.vlan.bandwidth.action.violateAction.ethernet.cosDepth5

       Possibilities:
               unchanged   (256)"
   ::= {er1645v2Lan2FGVlanEntry 150357248}

er1645v2Lan2FGVlanBandwidthActViolActEthDei5 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth5

       Possibilities:
               unchanged   (255)
               clear   (0)
               set   (1)"
   ::= {er1645v2Lan2FGVlanEntry 150362368}

er1645v2Lan2FGVlanBandwidthActViolActEthCos6 OBJECT-TYPE
   SYNTAX      INTEGER
               {
               unchanged (256)
               }
   MAX-ACCESS  read-write
   STATUS      current
   DESCRIPTION
      "Path: ethernet2.editConf.vlan.bandwidth.action.violateAction.ethernet.cosDepth6

       Possibilities:
               unchanged   (256)"
   ::= {er1645v2Lan2FGVlanEntry 150357504}

er1645v2Lan2FGVlanBandwidthActViolActEthDei6 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth6

       Possibilities:
               unchanged   (255)
               clear   (0)
               set   (1)"
   ::= {er1645v2Lan2FGVlanEntry 150362624}

er1645v2Lan2FGVlanBandwidthActViolActEthCos7 OBJECT-TYPE
   SYNTAX      INTEGER
               {
               unchanged (256)
               }
   MAX-ACCESS  read-write
   STATUS      current
   DESCRIPTION
      "Path: ethernet2.editConf.vlan.bandwidth.action.violateAction.ethernet.cosDepth7

       Possibilities:
               unchanged   (256)"
   ::= {er1645v2Lan2FGVlanEntry 150357760}

er1645v2Lan2FGVlanBandwidthActViolActEthDei7 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth7

       Possibilities:
               unchanged   (255)
               clear   (0)
               set   (1)"
   ::= {er1645v2Lan2FGVlanEntry 150362880}

er1645v2Lan2FGVlanBandwidthActViolActEthCos8 OBJECT-TYPE
   SYNTAX      INTEGER
               {
               unchanged (256)
               }
   MAX-ACCESS  read-write
   STATUS      current
   DESCRIPTION
      "Path: ethernet2.editConf.vlan.bandwidth.action.violateAction.ethernet.cosDepth8

       Possibilities:
               unchanged   (256)"
   ::= {er1645v2Lan2FGVlanEntry 150358016}

er1645v2Lan2FGVlanBandwidthActViolActEthDei8 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth8

       Possibilities:
               unchanged   (255)
               clear   (0)
               set   (1)"
   ::= {er1645v2Lan2FGVlanEntry 150363136}

er1645v2Lan2FGVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 150358272}

er1645v2Lan2FGVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 150358528}

er1645v2Lan2FGVlanBandwidthActViolActEthDrpLev OBJECT-TYPE
   SYNTAX      INTEGER
               {
               unchanged (0)
               }
   MAX-ACCESS  read-write
   STATUS      current
   DESCRIPTION
      "Path: ethernet2.editConf.vlan.bandwidth.action.violateAction.ethernet.dropLevel

       Possibilities:
               unchanged   (0)"
   ::= {er1645v2Lan2FGVlanEntry 150358784}

er1645v2Lan2FGVlanBandwidthActViolActEthDeFlag OBJECT-TYPE
   SYNTAX      INTEGER
               {
               unchanged (255),
               clear (0),
               set (1)
               }
   MAX-ACCESS  read-write
   STATUS      current
   DESCRIPTION
      "Path: ethernet2.editConf.vlan.bandwidth.action.violateAction.ethernet.deFlag

       Possibilities:
               unchanged   (255)
               clear   (0)
               set   (1)"
   ::= {er1645v2Lan2FGVlanEntry 150359552}

er1645v2Lan2FGVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 150382848}

er1645v2Lan2FGVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 150383104}

er1645v2Lan2FGVlanBandwidthActViolActIpDrpLev OBJECT-TYPE
   SYNTAX      INTEGER
               {
               unchanged (0)
               }
   MAX-ACCESS  read-write
   STATUS      current
   DESCRIPTION
      "Path: ethernet2.editConf.vlan.bandwidth.action.violateAction.ip.dropLevel

       Possibilities:
               unchanged   (0)"
   ::= {er1645v2Lan2FGVlanEntry 150383360}

er1645v2Lan2FGVlanBandwidthActViolActIpDeFlag OBJECT-TYPE
   SYNTAX      INTEGER
               {
               unchanged (255),
               clear (0),
               set (1)
               }
   MAX-ACCESS  read-write
   STATUS      current
   DESCRIPTION
      "Path: ethernet2.editConf.vlan.bandwidth.action.violateAction.ip.deFlag

       Possibilities:
               unchanged   (255)
               clear   (0)
               set   (1)"
   ::= {er1645v2Lan2FGVlanEntry 150384128}

er1645v2Lan2FGVlanInbBwMode OBJECT-TYPE
   SYNTAX      INTEGER
               {
               reshaping (1),
               policing (2)
               }
   MAX-ACCESS  read-write
   STATUS      current
   DESCRIPTION
      "Path: ethernet2.editConf.vlan.inboundBandwidth.mode

       Possibilities:
               reshaping   (1)
               policing   (2)"
   ::= {er1645v2Lan2FGVlanEntry 132120576}

er1645v2Lan2FGVlanInbBwCir OBJECT-TYPE
   SYNTAX      Integer32
   MAX-ACCESS  read-write
   STATUS      current
   DESCRIPTION
      "Path: ethernet2.editConf.vlan.inboundBandwidth.cir"
   ::= {er1645v2Lan2FGVlanEntry 118489088}

er1645v2Lan2FGVlanInbBwEir OBJECT-TYPE
   SYNTAX      Integer32
   MAX-ACCESS  read-write
   STATUS      current
   DESCRIPTION
      "Path: ethernet2.editConf.vlan.inboundBandwidth.eir"
   ::= {er1645v2Lan2FGVlanEntry 124780544}

er1645v2Lan2FGVlanInbBwUnit OBJECT-TYPE
   SYNTAX      INTEGER
               {
               bitssec (1),
               percent (2)
               }
   MAX-ACCESS  read-write
   STATUS      current
   DESCRIPTION
      "Path: ethernet2.editConf.vlan.inboundBandwidth.unit

       Possibilities:
               bits/sec   (1)
               percent   (2)"
   ::= {er1645v2Lan2FGVlanEntry 122683392}

er1645v2Lan2FGVlanInbBwTc OBJECT-TYPE
   SYNTAX      INTEGER
               {
               auto (0)
               }
   MAX-ACCESS  read-write
   STATUS      current
   DESCRIPTION
      "Path: ethernet2.editConf.vlan.inboundBandwidth.tc

       Possibilities:
               auto   (0)"
   ::= {er1645v2Lan2FGVlanEntry 123731968}

er1645v2Lan2FGVlanInbBwTcFactor OBJECT-TYPE
   SYNTAX      INTEGER
               {
               ms (10),
               s100us (1)
               }
   MAX-ACCESS  read-write
   STATUS      current
   DESCRIPTION
      "Path: ethernet2.editConf.vlan.inboundBandwidth.tcFactor

       Possibilities:
               ms   (10)
               *100us   (1)"
   ::= {er1645v2Lan2FGVlanEntry 125829120}

er1645v2Lan2FGVlanInbBwCorrType OBJECT-TYPE
   SYNTAX      INTEGER
               {
               noCorrection (0),
               predefined (1),
               manual (2)
               }
   MAX-ACCESS  read-write
   STATUS      current
   DESCRIPTION
      "Path: ethernet2.editConf.vlan.inboundBandwidth.correction.type

       Possibilities:
               noCorrection   (0)
               predefined   (1)
               manual   (2)"
   ::= {er1645v2Lan2FGVlanEntry 119668736}

er1645v2Lan2FGVlanInbBwCorrPredefEncapsFrameRelay OBJECT-TYPE
   SYNTAX      DisplayString
   MAX-ACCESS  read-write
   STATUS      current
   DESCRIPTION
      "Path: ethernet2.editConf.vlan.inboundBandwidth.correction.predefined.encapsulation.frameRelay"
   ::= {er1645v2Lan2FGVlanEntry 119817216}

er1645v2Lan2FGVlanInbBwCorrPredefEncapsPpp OBJECT-TYPE
   SYNTAX      DisplayString
   MAX-ACCESS  read-write
   STATUS      current
   DESCRIPTION
      "Path: ethernet2.editConf.vlan.inboundBandwidth.correction.predefined.encapsulation.ppp"
   ::= {er1645v2Lan2FGVlanEntry 119818240}

er1645v2Lan2FGVlanInbBwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.vlan.inboundBandwidth.correction.predefined.encapsulation.atm.higherLayer

       Possibilities:
               rfc2684   (0)
               ppp   (1)
               pppOverEthernet   (2)"
   ::= {er1645v2Lan2FGVlanEntry 119819392}

er1645v2Lan2FGVlanInbBwCorrPredefEncapsAtmMp OBJECT-TYPE
   SYNTAX      INTEGER
               {
               llcEncapsulation (0),
               vcMultiplexing (1)
               }
   MAX-ACCESS  read-write
   STATUS      current
   DESCRIPTION
      "Path: ethernet2.editConf.vlan.inboundBandwidth.correction.predefined.encapsulation.atm.multiProtocol

       Possibilities:
               llcEncapsulation   (0)
               vcMultiplexing   (1)"
   ::= {er1645v2Lan2FGVlanEntry 119819520}

er1645v2Lan2FGVlanInbBwCorrPredefEncapsHdlc OBJECT-TYPE
   SYNTAX      DisplayString
   MAX-ACCESS  read-write
   STATUS      current
   DESCRIPTION
      "Path: ethernet2.editConf.vlan.inboundBandwidth.correction.predefined.encapsulation.hdlc"
   ::= {er1645v2Lan2FGVlanEntry 119820288}

er1645v2Lan2FGVlanInbBwCorrPredefEncapsEfmFs OBJECT-TYPE
   SYNTAX      Integer32
   MAX-ACCESS  read-write
   STATUS      current
   DESCRIPTION
      "Path: ethernet2.editConf.vlan.inboundBandwidth.correction.predefined.encapsulation.efm.fragmentSize"
   ::= {er1645v2Lan2FGVlanEntry 119821440}

er1645v2Lan2FGVlanInbBwCorrPredefEncapsEfmIb OBJECT-TYPE
   SYNTAX      Integer32
   MAX-ACCESS  read-write
   STATUS      current
   DESCRIPTION
      "Path: ethernet2.editConf.vlan.inboundBandwidth.correction.predefined.encapsulation.efm.idleBytes"
   ::= {er1645v2Lan2FGVlanEntry 119821568}

er1645v2Lan2FGVlanInbBwCorrPredefMode OBJECT-TYPE
   SYNTAX      INTEGER
               {
               routing (0),
               bridging (1)
               }
   MAX-ACCESS  read-write
   STATUS      current
   DESCRIPTION
      "Path: ethernet2.editConf.vlan.inboundBandwidth.correction.predefined.mode

       Possibilities:
               routing   (0)
               bridging   (1)"
   ::= {er1645v2Lan2FGVlanEntry 119832576}

er1645v2Lan2FGVlanInbBwCorrManualOverhead OBJECT-TYPE
   SYNTAX      Integer32
   MAX-ACCESS  read-write
   STATUS      current
   DESCRIPTION
      "Path: ethernet2.editConf.vlan.inboundBandwidth.correction.manual.overhead"
   ::= {er1645v2Lan2FGVlanEntry 119931392}

er1645v2Lan2FGVlanInbBwCorrManualFrameData OBJECT-TYPE
   SYNTAX      Counter32
   MAX-ACCESS  read-write
   STATUS      current
   DESCRIPTION
      "Path: ethernet2.editConf.vlan.inboundBandwidth.correction.manual.frameData

       32 bit unsigned wrappable counter."
   ::= {er1645v2Lan2FGVlanEntry 119931904}

er1645v2Lan2FGVlanInbBwCorrManualFrameHeader OBJECT-TYPE
   SYNTAX      Counter32
   MAX-ACCESS  read-write
   STATUS      current
   DESCRIPTION
      "Path: ethernet2.editConf.vlan.inboundBandwidth.correction.manual.frameHeader

       32 bit unsigned wrappable counter."
   ::= {er1645v2Lan2FGVlanEntry 119932416}

er1645v2Lan2FGVlanInbBwMaxFifoQLen OBJECT-TYPE
   SYNTAX      Integer32
   MAX-ACCESS  read-write
   STATUS      current
   DESCRIPTION
      "Path: ethernet2.editConf.vlan.inboundBandwidth.maxFifoQLen"
   ::= {er1645v2Lan2FGVlanEntry 120586240}

er1645v2Lan2FGVlanInbBwPriorityPolicy OBJECT-TYPE
   SYNTAX      DisplayString
   MAX-ACCESS  read-write
   STATUS      current
   DESCRIPTION
      "Path: ethernet2.editConf.vlan.inboundBandwidth.priorityPolicy"
   ::= {er1645v2Lan2FGVlanEntry 121634816}

er1645v2Lan2FGVlanInbBwDeFlagCir OBJECT-TYPE
   SYNTAX      INTEGER
               {
               allowed (1),
               notAllowed (2)
               }
   MAX-ACCESS  read-write
   STATUS      current
   DESCRIPTION
      "Path: ethernet2.editConf.vlan.inboundBandwidth.deFlag.cir

       Possibilities:
               allowed   (1)
               notAllowed   (2)"
   ::= {er1645v2Lan2FGVlanEntry 131076096}

er1645v2Lan2FGVlanInbBwDeFlagEir OBJECT-TYPE
   SYNTAX      INTEGER
               {
               allowed (1),
               notAllowed (2)
               }
   MAX-ACCESS  read-write
   STATUS      current
   DESCRIPTION
      "Path: ethernet2.editConf.vlan.inboundBandwidth.deFlag.eir

       Possibilities:
               allowed   (1)
               notAllowed   (2)"
   ::= {er1645v2Lan2FGVlanEntry 131080192}

er1645v2Lan2FGVlanInbBwDeFlagViolate OBJECT-TYPE
   SYNTAX      INTEGER
               {
               allowed (1),
               notAllowed (2)
               }
   MAX-ACCESS  read-write
   STATUS      current
   DESCRIPTION
      "Path: ethernet2.editConf.vlan.inboundBandwidth.deFlag.violate

       Possibilities:
               allowed   (1)
               notAllowed   (2)"
   ::= {er1645v2Lan2FGVlanEntry 131084288}

er1645v2Lan2FGVlanInbBwActCirActNone OBJECT-TYPE
   SYNTAX      OCTET STRING
   MAX-ACCESS  read-write
   STATUS      current
   DESCRIPTION
      "Path: ethernet2.editConf.vlan.inboundBandwidth.action.cirAction.none"
   ::= {er1645v2Lan2FGVlanEntry 133308416}

er1645v2Lan2FGVlanInbBwActCirActEthCos1 OBJECT-TYPE
   SYNTAX      INTEGER
               {
               unchanged (256)
               }
   MAX-ACCESS  read-write
   STATUS      current
   DESCRIPTION
      "Path: ethernet2.editConf.vlan.inboundBandwidth.action.cirAction.ethernet.cosDepth1

       Possibilities:
               unchanged   (256)"
   ::= {er1645v2Lan2FGVlanEntry 133316864}

er1645v2Lan2FGVlanInbBwActCirActEthDei1 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth1

       Possibilities:
               unchanged   (255)
               clear   (0)
               set   (1)"
   ::= {er1645v2Lan2FGVlanEntry 133321984}

er1645v2Lan2FGVlanInbBwActCirActEthCos2 OBJECT-TYPE
   SYNTAX      INTEGER
               {
               unchanged (256)
               }
   MAX-ACCESS  read-write
   STATUS      current
   DESCRIPTION
      "Path: ethernet2.editConf.vlan.inboundBandwidth.action.cirAction.ethernet.cosDepth2

       Possibilities:
               unchanged   (256)"
   ::= {er1645v2Lan2FGVlanEntry 133317120}

er1645v2Lan2FGVlanInbBwActCirActEthDei2 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth2

       Possibilities:
               unchanged   (255)
               clear   (0)
               set   (1)"
   ::= {er1645v2Lan2FGVlanEntry 133322240}

er1645v2Lan2FGVlanInbBwActCirActEthCos3 OBJECT-TYPE
   SYNTAX      INTEGER
               {
               unchanged (256)
               }
   MAX-ACCESS  read-write
   STATUS      current
   DESCRIPTION
      "Path: ethernet2.editConf.vlan.inboundBandwidth.action.cirAction.ethernet.cosDepth3

       Possibilities:
               unchanged   (256)"
   ::= {er1645v2Lan2FGVlanEntry 133317376}

er1645v2Lan2FGVlanInbBwActCirActEthDei3 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth3

       Possibilities:
               unchanged   (255)
               clear   (0)
               set   (1)"
   ::= {er1645v2Lan2FGVlanEntry 133322496}

er1645v2Lan2FGVlanInbBwActCirActEthCos4 OBJECT-TYPE
   SYNTAX      INTEGER
               {
               unchanged (256)
               }
   MAX-ACCESS  read-write
   STATUS      current
   DESCRIPTION
      "Path: ethernet2.editConf.vlan.inboundBandwidth.action.cirAction.ethernet.cosDepth4

       Possibilities:
               unchanged   (256)"
   ::= {er1645v2Lan2FGVlanEntry 133317632}

er1645v2Lan2FGVlanInbBwActCirActEthDei4 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth4

       Possibilities:
               unchanged   (255)
               clear   (0)
               set   (1)"
   ::= {er1645v2Lan2FGVlanEntry 133322752}

er1645v2Lan2FGVlanInbBwActCirActEthCos5 OBJECT-TYPE
   SYNTAX      INTEGER
               {
               unchanged (256)
               }
   MAX-ACCESS  read-write
   STATUS      current
   DESCRIPTION
      "Path: ethernet2.editConf.vlan.inboundBandwidth.action.cirAction.ethernet.cosDepth5

       Possibilities:
               unchanged   (256)"
   ::= {er1645v2Lan2FGVlanEntry 133317888}

er1645v2Lan2FGVlanInbBwActCirActEthDei5 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth5

       Possibilities:
               unchanged   (255)
               clear   (0)
               set   (1)"
   ::= {er1645v2Lan2FGVlanEntry 133323008}

er1645v2Lan2FGVlanInbBwActCirActEthCos6 OBJECT-TYPE
   SYNTAX      INTEGER
               {
               unchanged (256)
               }
   MAX-ACCESS  read-write
   STATUS      current
   DESCRIPTION
      "Path: ethernet2.editConf.vlan.inboundBandwidth.action.cirAction.ethernet.cosDepth6

       Possibilities:
               unchanged   (256)"
   ::= {er1645v2Lan2FGVlanEntry 133318144}

er1645v2Lan2FGVlanInbBwActCirActEthDei6 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth6

       Possibilities:
               unchanged   (255)
               clear   (0)
               set   (1)"
   ::= {er1645v2Lan2FGVlanEntry 133323264}

er1645v2Lan2FGVlanInbBwActCirActEthCos7 OBJECT-TYPE
   SYNTAX      INTEGER
               {
               unchanged (256)
               }
   MAX-ACCESS  read-write
   STATUS      current
   DESCRIPTION
      "Path: ethernet2.editConf.vlan.inboundBandwidth.action.cirAction.ethernet.cosDepth7

       Possibilities:
               unchanged   (256)"
   ::= {er1645v2Lan2FGVlanEntry 133318400}

er1645v2Lan2FGVlanInbBwActCirActEthDei7 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth7

       Possibilities:
               unchanged   (255)
               clear   (0)
               set   (1)"
   ::= {er1645v2Lan2FGVlanEntry 133323520}

er1645v2Lan2FGVlanInbBwActCirActEthCos8 OBJECT-TYPE
   SYNTAX      INTEGER
               {
               unchanged (256)
               }
   MAX-ACCESS  read-write
   STATUS      current
   DESCRIPTION
      "Path: ethernet2.editConf.vlan.inboundBandwidth.action.cirAction.ethernet.cosDepth8

       Possibilities:
               unchanged   (256)"
   ::= {er1645v2Lan2FGVlanEntry 133318656}

er1645v2Lan2FGVlanInbBwActCirActEthDei8 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth8

       Possibilities:
               unchanged   (255)
               clear   (0)
               set   (1)"
   ::= {er1645v2Lan2FGVlanEntry 133323776}

er1645v2Lan2FGVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 133318912}

er1645v2Lan2FGVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 133319168}

er1645v2Lan2FGVlanInbBwActCirActEthDrpLev OBJECT-TYPE
   SYNTAX      INTEGER
               {
               unchanged (0)
               }
   MAX-ACCESS  read-write
   STATUS      current
   DESCRIPTION
      "Path: ethernet2.editConf.vlan.inboundBandwidth.action.cirAction.ethernet.dropLevel

       Possibilities:
               unchanged   (0)"
   ::= {er1645v2Lan2FGVlanEntry 133319424}

er1645v2Lan2FGVlanInbBwActCirActEthDeFlag OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deFlag

       Possibilities:
               unchanged   (255)
               clear   (0)
               set   (1)"
   ::= {er1645v2Lan2FGVlanEntry 133320192}

er1645v2Lan2FGVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 133343488}

er1645v2Lan2FGVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 133343744}

er1645v2Lan2FGVlanInbBwActCirActIpDrpLev OBJECT-TYPE
   SYNTAX      INTEGER
               {
               unchanged (0)
               }
   MAX-ACCESS  read-write
   STATUS      current
   DESCRIPTION
      "Path: ethernet2.editConf.vlan.inboundBandwidth.action.cirAction.ip.dropLevel

       Possibilities:
               unchanged   (0)"
   ::= {er1645v2Lan2FGVlanEntry 133344000}

er1645v2Lan2FGVlanInbBwActCirActIpDeFlag OBJECT-TYPE
   SYNTAX      INTEGER
               {
               unchanged (255),
               clear (0),
               set (1)
               }
   MAX-ACCESS  read-write
   STATUS      current
   DESCRIPTION
      "Path: ethernet2.editConf.vlan.inboundBandwidth.action.cirAction.ip.deFlag

       Possibilities:
               unchanged   (255)
               clear   (0)
               set   (1)"
   ::= {er1645v2Lan2FGVlanEntry 133344768}

er1645v2Lan2FGVlanInbBwActEirActNone OBJECT-TYPE
   SYNTAX      OCTET STRING
   MAX-ACCESS  read-write
   STATUS      current
   DESCRIPTION
      "Path: ethernet2.editConf.vlan.inboundBandwidth.action.eirAction.none"
   ::= {er1645v2Lan2FGVlanEntry 133439488}

er1645v2Lan2FGVlanInbBwActEirActEthCos1 OBJECT-TYPE
   SYNTAX      INTEGER
               {
               unchanged (256)
               }
   MAX-ACCESS  read-write
   STATUS      current
   DESCRIPTION
      "Path: ethernet2.editConf.vlan.inboundBandwidth.action.eirAction.ethernet.cosDepth1

       Possibilities:
               unchanged   (256)"
   ::= {er1645v2Lan2FGVlanEntry 133447936}

er1645v2Lan2FGVlanInbBwActEirActEthDei1 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth1

       Possibilities:
               unchanged   (255)
               clear   (0)
               set   (1)"
   ::= {er1645v2Lan2FGVlanEntry 133453056}

er1645v2Lan2FGVlanInbBwActEirActEthCos2 OBJECT-TYPE
   SYNTAX      INTEGER
               {
               unchanged (256)
               }
   MAX-ACCESS  read-write
   STATUS      current
   DESCRIPTION
      "Path: ethernet2.editConf.vlan.inboundBandwidth.action.eirAction.ethernet.cosDepth2

       Possibilities:
               unchanged   (256)"
   ::= {er1645v2Lan2FGVlanEntry 133448192}

er1645v2Lan2FGVlanInbBwActEirActEthDei2 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth2

       Possibilities:
               unchanged   (255)
               clear   (0)
               set   (1)"
   ::= {er1645v2Lan2FGVlanEntry 133453312}

er1645v2Lan2FGVlanInbBwActEirActEthCos3 OBJECT-TYPE
   SYNTAX      INTEGER
               {
               unchanged (256)
               }
   MAX-ACCESS  read-write
   STATUS      current
   DESCRIPTION
      "Path: ethernet2.editConf.vlan.inboundBandwidth.action.eirAction.ethernet.cosDepth3

       Possibilities:
               unchanged   (256)"
   ::= {er1645v2Lan2FGVlanEntry 133448448}

er1645v2Lan2FGVlanInbBwActEirActEthDei3 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth3

       Possibilities:
               unchanged   (255)
               clear   (0)
               set   (1)"
   ::= {er1645v2Lan2FGVlanEntry 133453568}

er1645v2Lan2FGVlanInbBwActEirActEthCos4 OBJECT-TYPE
   SYNTAX      INTEGER
               {
               unchanged (256)
               }
   MAX-ACCESS  read-write
   STATUS      current
   DESCRIPTION
      "Path: ethernet2.editConf.vlan.inboundBandwidth.action.eirAction.ethernet.cosDepth4

       Possibilities:
               unchanged   (256)"
   ::= {er1645v2Lan2FGVlanEntry 133448704}

er1645v2Lan2FGVlanInbBwActEirActEthDei4 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth4

       Possibilities:
               unchanged   (255)
               clear   (0)
               set   (1)"
   ::= {er1645v2Lan2FGVlanEntry 133453824}

er1645v2Lan2FGVlanInbBwActEirActEthCos5 OBJECT-TYPE
   SYNTAX      INTEGER
               {
               unchanged (256)
               }
   MAX-ACCESS  read-write
   STATUS      current
   DESCRIPTION
      "Path: ethernet2.editConf.vlan.inboundBandwidth.action.eirAction.ethernet.cosDepth5

       Possibilities:
               unchanged   (256)"
   ::= {er1645v2Lan2FGVlanEntry 133448960}

er1645v2Lan2FGVlanInbBwActEirActEthDei5 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth5

       Possibilities:
               unchanged   (255)
               clear   (0)
               set   (1)"
   ::= {er1645v2Lan2FGVlanEntry 133454080}

er1645v2Lan2FGVlanInbBwActEirActEthCos6 OBJECT-TYPE
   SYNTAX      INTEGER
               {
               unchanged (256)
               }
   MAX-ACCESS  read-write
   STATUS      current
   DESCRIPTION
      "Path: ethernet2.editConf.vlan.inboundBandwidth.action.eirAction.ethernet.cosDepth6

       Possibilities:
               unchanged   (256)"
   ::= {er1645v2Lan2FGVlanEntry 133449216}

er1645v2Lan2FGVlanInbBwActEirActEthDei6 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth6

       Possibilities:
               unchanged   (255)
               clear   (0)
               set   (1)"
   ::= {er1645v2Lan2FGVlanEntry 133454336}

er1645v2Lan2FGVlanInbBwActEirActEthCos7 OBJECT-TYPE
   SYNTAX      INTEGER
               {
               unchanged (256)
               }
   MAX-ACCESS  read-write
   STATUS      current
   DESCRIPTION
      "Path: ethernet2.editConf.vlan.inboundBandwidth.action.eirAction.ethernet.cosDepth7

       Possibilities:
               unchanged   (256)"
   ::= {er1645v2Lan2FGVlanEntry 133449472}

er1645v2Lan2FGVlanInbBwActEirActEthDei7 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth7

       Possibilities:
               unchanged   (255)
               clear   (0)
               set   (1)"
   ::= {er1645v2Lan2FGVlanEntry 133454592}

er1645v2Lan2FGVlanInbBwActEirActEthCos8 OBJECT-TYPE
   SYNTAX      INTEGER
               {
               unchanged (256)
               }
   MAX-ACCESS  read-write
   STATUS      current
   DESCRIPTION
      "Path: ethernet2.editConf.vlan.inboundBandwidth.action.eirAction.ethernet.cosDepth8

       Possibilities:
               unchanged   (256)"
   ::= {er1645v2Lan2FGVlanEntry 133449728}

er1645v2Lan2FGVlanInbBwActEirActEthDei8 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth8

       Possibilities:
               unchanged   (255)
               clear   (0)
               set   (1)"
   ::= {er1645v2Lan2FGVlanEntry 133454848}

er1645v2Lan2FGVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 133449984}

er1645v2Lan2FGVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 133450240}

er1645v2Lan2FGVlanInbBwActEirActEthDrpLev OBJECT-TYPE
   SYNTAX      INTEGER
               {
               unchanged (0)
               }
   MAX-ACCESS  read-write
   STATUS      current
   DESCRIPTION
      "Path: ethernet2.editConf.vlan.inboundBandwidth.action.eirAction.ethernet.dropLevel

       Possibilities:
               unchanged   (0)"
   ::= {er1645v2Lan2FGVlanEntry 133450496}

er1645v2Lan2FGVlanInbBwActEirActEthDeFlag OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deFlag

       Possibilities:
               unchanged   (255)
               clear   (0)
               set   (1)"
   ::= {er1645v2Lan2FGVlanEntry 133451264}

er1645v2Lan2FGVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 133474560}

er1645v2Lan2FGVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 133474816}

er1645v2Lan2FGVlanInbBwActEirActIpDrpLev OBJECT-TYPE
   SYNTAX      INTEGER
               {
               unchanged (0)
               }
   MAX-ACCESS  read-write
   STATUS      current
   DESCRIPTION
      "Path: ethernet2.editConf.vlan.inboundBandwidth.action.eirAction.ip.dropLevel

       Possibilities:
               unchanged   (0)"
   ::= {er1645v2Lan2FGVlanEntry 133475072}

er1645v2Lan2FGVlanInbBwActEirActIpDeFlag OBJECT-TYPE
   SYNTAX      INTEGER
               {
               unchanged (255),
               clear (0),
               set (1)
               }
   MAX-ACCESS  read-write
   STATUS      current
   DESCRIPTION
      "Path: ethernet2.editConf.vlan.inboundBandwidth.action.eirAction.ip.deFlag

       Possibilities:
               unchanged   (255)
               clear   (0)
               set   (1)"
   ::= {er1645v2Lan2FGVlanEntry 133475840}

er1645v2Lan2FGVlanInbBwActViolActNone OBJECT-TYPE
   SYNTAX      OCTET STRING
   MAX-ACCESS  read-write
   STATUS      current
   DESCRIPTION
      "Path: ethernet2.editConf.vlan.inboundBandwidth.action.violateAction.none"
   ::= {er1645v2Lan2FGVlanEntry 133570560}

er1645v2Lan2FGVlanInbBwActViolActDrop OBJECT-TYPE
   SYNTAX      OCTET STRING
   MAX-ACCESS  read-write
   STATUS      current
   DESCRIPTION
      "Path: ethernet2.editConf.vlan.inboundBandwidth.action.violateAction.drop"
   ::= {er1645v2Lan2FGVlanEntry 133586944}

er1645v2Lan2FGVlanInbBwActViolActEthCos1 OBJECT-TYPE
   SYNTAX      INTEGER
               {
               unchanged (256)
               }
   MAX-ACCESS  read-write
   STATUS      current
   DESCRIPTION
      "Path: ethernet2.editConf.vlan.inboundBandwidth.action.violateAction.ethernet.cosDepth1

       Possibilities:
               unchanged   (256)"
   ::= {er1645v2Lan2FGVlanEntry 133579008}

er1645v2Lan2FGVlanInbBwActViolActEthDei1 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth1

       Possibilities:
               unchanged   (255)
               clear   (0)
               set   (1)"
   ::= {er1645v2Lan2FGVlanEntry 133584128}

er1645v2Lan2FGVlanInbBwActViolActEthCos2 OBJECT-TYPE
   SYNTAX      INTEGER
               {
               unchanged (256)
               }
   MAX-ACCESS  read-write
   STATUS      current
   DESCRIPTION
      "Path: ethernet2.editConf.vlan.inboundBandwidth.action.violateAction.ethernet.cosDepth2

       Possibilities:
               unchanged   (256)"
   ::= {er1645v2Lan2FGVlanEntry 133579264}

er1645v2Lan2FGVlanInbBwActViolActEthDei2 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth2

       Possibilities:
               unchanged   (255)
               clear   (0)
               set   (1)"
   ::= {er1645v2Lan2FGVlanEntry 133584384}

er1645v2Lan2FGVlanInbBwActViolActEthCos3 OBJECT-TYPE
   SYNTAX      INTEGER
               {
               unchanged (256)
               }
   MAX-ACCESS  read-write
   STATUS      current
   DESCRIPTION
      "Path: ethernet2.editConf.vlan.inboundBandwidth.action.violateAction.ethernet.cosDepth3

       Possibilities:
               unchanged   (256)"
   ::= {er1645v2Lan2FGVlanEntry 133579520}

er1645v2Lan2FGVlanInbBwActViolActEthDei3 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth3

       Possibilities:
               unchanged   (255)
               clear   (0)
               set   (1)"
   ::= {er1645v2Lan2FGVlanEntry 133584640}

er1645v2Lan2FGVlanInbBwActViolActEthCos4 OBJECT-TYPE
   SYNTAX      INTEGER
               {
               unchanged (256)
               }
   MAX-ACCESS  read-write
   STATUS      current
   DESCRIPTION
      "Path: ethernet2.editConf.vlan.inboundBandwidth.action.violateAction.ethernet.cosDepth4

       Possibilities:
               unchanged   (256)"
   ::= {er1645v2Lan2FGVlanEntry 133579776}

er1645v2Lan2FGVlanInbBwActViolActEthDei4 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth4

       Possibilities:
               unchanged   (255)
               clear   (0)
               set   (1)"
   ::= {er1645v2Lan2FGVlanEntry 133584896}

er1645v2Lan2FGVlanInbBwActViolActEthCos5 OBJECT-TYPE
   SYNTAX      INTEGER
               {
               unchanged (256)
               }
   MAX-ACCESS  read-write
   STATUS      current
   DESCRIPTION
      "Path: ethernet2.editConf.vlan.inboundBandwidth.action.violateAction.ethernet.cosDepth5

       Possibilities:
               unchanged   (256)"
   ::= {er1645v2Lan2FGVlanEntry 133580032}

er1645v2Lan2FGVlanInbBwActViolActEthDei5 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth5

       Possibilities:
               unchanged   (255)
               clear   (0)
               set   (1)"
   ::= {er1645v2Lan2FGVlanEntry 133585152}

er1645v2Lan2FGVlanInbBwActViolActEthCos6 OBJECT-TYPE
   SYNTAX      INTEGER
               {
               unchanged (256)
               }
   MAX-ACCESS  read-write
   STATUS      current
   DESCRIPTION
      "Path: ethernet2.editConf.vlan.inboundBandwidth.action.violateAction.ethernet.cosDepth6

       Possibilities:
               unchanged   (256)"
   ::= {er1645v2Lan2FGVlanEntry 133580288}

er1645v2Lan2FGVlanInbBwActViolActEthDei6 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth6

       Possibilities:
               unchanged   (255)
               clear   (0)
               set   (1)"
   ::= {er1645v2Lan2FGVlanEntry 133585408}

er1645v2Lan2FGVlanInbBwActViolActEthCos7 OBJECT-TYPE
   SYNTAX      INTEGER
               {
               unchanged (256)
               }
   MAX-ACCESS  read-write
   STATUS      current
   DESCRIPTION
      "Path: ethernet2.editConf.vlan.inboundBandwidth.action.violateAction.ethernet.cosDepth7

       Possibilities:
               unchanged   (256)"
   ::= {er1645v2Lan2FGVlanEntry 133580544}

er1645v2Lan2FGVlanInbBwActViolActEthDei7 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth7

       Possibilities:
               unchanged   (255)
               clear   (0)
               set   (1)"
   ::= {er1645v2Lan2FGVlanEntry 133585664}

er1645v2Lan2FGVlanInbBwActViolActEthCos8 OBJECT-TYPE
   SYNTAX      INTEGER
               {
               unchanged (256)
               }
   MAX-ACCESS  read-write
   STATUS      current
   DESCRIPTION
      "Path: ethernet2.editConf.vlan.inboundBandwidth.action.violateAction.ethernet.cosDepth8

       Possibilities:
               unchanged   (256)"
   ::= {er1645v2Lan2FGVlanEntry 133580800}

er1645v2Lan2FGVlanInbBwActViolActEthDei8 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth8

       Possibilities:
               unchanged   (255)
               clear   (0)
               set   (1)"
   ::= {er1645v2Lan2FGVlanEntry 133585920}

er1645v2Lan2FGVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 133581056}

er1645v2Lan2FGVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 133581312}

er1645v2Lan2FGVlanInbBwActViolActEthDrpLev OBJECT-TYPE
   SYNTAX      INTEGER
               {
               unchanged (0)
               }
   MAX-ACCESS  read-write
   STATUS      current
   DESCRIPTION
      "Path: ethernet2.editConf.vlan.inboundBandwidth.action.violateAction.ethernet.dropLevel

       Possibilities:
               unchanged   (0)"
   ::= {er1645v2Lan2FGVlanEntry 133581568}

er1645v2Lan2FGVlanInbBwActViolActEthDeFlag OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deFlag

       Possibilities:
               unchanged   (255)
               clear   (0)
               set   (1)"
   ::= {er1645v2Lan2FGVlanEntry 133582336}

er1645v2Lan2FGVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanEntry 133605632}

er1645v2Lan2FGVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanEntry 133605888}

er1645v2Lan2FGVlanInbBwActViolActIpDrpLev OBJECT-TYPE
   SYNTAX      INTEGER
               {
               unchanged (0)
               }
   MAX-ACCESS  read-write
   STATUS      current
   DESCRIPTION
      "Path: ethernet2.editConf.vlan.inboundBandwidth.action.violateAction.ip.dropLevel

       Possibilities:
               unchanged   (0)"
   ::= {er1645v2Lan2FGVlanEntry 133606144}

er1645v2Lan2FGVlanInbBwActViolActIpDeFlag OBJECT-TYPE
   SYNTAX      INTEGER
               {
               unchanged (255),
               clear (0),
               set (1)
               }
   MAX-ACCESS  read-write
   STATUS      current
   DESCRIPTION
      "Path: ethernet2.editConf.vlan.inboundBandwidth.action.violateAction.ip.deFlag

       Possibilities:
               unchanged   (255)
               clear   (0)
               set   (1)"
   ::= {er1645v2Lan2FGVlanEntry 133606912}

er1645v2Lan2FGVlanPppoE OBJECT-TYPE
   SYNTAX      INTEGER
               {
               disabled (0),
               enabled (1)
               }
   MAX-ACCESS  read-write
   STATUS      current
   DESCRIPTION
      "Path: ethernet2.editConf.vlan.pppoE

       Possibilities:
               disabled   (0)
               enabled   (1)"
   ::= {er1645v2Lan2FGVlanEntry 838860800}

er1645v2Lan2FGVlanPppLnkMOperation OBJECT-TYPE
   SYNTAX      INTEGER
               {
               disabled (0),
               enabled (1)
               }
   MAX-ACCESS  read-write
   STATUS      current
   DESCRIPTION
      "Path: ethernet2.editConf.vlan.ppp.linkMonitoring.operation

       Possibilities:
               disabled   (0)
               enabled   (1)"
   ::= {er1645v2Lan2FGVlanEntry 251724032}

er1645v2Lan2FGVlanPppLnkMInterval OBJECT-TYPE
   SYNTAX      TimeTicks
   MAX-ACCESS  read-write
   STATUS      current
   DESCRIPTION
      "Path: ethernet2.editConf.vlan.ppp.linkMonitoring.interval

       Time in centi-second."
   ::= {er1645v2Lan2FGVlanEntry 251724288}

er1645v2Lan2FGVlanPppLnkMRepTimeOut OBJECT-TYPE
   SYNTAX      TimeTicks
   MAX-ACCESS  read-write
   STATUS      current
   DESCRIPTION
      "Path: ethernet2.editConf.vlan.ppp.linkMonitoring.replyTimeOut

       Time in centi-second."
   ::= {er1645v2Lan2FGVlanEntry 251724544}

er1645v2Lan2FGVlanPppLnkMFailsPrmt OBJECT-TYPE
   SYNTAX      Integer32
   MAX-ACCESS  read-write
   STATUS      current
   DESCRIPTION
      "Path: ethernet2.editConf.vlan.ppp.linkMonitoring.failsPermitted"
   ::= {er1645v2Lan2FGVlanEntry 251724800}

er1645v2Lan2FGVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet2.editConf.vlan.ppp.authentication

       Possibilities:
               disabled   (0)
               chap   (1)
               pap   (2)
               chapOrPap   (3)
               msChap   (4)
               msChapV2   (5)"
   ::= {er1645v2Lan2FGVlanEntry 251789312}

er1645v2Lan2FGVlanPppAuthenPeriod OBJECT-TYPE
   SYNTAX      TimeTicks
   MAX-ACCESS  read-write
   STATUS      current
   DESCRIPTION
      "Path: ethernet2.editConf.vlan.ppp.authenPeriod

       Time in centi-second."
   ::= {er1645v2Lan2FGVlanEntry 251854848}

er1645v2Lan2FGVlanPppSessionName OBJECT-TYPE
   SYNTAX      DisplayString
   MAX-ACCESS  read-write
   STATUS      current
   DESCRIPTION
      "Path: ethernet2.editConf.vlan.ppp.sessionName"
   ::= {er1645v2Lan2FGVlanEntry 251985920}

er1645v2Lan2FGVlanPppSessionSecret OBJECT-TYPE
   SYNTAX      DisplayString
   MAX-ACCESS  read-write
   STATUS      current
   DESCRIPTION
      "Path: ethernet2.editConf.vlan.ppp.sessionSecret"
   ::= {er1645v2Lan2FGVlanEntry 252051456}

er1645v2Lan2FGVlanPppEncModeSessionSecret OBJECT-TYPE
   SYNTAX      INTEGER
               {
               none (1),
               encrypt (2),
               encType1 (3),
               invalid (128)
               }
   MAX-ACCESS  read-write
   STATUS      current
   DESCRIPTION
      "Path: ethernet2.editConf.vlan.ppp.encModeSessionSecret

       Possibilities:
               none   (1)
               encrypt   (2)
               encType1   (3)
               invalid   (128)"
   ::= {er1645v2Lan2FGVlanEntry 252182528}

er1645v2Lan2FGVlanPppEncSessionSecret OBJECT-TYPE
   SYNTAX      DisplayString
   MAX-ACCESS  read-write
   STATUS      current
   DESCRIPTION
      "Path: ethernet2.editConf.vlan.ppp.encSessionSecret"
   ::= {er1645v2Lan2FGVlanEntry 252248064}

er1645v2Lan2FGVlanPppServiceName OBJECT-TYPE
   SYNTAX      DisplayString
   MAX-ACCESS  read-write
   STATUS      current
   DESCRIPTION
      "Path: ethernet2.editConf.vlan.ppp.serviceName"
   ::= {er1645v2Lan2FGVlanEntry 252116992}

er1645v2Lan2FGVlanPbbMode OBJECT-TYPE
   SYNTAX      INTEGER
               {
               disabled (0),
               static (1),
               dynamicPtp (2),
               dynamicPtmp (3)
               }
   MAX-ACCESS  read-write
   STATUS      current
   DESCRIPTION
      "Path: ethernet2.editConf.vlan.pbb.mode

       Possibilities:
               disabled   (0)
               static   (1)
               dynamicPtp   (2)
               dynamicPtmp   (3)"
   ::= {er1645v2Lan2FGVlanEntry 1174667264}

er1645v2Lan2FGVlanPbbTxCos OBJECT-TYPE
   SYNTAX      Integer32
   MAX-ACCESS  read-write
   STATUS      current
   DESCRIPTION
      "Path: ethernet2.editConf.vlan.pbb.txCos"
   ::= {er1645v2Lan2FGVlanEntry 1175191552}

er1645v2Lan2FGVlanPbbIsid OBJECT-TYPE
   SYNTAX      Integer32
   MAX-ACCESS  read-write
   STATUS      current
   DESCRIPTION
      "Path: ethernet2.editConf.vlan.pbb.isid"
   ::= {er1645v2Lan2FGVlanEntry 1175453696}

er1645v2Lan2FGVlanPbbDestMac OBJECT-TYPE
   SYNTAX      OCTET STRING
   MAX-ACCESS  read-write
   STATUS      current
   DESCRIPTION
      "Path: ethernet2.editConf.vlan.pbb.destMac

       MAC address."
   ::= {er1645v2Lan2FGVlanEntry 1175715840}

er1645v2Lan2FGVlanPbbCustomGroupMac OBJECT-TYPE
   SYNTAX      OCTET STRING
   MAX-ACCESS  read-write
   STATUS      current
   DESCRIPTION
      "Path: ethernet2.editConf.vlan.pbb.customGroupMac

       MAC address."
   ::= {er1645v2Lan2FGVlanEntry 1175977984}

er1645v2Lan2FGVlanIpSaddr OBJECT-TYPE
   SYNTAX      SEQUENCE OF Er1645v2Lan2FGVlanIpSaddrEntry
   MAX-ACCESS  not-accessible
   STATUS      current
   DESCRIPTION
      ""
   ::= {er1645v2Lan2FGVlan 51838976}

er1645v2Lan2FGVlanIpSaddrEntry OBJECT-TYPE
   SYNTAX      Er1645v2Lan2FGVlanIpSaddrEntry
   MAX-ACCESS  not-accessible
   STATUS      current
   DESCRIPTION
      ""
   INDEX      { er1645v2Lan2FGVlanTableIx,
                er1645v2Lan2FGVlanIpSaddrTableIx }
   ::= {er1645v2Lan2FGVlanIpSaddr 1}

Er1645v2Lan2FGVlanIpSaddrEntry ::=
   SEQUENCE
      {
      er1645v2Lan2FGVlanIpSaddrActions
         VariableLengthTableActions,
      er1645v2Lan2FGVlanIpSaddrTableIx
         TableIndex,
      er1645v2Lan2FGVlanIpSaddrAddress
         IpAddress,
      er1645v2Lan2FGVlanIpSaddrNetMask
         IpAddress
      }

er1645v2Lan2FGVlanIpSaddrActions OBJECT-TYPE
   SYNTAX      VariableLengthTableActions
   MAX-ACCESS  read-write
   STATUS      current
   DESCRIPTION
      "By way of this field, some manipulations
       on this table may be performed."
   ::= {er1645v2Lan2FGVlanIpSaddrEntry 2}

er1645v2Lan2FGVlanIpSaddrTableIx OBJECT-TYPE
   SYNTAX      TableIndex
   MAX-ACCESS  not-accessible
   STATUS      current
   DESCRIPTION
      ""
   ::= {er1645v2Lan2FGVlanIpSaddrEntry 11}

er1645v2Lan2FGVlanIpSaddrAddress OBJECT-TYPE
   SYNTAX      IpAddress
   MAX-ACCESS  read-write
   STATUS      current
   DESCRIPTION
      "Path: ethernet2.editConf.vlan.ip.secondaryIp.address"
   ::= {er1645v2Lan2FGVlanIpSaddrEntry 2030043136}

er1645v2Lan2FGVlanIpSaddrNetMask OBJECT-TYPE
   SYNTAX      IpAddress
   MAX-ACCESS  read-write
   STATUS      current
   DESCRIPTION
      "Path: ethernet2.editConf.vlan.ip.secondaryIp.netMask"
   ::= {er1645v2Lan2FGVlanIpSaddrEntry 2063597568}

er1645v2Lan2FGVlanIpH OBJECT-TYPE
   SYNTAX      SEQUENCE OF Er1645v2Lan2FGVlanIpHEntry
   MAX-ACCESS  not-accessible
   STATUS      current
   DESCRIPTION
      ""
   ::= {er1645v2Lan2FGVlan 51314688}

er1645v2Lan2FGVlanIpHEntry OBJECT-TYPE
   SYNTAX      Er1645v2Lan2FGVlanIpHEntry
   MAX-ACCESS  not-accessible
   STATUS      current
   DESCRIPTION
      ""
   INDEX      { er1645v2Lan2FGVlanTableIx,
                er1645v2Lan2FGVlanIpHTableIx }
   ::= {er1645v2Lan2FGVlanIpH 1}

Er1645v2Lan2FGVlanIpHEntry ::=
   SEQUENCE
      {
      er1645v2Lan2FGVlanIpHActions
         VariableLengthTableActions,
      er1645v2Lan2FGVlanIpHTableIx
         TableIndex,
      er1645v2Lan2FGVlanIpHAddress
         IpAddress,
      er1645v2Lan2FGVlanIpHDhcpRelayOptionSubscriberId
         DisplayString
      }

er1645v2Lan2FGVlanIpHActions OBJECT-TYPE
   SYNTAX      VariableLengthTableActions
   MAX-ACCESS  read-write
   STATUS      current
   DESCRIPTION
      "By way of this field, some manipulations
       on this table may be performed."
   ::= {er1645v2Lan2FGVlanIpHEntry 2}

er1645v2Lan2FGVlanIpHTableIx OBJECT-TYPE
   SYNTAX      TableIndex
   MAX-ACCESS  not-accessible
   STATUS      current
   DESCRIPTION
      ""
   ::= {er1645v2Lan2FGVlanIpHEntry 11}

er1645v2Lan2FGVlanIpHAddress OBJECT-TYPE
   SYNTAX      IpAddress
   MAX-ACCESS  read-write
   STATUS      current
   DESCRIPTION
      "Path: ethernet2.editConf.vlan.ip.helpers.address"
   ::= {er1645v2Lan2FGVlanIpHEntry 16777216}

er1645v2Lan2FGVlanIpHDhcpRelayOptionSubscriberId OBJECT-TYPE
   SYNTAX      DisplayString
   MAX-ACCESS  read-write
   STATUS      current
   DESCRIPTION
      "Path: ethernet2.editConf.vlan.ip.helpers.dhcpRelayOption.subscriberId"
   ::= {er1645v2Lan2FGVlanIpHEntry 33947648}

er1645v2Lan2FGVlanIpV6Addresses OBJECT-TYPE
   SYNTAX      SEQUENCE OF Er1645v2Lan2FGVlanIpV6AddressesEntry
   MAX-ACCESS  not-accessible
   STATUS      current
   DESCRIPTION
      ""
   ::= {er1645v2Lan2FGVlan 704839680}

er1645v2Lan2FGVlanIpV6AddressesEntry OBJECT-TYPE
   SYNTAX      Er1645v2Lan2FGVlanIpV6AddressesEntry
   MAX-ACCESS  not-accessible
   STATUS      current
   DESCRIPTION
      ""
   INDEX      { er1645v2Lan2FGVlanTableIx,
                er1645v2Lan2FGVlanIpV6AddressesTableIx }
   ::= {er1645v2Lan2FGVlanIpV6Addresses 1}

Er1645v2Lan2FGVlanIpV6AddressesEntry ::=
   SEQUENCE
      {
      er1645v2Lan2FGVlanIpV6AddressesActions
         VariableLengthTableActions,
      er1645v2Lan2FGVlanIpV6AddressesTableIx
         TableIndex,
      er1645v2Lan2FGVlanIpV6AddressesType
         INTEGER,
      er1645v2Lan2FGVlanIpV6AddressesAddress
         Ipv6Address,
      er1645v2Lan2FGVlanIpV6AddressesPrefixLength
         Integer32,
      er1645v2Lan2FGVlanIpV6AddressesGeneralPrefix
         DisplayString,
      er1645v2Lan2FGVlanIpV6AddressesRaSend
         INTEGER,
      er1645v2Lan2FGVlanIpV6AddressesRaOnLinkFlag
         INTEGER,
      er1645v2Lan2FGVlanIpV6AddressesRaAutoFlag
         INTEGER,
      er1645v2Lan2FGVlanIpV6AddressesRaValidLifeTime
         TimeTicks,
      er1645v2Lan2FGVlanIpV6AddressesRaValidLTMode
         INTEGER,
      er1645v2Lan2FGVlanIpV6AddressesRaPrefLifeTime
         TimeTicks,
      er1645v2Lan2FGVlanIpV6AddressesRaPrefLTMode
         INTEGER
      }

er1645v2Lan2FGVlanIpV6AddressesActions OBJECT-TYPE
   SYNTAX      VariableLengthTableActions
   MAX-ACCESS  read-write
   STATUS      current
   DESCRIPTION
      "By way of this field, some manipulations
       on this table may be performed."
   ::= {er1645v2Lan2FGVlanIpV6AddressesEntry 2}

er1645v2Lan2FGVlanIpV6AddressesTableIx OBJECT-TYPE
   SYNTAX      TableIndex
   MAX-ACCESS  not-accessible
   STATUS      current
   DESCRIPTION
      ""
   ::= {er1645v2Lan2FGVlanIpV6AddressesEntry 11}

er1645v2Lan2FGVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.vlan.ipV6.addresses.type

       Possibilities:
               unicast   (0)
               eui64   (1)
               anycast   (2)
               linkLocal   (3)
               generalPrefix   (4)"
   ::= {er1645v2Lan2FGVlanIpV6AddressesEntry 50331648}

er1645v2Lan2FGVlanIpV6AddressesAddress OBJECT-TYPE
   SYNTAX      Ipv6Address
   MAX-ACCESS  read-write
   STATUS      current
   DESCRIPTION
      "Path: ethernet2.editConf.vlan.ipV6.addresses.address

       ipv6 address"
   ::= {er1645v2Lan2FGVlanIpV6AddressesEntry 16777216}

er1645v2Lan2FGVlanIpV6AddressesPrefixLength OBJECT-TYPE
   SYNTAX      Integer32
   MAX-ACCESS  read-write
   STATUS      current
   DESCRIPTION
      "Path: ethernet2.editConf.vlan.ipV6.addresses.prefixLength"
   ::= {er1645v2Lan2FGVlanIpV6AddressesEntry 33554432}

er1645v2Lan2FGVlanIpV6AddressesGeneralPrefix OBJECT-TYPE
   SYNTAX      DisplayString
   MAX-ACCESS  read-write
   STATUS      current
   DESCRIPTION
      "Path: ethernet2.editConf.vlan.ipV6.addresses.generalPrefix"
   ::= {er1645v2Lan2FGVlanIpV6AddressesEntry 83886080}

er1645v2Lan2FGVlanIpV6AddressesRaSend OBJECT-TYPE
   SYNTAX      INTEGER
               {
               disabled (0),
               enabled (1)
               }
   MAX-ACCESS  read-write
   STATUS      current
   DESCRIPTION
      "Path: ethernet2.editConf.vlan.ipV6.addresses.ra.send

       Possibilities:
               disabled   (0)
               enabled   (1)"
   ::= {er1645v2Lan2FGVlanIpV6AddressesEntry 67174400}

er1645v2Lan2FGVlanIpV6AddressesRaOnLinkFlag OBJECT-TYPE
   SYNTAX      INTEGER
               {
               disabled (0),
               enabled (1)
               }
   MAX-ACCESS  read-write
   STATUS      current
   DESCRIPTION
      "Path: ethernet2.editConf.vlan.ipV6.addresses.ra.onLinkFlag

       Possibilities:
               disabled   (0)
               enabled   (1)"
   ::= {er1645v2Lan2FGVlanIpV6AddressesEntry 67371008}

er1645v2Lan2FGVlanIpV6AddressesRaAutoFlag OBJECT-TYPE
   SYNTAX      INTEGER
               {
               disabled (0),
               enabled (1)
               }
   MAX-ACCESS  read-write
   STATUS      current
   DESCRIPTION
      "Path: ethernet2.editConf.vlan.ipV6.addresses.ra.autonomousFlag

       Possibilities:
               disabled   (0)
               enabled   (1)"
   ::= {er1645v2Lan2FGVlanIpV6AddressesEntry 67567616}

er1645v2Lan2FGVlanIpV6AddressesRaValidLifeTime OBJECT-TYPE
   SYNTAX      TimeTicks
   MAX-ACCESS  read-write
   STATUS      current
   DESCRIPTION
      "Path: ethernet2.editConf.vlan.ipV6.addresses.ra.validLifeTime

       Time in centi-second."
   ::= {er1645v2Lan2FGVlanIpV6AddressesEntry 67239936}

er1645v2Lan2FGVlanIpV6AddressesRaValidLTMode OBJECT-TYPE
   SYNTAX      INTEGER
               {
               fixed (0),
               infinite (2)
               }
   MAX-ACCESS  read-write
   STATUS      current
   DESCRIPTION
      "Path: ethernet2.editConf.vlan.ipV6.addresses.ra.validLifeTimeMode

       Possibilities:
               fixed   (0)
               infinite   (2)"
   ::= {er1645v2Lan2FGVlanIpV6AddressesEntry 67305472}

er1645v2Lan2FGVlanIpV6AddressesRaPrefLifeTime OBJECT-TYPE
   SYNTAX      TimeTicks
   MAX-ACCESS  read-write
   STATUS      current
   DESCRIPTION
      "Path: ethernet2.editConf.vlan.ipV6.addresses.ra.prefLifeTime

       Time in centi-second."
   ::= {er1645v2Lan2FGVlanIpV6AddressesEntry 67436544}

er1645v2Lan2FGVlanIpV6AddressesRaPrefLTMode OBJECT-TYPE
   SYNTAX      INTEGER
               {
               fixed (0),
               infinite (2)
               }
   MAX-ACCESS  read-write
   STATUS      current
   DESCRIPTION
      "Path: ethernet2.editConf.vlan.ipV6.addresses.ra.prefLifeTimeMode

       Possibilities:
               fixed   (0)
               infinite   (2)"
   ::= {er1645v2Lan2FGVlanIpV6AddressesEntry 67502080}

er1645v2Lan2FGVlanIpV6RaDnsOptionsRdnssServers OBJECT-TYPE
   SYNTAX      SEQUENCE OF Er1645v2Lan2FGVlanIpV6RaDnsOptionsRdnssServersEntry
   MAX-ACCESS  not-accessible
   STATUS      current
   DESCRIPTION
      ""
   ::= {er1645v2Lan2FGVlan 705039144}

er1645v2Lan2FGVlanIpV6RaDnsOptionsRdnssServersEntry OBJECT-TYPE
   SYNTAX      Er1645v2Lan2FGVlanIpV6RaDnsOptionsRdnssServersEntry
   MAX-ACCESS  not-accessible
   STATUS      current
   DESCRIPTION
      ""
   INDEX      { er1645v2Lan2FGVlanTableIx,
                er1645v2Lan2FGVlanIpV6RaDnsOptionsRdnssServersTableIx }
   ::= {er1645v2Lan2FGVlanIpV6RaDnsOptionsRdnssServers 1}

Er1645v2Lan2FGVlanIpV6RaDnsOptionsRdnssServersEntry ::=
   SEQUENCE
      {
      er1645v2Lan2FGVlanIpV6RaDnsOptionsRdnssServersActions
         VariableLengthTableActions,
      er1645v2Lan2FGVlanIpV6RaDnsOptionsRdnssServersTableIx
         TableIndex,
      er1645v2Lan2FGVlanIpV6RaDnsOptionsRdnssServersAddress
         Ipv6Address
      }

er1645v2Lan2FGVlanIpV6RaDnsOptionsRdnssServersActions OBJECT-TYPE
   SYNTAX      VariableLengthTableActions
   MAX-ACCESS  read-write
   STATUS      current
   DESCRIPTION
      "By way of this field, some manipulations
       on this table may be performed."
   ::= {er1645v2Lan2FGVlanIpV6RaDnsOptionsRdnssServersEntry 2}

er1645v2Lan2FGVlanIpV6RaDnsOptionsRdnssServersTableIx OBJECT-TYPE
   SYNTAX      TableIndex
   MAX-ACCESS  not-accessible
   STATUS      current
   DESCRIPTION
      ""
   ::= {er1645v2Lan2FGVlanIpV6RaDnsOptionsRdnssServersEntry 11}

er1645v2Lan2FGVlanIpV6RaDnsOptionsRdnssServersAddress OBJECT-TYPE
   SYNTAX      Ipv6Address
   MAX-ACCESS  read-write
   STATUS      current
   DESCRIPTION
      "Path: ethernet2.editConf.vlan.ipV6.ra.dnsOptions.rdnss.servers.address

       ipv6 address"
   ::= {er1645v2Lan2FGVlanIpV6RaDnsOptionsRdnssServersEntry 16777216}

er1645v2Lan2FGVlanIpV6RaDnsOptionsDnsslDomains OBJECT-TYPE
   SYNTAX      SEQUENCE OF Er1645v2Lan2FGVlanIpV6RaDnsOptionsDnsslDomainsEntry
   MAX-ACCESS  not-accessible
   STATUS      current
   DESCRIPTION
      ""
   ::= {er1645v2Lan2FGVlan 705039176}

er1645v2Lan2FGVlanIpV6RaDnsOptionsDnsslDomainsEntry OBJECT-TYPE
   SYNTAX      Er1645v2Lan2FGVlanIpV6RaDnsOptionsDnsslDomainsEntry
   MAX-ACCESS  not-accessible
   STATUS      current
   DESCRIPTION
      ""
   INDEX      { er1645v2Lan2FGVlanTableIx,
                er1645v2Lan2FGVlanIpV6RaDnsOptionsDnsslDomainsTableIx }
   ::= {er1645v2Lan2FGVlanIpV6RaDnsOptionsDnsslDomains 1}

Er1645v2Lan2FGVlanIpV6RaDnsOptionsDnsslDomainsEntry ::=
   SEQUENCE
      {
      er1645v2Lan2FGVlanIpV6RaDnsOptionsDnsslDomainsActions
         VariableLengthTableActions,
      er1645v2Lan2FGVlanIpV6RaDnsOptionsDnsslDomainsTableIx
         TableIndex,
      er1645v2Lan2FGVlanIpV6RaDnsOptionsDnsslDomainsName
         DisplayString
      }

er1645v2Lan2FGVlanIpV6RaDnsOptionsDnsslDomainsActions OBJECT-TYPE
   SYNTAX      VariableLengthTableActions
   MAX-ACCESS  read-write
   STATUS      current
   DESCRIPTION
      "By way of this field, some manipulations
       on this table may be performed."
   ::= {er1645v2Lan2FGVlanIpV6RaDnsOptionsDnsslDomainsEntry 2}

er1645v2Lan2FGVlanIpV6RaDnsOptionsDnsslDomainsTableIx OBJECT-TYPE
   SYNTAX      TableIndex
   MAX-ACCESS  not-accessible
   STATUS      current
   DESCRIPTION
      ""
   ::= {er1645v2Lan2FGVlanIpV6RaDnsOptionsDnsslDomainsEntry 11}

er1645v2Lan2FGVlanIpV6RaDnsOptionsDnsslDomainsName OBJECT-TYPE
   SYNTAX      DisplayString
   MAX-ACCESS  read-write
   STATUS      current
   DESCRIPTION
      "Path: ethernet2.editConf.vlan.ipV6.ra.dnsOptions.dnssl.domains.name"
   ::= {er1645v2Lan2FGVlanIpV6RaDnsOptionsDnsslDomainsEntry 16777216}

er1645v2Lan2FGVlanIpV6DhcpClientUserClassOpt OBJECT-TYPE
   SYNTAX      SEQUENCE OF Er1645v2Lan2FGVlanIpV6DhcpClientUserClassOptEntry
   MAX-ACCESS  not-accessible
   STATUS      current
   DESCRIPTION
      ""
   ::= {er1645v2Lan2FGVlan 705312768}

er1645v2Lan2FGVlanIpV6DhcpClientUserClassOptEntry OBJECT-TYPE
   SYNTAX      Er1645v2Lan2FGVlanIpV6DhcpClientUserClassOptEntry
   MAX-ACCESS  not-accessible
   STATUS      current
   DESCRIPTION
      ""
   INDEX      { er1645v2Lan2FGVlanTableIx,
                er1645v2Lan2FGVlanIpV6DhcpClientUserClassOptTableIx }
   ::= {er1645v2Lan2FGVlanIpV6DhcpClientUserClassOpt 1}

Er1645v2Lan2FGVlanIpV6DhcpClientUserClassOptEntry ::=
   SEQUENCE
      {
      er1645v2Lan2FGVlanIpV6DhcpClientUserClassOptActions
         VariableLengthTableActions,
      er1645v2Lan2FGVlanIpV6DhcpClientUserClassOptTableIx
         TableIndex,
      er1645v2Lan2FGVlanIpV6DhcpClientUserClassOptValueAscii
         DisplayString,
      er1645v2Lan2FGVlanIpV6DhcpClientUserClassOptValueDecimal
         Integer32,
      er1645v2Lan2FGVlanIpV6DhcpClientUserClassOptValueHexData
         OCTET STRING
      }

er1645v2Lan2FGVlanIpV6DhcpClientUserClassOptActions OBJECT-TYPE
   SYNTAX      VariableLengthTableActions
   MAX-ACCESS  read-write
   STATUS      current
   DESCRIPTION
      "By way of this field, some manipulations
       on this table may be performed."
   ::= {er1645v2Lan2FGVlanIpV6DhcpClientUserClassOptEntry 2}

er1645v2Lan2FGVlanIpV6DhcpClientUserClassOptTableIx OBJECT-TYPE
   SYNTAX      TableIndex
   MAX-ACCESS  not-accessible
   STATUS      current
   DESCRIPTION
      ""
   ::= {er1645v2Lan2FGVlanIpV6DhcpClientUserClassOptEntry 11}

er1645v2Lan2FGVlanIpV6DhcpClientUserClassOptValueAscii OBJECT-TYPE
   SYNTAX      DisplayString
   MAX-ACCESS  read-write
   STATUS      current
   DESCRIPTION
      "Path: ethernet2.editConf.vlan.ipV6.dhcp.client.userClassOpt.value.ascii"
   ::= {er1645v2Lan2FGVlanIpV6DhcpClientUserClassOptEntry 16842752}

er1645v2Lan2FGVlanIpV6DhcpClientUserClassOptValueDecimal OBJECT-TYPE
   SYNTAX      Integer32
   MAX-ACCESS  read-write
   STATUS      current
   DESCRIPTION
      "Path: ethernet2.editConf.vlan.ipV6.dhcp.client.userClassOpt.value.decimal"
   ::= {er1645v2Lan2FGVlanIpV6DhcpClientUserClassOptEntry 16908288}

er1645v2Lan2FGVlanIpV6DhcpClientUserClassOptValueHexData OBJECT-TYPE
   SYNTAX      OCTET STRING
   MAX-ACCESS  read-write
   STATUS      current
   DESCRIPTION
      "Path: ethernet2.editConf.vlan.ipV6.dhcp.client.userClassOpt.value.hexData"
   ::= {er1645v2Lan2FGVlanIpV6DhcpClientUserClassOptEntry 16973824}

er1645v2Lan2FGVlanIpV6DhcpClientVendorCl OBJECT-TYPE
   SYNTAX      SEQUENCE OF Er1645v2Lan2FGVlanIpV6DhcpClientVendorClEntry
   MAX-ACCESS  not-accessible
   STATUS      current
   DESCRIPTION
      ""
   ::= {er1645v2Lan2FGVlan 705313792}

er1645v2Lan2FGVlanIpV6DhcpClientVendorClEntry OBJECT-TYPE
   SYNTAX      Er1645v2Lan2FGVlanIpV6DhcpClientVendorClEntry
   MAX-ACCESS  not-accessible
   STATUS      current
   DESCRIPTION
      ""
   INDEX      { er1645v2Lan2FGVlanTableIx,
                er1645v2Lan2FGVlanIpV6DhcpClientVendorClTableIx }
   ::= {er1645v2Lan2FGVlanIpV6DhcpClientVendorCl 1}

Er1645v2Lan2FGVlanIpV6DhcpClientVendorClEntry ::=
   SEQUENCE
      {
      er1645v2Lan2FGVlanIpV6DhcpClientVendorClActions
         VariableLengthTableActions,
      er1645v2Lan2FGVlanIpV6DhcpClientVendorClTableIx
         TableIndex,
      er1645v2Lan2FGVlanIpV6DhcpClientVendorClValueAscii
         DisplayString,
      er1645v2Lan2FGVlanIpV6DhcpClientVendorClValueDecimal
         Integer32,
      er1645v2Lan2FGVlanIpV6DhcpClientVendorClValueHexData
         OCTET STRING
      }

er1645v2Lan2FGVlanIpV6DhcpClientVendorClActions OBJECT-TYPE
   SYNTAX      VariableLengthTableActions
   MAX-ACCESS  read-write
   STATUS      current
   DESCRIPTION
      "By way of this field, some manipulations
       on this table may be performed."
   ::= {er1645v2Lan2FGVlanIpV6DhcpClientVendorClEntry 2}

er1645v2Lan2FGVlanIpV6DhcpClientVendorClTableIx OBJECT-TYPE
   SYNTAX      TableIndex
   MAX-ACCESS  not-accessible
   STATUS      current
   DESCRIPTION
      ""
   ::= {er1645v2Lan2FGVlanIpV6DhcpClientVendorClEntry 11}

er1645v2Lan2FGVlanIpV6DhcpClientVendorClValueAscii OBJECT-TYPE
   SYNTAX      DisplayString
   MAX-ACCESS  read-write
   STATUS      current
   DESCRIPTION
      "Path: ethernet2.editConf.vlan.ipV6.dhcp.client.vendorClassOpt.value.ascii"
   ::= {er1645v2Lan2FGVlanIpV6DhcpClientVendorClEntry 16842752}

er1645v2Lan2FGVlanIpV6DhcpClientVendorClValueDecimal OBJECT-TYPE
   SYNTAX      Integer32
   MAX-ACCESS  read-write
   STATUS      current
   DESCRIPTION
      "Path: ethernet2.editConf.vlan.ipV6.dhcp.client.vendorClassOpt.value.decimal"
   ::= {er1645v2Lan2FGVlanIpV6DhcpClientVendorClEntry 16908288}

er1645v2Lan2FGVlanIpV6DhcpClientVendorClValueHexData OBJECT-TYPE
   SYNTAX      OCTET STRING
   MAX-ACCESS  read-write
   STATUS      current
   DESCRIPTION
      "Path: ethernet2.editConf.vlan.ipV6.dhcp.client.vendorClassOpt.value.hexData"
   ::= {er1645v2Lan2FGVlanIpV6DhcpClientVendorClEntry 16973824}

er1645v2Lan2FGVlanIpV6DhcpRelayDestinations OBJECT-TYPE
   SYNTAX      SEQUENCE OF Er1645v2Lan2FGVlanIpV6DhcpRelayDestinationsEntry
   MAX-ACCESS  not-accessible
   STATUS      current
   DESCRIPTION
      ""
   ::= {er1645v2Lan2FGVlan 705323072}

er1645v2Lan2FGVlanIpV6DhcpRelayDestinationsEntry OBJECT-TYPE
   SYNTAX      Er1645v2Lan2FGVlanIpV6DhcpRelayDestinationsEntry
   MAX-ACCESS  not-accessible
   STATUS      current
   DESCRIPTION
      ""
   INDEX      { er1645v2Lan2FGVlanTableIx,
                er1645v2Lan2FGVlanIpV6DhcpRelayDestinationsTableIx }
   ::= {er1645v2Lan2FGVlanIpV6DhcpRelayDestinations 1}

Er1645v2Lan2FGVlanIpV6DhcpRelayDestinationsEntry ::=
   SEQUENCE
      {
      er1645v2Lan2FGVlanIpV6DhcpRelayDestinationsActions
         VariableLengthTableActions,
      er1645v2Lan2FGVlanIpV6DhcpRelayDestinationsTableIx
         TableIndex,
      er1645v2Lan2FGVlanIpV6DhcpRelayDestinationsAddress
         Ipv6Address,
      er1645v2Lan2FGVlanIpV6DhcpRelayDestinationsInterface
         DisplayString
      }

er1645v2Lan2FGVlanIpV6DhcpRelayDestinationsActions OBJECT-TYPE
   SYNTAX      VariableLengthTableActions
   MAX-ACCESS  read-write
   STATUS      current
   DESCRIPTION
      "By way of this field, some manipulations
       on this table may be performed."
   ::= {er1645v2Lan2FGVlanIpV6DhcpRelayDestinationsEntry 2}

er1645v2Lan2FGVlanIpV6DhcpRelayDestinationsTableIx OBJECT-TYPE
   SYNTAX      TableIndex
   MAX-ACCESS  not-accessible
   STATUS      current
   DESCRIPTION
      ""
   ::= {er1645v2Lan2FGVlanIpV6DhcpRelayDestinationsEntry 11}

er1645v2Lan2FGVlanIpV6DhcpRelayDestinationsAddress OBJECT-TYPE
   SYNTAX      Ipv6Address
   MAX-ACCESS  read-write
   STATUS      current
   DESCRIPTION
      "Path: ethernet2.editConf.vlan.ipV6.dhcp.relay.destinations.address

       ipv6 address"
   ::= {er1645v2Lan2FGVlanIpV6DhcpRelayDestinationsEntry 16777216}

er1645v2Lan2FGVlanIpV6DhcpRelayDestinationsInterface OBJECT-TYPE
   SYNTAX      DisplayString
   MAX-ACCESS  read-write
   STATUS      current
   DESCRIPTION
      "Path: ethernet2.editConf.vlan.ipV6.dhcp.relay.destinations.interface"
   ::= {er1645v2Lan2FGVlanIpV6DhcpRelayDestinationsEntry 33554432}

er1645v2Lan2FGVlanBridgingVlTVlans OBJECT-TYPE
   SYNTAX      SEQUENCE OF Er1645v2Lan2FGVlanBridgingVlTVlansEntry
   MAX-ACCESS  not-accessible
   STATUS      current
   DESCRIPTION
      ""
   ::= {er1645v2Lan2FGVlan 459079680}

er1645v2Lan2FGVlanBridgingVlTVlansEntry OBJECT-TYPE
   SYNTAX      Er1645v2Lan2FGVlanBridgingVlTVlansEntry
   MAX-ACCESS  not-accessible
   STATUS      current
   DESCRIPTION
      ""
   INDEX      { er1645v2Lan2FGVlanTableIx,
                er1645v2Lan2FGVlanBridgingVlTVlansTableIx }
   ::= {er1645v2Lan2FGVlanBridgingVlTVlans 1}

Er1645v2Lan2FGVlanBridgingVlTVlansEntry ::=
   SEQUENCE
      {
      er1645v2Lan2FGVlanBridgingVlTVlansActions
         VariableLengthTableActions,
      er1645v2Lan2FGVlanBridgingVlTVlansTableIx
         TableIndex,
      er1645v2Lan2FGVlanBridgingVlTVlansVid
         Integer32,
      er1645v2Lan2FGVlanBridgingVlTVlansEndVid
         Integer32,
      er1645v2Lan2FGVlanBridgingVlTVlansAction
         INTEGER,
      er1645v2Lan2FGVlanBridgingVlTVlansTagInfoTpid
         INTEGER,
      er1645v2Lan2FGVlanBridgingVlTVlansTagInfoVid
         Integer32
      }

er1645v2Lan2FGVlanBridgingVlTVlansActions OBJECT-TYPE
   SYNTAX      VariableLengthTableActions
   MAX-ACCESS  read-write
   STATUS      current
   DESCRIPTION
      "By way of this field, some manipulations
       on this table may be performed."
   ::= {er1645v2Lan2FGVlanBridgingVlTVlansEntry 2}

er1645v2Lan2FGVlanBridgingVlTVlansTableIx OBJECT-TYPE
   SYNTAX      TableIndex
   MAX-ACCESS  not-accessible
   STATUS      current
   DESCRIPTION
      ""
   ::= {er1645v2Lan2FGVlanBridgingVlTVlansEntry 11}

er1645v2Lan2FGVlanBridgingVlTVlansVid OBJECT-TYPE
   SYNTAX      Integer32
   MAX-ACCESS  read-write
   STATUS      current
   DESCRIPTION
      "Path: ethernet2.editConf.vlan.bridging.vlanTagging.vlans.vid"
   ::= {er1645v2Lan2FGVlanBridgingVlTVlansEntry 536870912}

er1645v2Lan2FGVlanBridgingVlTVlansEndVid OBJECT-TYPE
   SYNTAX      Integer32
   MAX-ACCESS  read-write
   STATUS      current
   DESCRIPTION
      "Path: ethernet2.editConf.vlan.bridging.vlanTagging.vlans.endVid"
   ::= {er1645v2Lan2FGVlanBridgingVlTVlansEntry 2147483648}

er1645v2Lan2FGVlanBridgingVlTVlansAction OBJECT-TYPE
   SYNTAX      INTEGER
               {
               discard (0),
               accept (1),
               tag (2)
               }
   MAX-ACCESS  read-write
   STATUS      current
   DESCRIPTION
      "Path: ethernet2.editConf.vlan.bridging.vlanTagging.vlans.action

       Possibilities:
               discard   (0)
               accept   (1)
               tag   (2)"
   ::= {er1645v2Lan2FGVlanBridgingVlTVlansEntry 1073741824}

er1645v2Lan2FGVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.vlans.tagInfo.tpid

       Possibilities:
               dot1Q   (33024)
               dot1ad   (34984)
               0x9100   (37120)
               0x9200   (37376)
               0x9300   (37632)"
   ::= {er1645v2Lan2FGVlanBridgingVlTVlansEntry 1677721600}

er1645v2Lan2FGVlanBridgingVlTVlansTagInfoVid OBJECT-TYPE
   SYNTAX      Integer32
   MAX-ACCESS  read-write
   STATUS      current
   DESCRIPTION
      "Path: ethernet2.editConf.vlan.bridging.vlanTagging.vlans.tagInfo.vid"
   ::= {er1645v2Lan2FGVlanBridgingVlTVlansEntry 1744830464}

er1645v2Lan2FGVlanVlanVidExtensionTable OBJECT-TYPE
   SYNTAX      SEQUENCE OF Er1645v2Lan2FGVlanVlanVidExtensionTableEntry
   MAX-ACCESS  not-accessible
   STATUS      current
   DESCRIPTION
      ""
   ::= {er1645v2Lan2FGVlan 235340544}

er1645v2Lan2FGVlanVlanVidExtensionTableEntry OBJECT-TYPE
   SYNTAX      Er1645v2Lan2FGVlanVlanVidExtensionTableEntry
   MAX-ACCESS  not-accessible
   STATUS      current
   DESCRIPTION
      ""
   INDEX      { er1645v2Lan2FGVlanTableIx,
                er1645v2Lan2FGVlanVlanVidExtensionTableTableIx }
   ::= {er1645v2Lan2FGVlanVlanVidExtensionTable 1}

Er1645v2Lan2FGVlanVlanVidExtensionTableEntry ::=
   SEQUENCE
      {
      er1645v2Lan2FGVlanVlanVidExtensionTableActions
         VariableLengthTableActions,
      er1645v2Lan2FGVlanVlanVidExtensionTableTableIx
         TableIndex,
      er1645v2Lan2FGVlanVlanVidExtensionTableTpid
         INTEGER,
      er1645v2Lan2FGVlanVlanVidExtensionTableVid
         Integer32,
      er1645v2Lan2FGVlanVlanVidExtensionTableEndVid
         Integer32
      }

er1645v2Lan2FGVlanVlanVidExtensionTableActions OBJECT-TYPE
   SYNTAX      VariableLengthTableActions
   MAX-ACCESS  read-write
   STATUS      current
   DESCRIPTION
      "By way of this field, some manipulations
       on this table may be performed."
   ::= {er1645v2Lan2FGVlanVlanVidExtensionTableEntry 2}

er1645v2Lan2FGVlanVlanVidExtensionTableTableIx OBJECT-TYPE
   SYNTAX      TableIndex
   MAX-ACCESS  not-accessible
   STATUS      current
   DESCRIPTION
      ""
   ::= {er1645v2Lan2FGVlanVlanVidExtensionTableEntry 11}

er1645v2Lan2FGVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.vidExtension.table.tpid

       Possibilities:
               dot1Q   (33024)
               dot1ad   (34984)
               0x9100   (37120)
               0x9200   (37376)
               0x9300   (37632)"
   ::= {er1645v2Lan2FGVlanVlanVidExtensionTableEntry 16777216}

er1645v2Lan2FGVlanVlanVidExtensionTableVid OBJECT-TYPE
   SYNTAX      Integer32
   MAX-ACCESS  read-write
   STATUS      current
   DESCRIPTION
      "Path: ethernet2.editConf.vlan.vlan.vidExtension.table.vid"
   ::= {er1645v2Lan2FGVlanVlanVidExtensionTableEntry 33554432}

er1645v2Lan2FGVlanVlanVidExtensionTableEndVid OBJECT-TYPE
   SYNTAX      Integer32
   MAX-ACCESS  read-write
   STATUS      current
   DESCRIPTION
      "Path: ethernet2.editConf.vlan.vlan.vidExtension.table.endVid"
   ::= {er1645v2Lan2FGVlanVlanVidExtensionTableEntry 50331648}

er1645v2Lan2FGVlanVlanCSMap OBJECT-TYPE
   SYNTAX      SEQUENCE OF Er1645v2Lan2FGVlanVlanCSMapEntry
   MAX-ACCESS  not-accessible
   STATUS      current
   DESCRIPTION
      ""
   ::= {er1645v2Lan2FGVlan 235405312}

er1645v2Lan2FGVlanVlanCSMapEntry OBJECT-TYPE
   SYNTAX      Er1645v2Lan2FGVlanVlanCSMapEntry
   MAX-ACCESS  not-accessible
   STATUS      current
   DESCRIPTION
      ""
   INDEX      { er1645v2Lan2FGVlanTableIx,
                er1645v2Lan2FGVlanVlanCSMapTableIx }
   ::= {er1645v2Lan2FGVlanVlanCSMap 1}

Er1645v2Lan2FGVlanVlanCSMapEntry ::=
   SEQUENCE
      {
      er1645v2Lan2FGVlanVlanCSMapActions
         VariableLengthTableActions,
      er1645v2Lan2FGVlanVlanCSMapTableIx
         TableIndex,
      er1645v2Lan2FGVlanVlanCSMapCos
         INTEGER,
      er1645v2Lan2FGVlanVlanCSMapDei
         INTEGER,
      er1645v2Lan2FGVlanVlanCSMapTos
         INTEGER,
      er1645v2Lan2FGVlanVlanCSMapQueue
         INTEGER,
      er1645v2Lan2FGVlanVlanCSMapDropLevel
         INTEGER,
      er1645v2Lan2FGVlanVlanCSMapDeFlag
         INTEGER
      }

er1645v2Lan2FGVlanVlanCSMapActions OBJECT-TYPE
   SYNTAX      VariableLengthTableActions
   MAX-ACCESS  read-write
   STATUS      current
   DESCRIPTION
      "By way of this field, some manipulations
       on this table may be performed."
   ::= {er1645v2Lan2FGVlanVlanCSMapEntry 2}

er1645v2Lan2FGVlanVlanCSMapTableIx OBJECT-TYPE
   SYNTAX      TableIndex
   MAX-ACCESS  not-accessible
   STATUS      current
   DESCRIPTION
      ""
   ::= {er1645v2Lan2FGVlanVlanCSMapEntry 11}

er1645v2Lan2FGVlanVlanCSMapCos OBJECT-TYPE
   SYNTAX      INTEGER
               {
               any (8)
               }
   MAX-ACCESS  read-write
   STATUS      current
   DESCRIPTION
      "Path: ethernet2.editConf.vlan.vlan.cosMap.cos

       Possibilities:
               any   (8)"
   ::= {er1645v2Lan2FGVlanVlanCSMapEntry 16777216}

er1645v2Lan2FGVlanVlanCSMapDei OBJECT-TYPE
   SYNTAX      INTEGER
               {
               clear (0),
               set (1),
               any (2)
               }
   MAX-ACCESS  read-write
   STATUS      current
   DESCRIPTION
      "Path: ethernet2.editConf.vlan.vlan.cosMap.dei

       Possibilities:
               clear   (0)
               set   (1)
               any   (2)"
   ::= {er1645v2Lan2FGVlanVlanCSMapEntry 33554432}

er1645v2Lan2FGVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2FGVlanVlanCSMapEntry 50331648}

er1645v2Lan2FGVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1645v2Lan2FGVlanVlanCSMapEntry 67108864}

er1645v2Lan2FGVlanVlanCSMapDropLevel OBJECT-TYPE
   SYNTAX      INTEGER
               {
               unchanged (-1),
               dropOnQueue (0)
               }
   MAX-ACCESS  read-write
   STATUS      current
   DESCRIPTION
      "Path: ethernet2.editConf.vlan.vlan.cosMap.dropLevel

       Possibilities:
               unchanged   (-1)
               dropOnQueue   (0)"
   ::= {er1645v2Lan2FGVlanVlanCSMapEntry 83886080}

er1645v2Lan2FGVlanVlanCSMapDeFlag OBJECT-TYPE
   SYNTAX      INTEGER
               {
               unchanged (255),
               clear (0),
               set (1)
               }
   MAX-ACCESS  read-write
   STATUS      current
   DESCRIPTION
      "Path: ethernet2.editConf.vlan.vlan.cosMap.deFlag

       Possibilities:
               unchanged   (255)
               clear   (0)
               set   (1)"
   ::= {er1645v2Lan2FGVlanVlanCSMapEntry 117440512}

er1645v2Lan2FGVlanVlanTCMap OBJECT-TYPE
   SYNTAX      SEQUENCE OF Er1645v2Lan2FGVlanVlanTCMapEntry
   MAX-ACCESS  not-accessible
   STATUS      current
   DESCRIPTION
      ""
   ::= {er1645v2Lan2FGVlan 241369088}

er1645v2Lan2FGVlanVlanTCMapEntry OBJECT-TYPE
   SYNTAX      Er1645v2Lan2FGVlanVlanTCMapEntry
   MAX-ACCESS  not-accessible
   STATUS      current
   DESCRIPTION
      ""
   INDEX      { er1645v2Lan2FGVlanTableIx,
                er1645v2Lan2FGVlanVlanTCMapTableIx }
   ::= {er1645v2Lan2FGVlanVlanTCMap 1}

Er1645v2Lan2FGVlanVlanTCMapEntry ::=
   SEQUENCE
      {
      er1645v2Lan2FGVlanVlanTCMapActions
         VariableLengthTableActions,
      er1645v2Lan2FGVlanVlanTCMapTableIx
         TableIndex,
      er1645v2Lan2FGVlanVlanTCMapStartTos
         INTEGER,
      er1645v2Lan2FGVlanVlanTCMapEndTos
         INTEGER,
      er1645v2Lan2FGVlanVlanTCMapCos
         INTEGER
      }

er1645v2Lan2FGVlanVlanTCMapActions OBJECT-TYPE
   SYNTAX      VariableLengthTableActions
   MAX-ACCESS  read-write
   STATUS      current
   DESCRIPTION
      "By way of this field, some manipulations
       on this table may be performed."
   ::= {er1645v2Lan2FGVlanVlanTCMapEntry 2}

er1645v2Lan2FGVlanVlanTCMapTableIx OBJECT-TYPE
   SYNTAX      TableIndex
   MAX-ACCESS  not-accessible
   STATUS      current
   DESCRIPTION
      ""
   ::= {er1645v2Lan2FGVlanVlanTCMapEntry 11}

er1645v2Lan2FGVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet2.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan2FGVlanVlanTCMapEntry 16777216}

er1645v2Lan2FGVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet2.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan2FGVlanVlanTCMapEntry 33554432}

er1645v2Lan2FGVlanVlanTCMapCos OBJECT-TYPE
   SYNTAX      INTEGER
               {
               queueCosMap (8)
               }
   MAX-ACCESS  read-write
   STATUS      current
   DESCRIPTION
      "Path: ethernet2.editConf.vlan.vlan.tosCosMap.cos

       Possibilities:
               queueCosMap   (8)"
   ::= {er1645v2Lan2FGVlanVlanTCMapEntry 50331648}

er1645v2Lan2FGVlanVlanArpStaticArp OBJECT-TYPE
   SYNTAX      SEQUENCE OF Er1645v2Lan2FGVlanVlanArpStaticArpEntry
   MAX-ACCESS  not-accessible
   STATUS      current
   DESCRIPTION
      ""
   ::= {er1645v2Lan2FGVlan 235275008}

er1645v2Lan2FGVlanVlanArpStaticArpEntry OBJECT-TYPE
   SYNTAX      Er1645v2Lan2FGVlanVlanArpStaticArpEntry
   MAX-ACCESS  not-accessible
   STATUS      current
   DESCRIPTION
      ""
   INDEX      { er1645v2Lan2FGVlanTableIx,
                er1645v2Lan2FGVlanVlanArpStaticArpTableIx }
   ::= {er1645v2Lan2FGVlanVlanArpStaticArp 1}

Er1645v2Lan2FGVlanVlanArpStaticArpEntry ::=
   SEQUENCE
      {
      er1645v2Lan2FGVlanVlanArpStaticArpActions
         VariableLengthTableActions,
      er1645v2Lan2FGVlanVlanArpStaticArpTableIx
         TableIndex,
      er1645v2Lan2FGVlanVlanArpStaticArpMacAddress
         OCTET STRING,
      er1645v2Lan2FGVlanVlanArpStaticArpIpAddress
         IpAddress
      }

er1645v2Lan2FGVlanVlanArpStaticArpActions OBJECT-TYPE
   SYNTAX      VariableLengthTableActions
   MAX-ACCESS  read-write
   STATUS      current
   DESCRIPTION
      "By way of this field, some manipulations
       on this table may be performed."
   ::= {er1645v2Lan2FGVlanVlanArpStaticArpEntry 2}

er1645v2Lan2FGVlanVlanArpStaticArpTableIx OBJECT-TYPE
   SYNTAX      TableIndex
   MAX-ACCESS  not-accessible
   STATUS      current
   DESCRIPTION
      ""
   ::= {er1645v2Lan2FGVlanVlanArpStaticArpEntry 11}

er1645v2Lan2FGVlanVlanArpStaticArpMacAddress OBJECT-TYPE
   SYNTAX      OCTET STRING
   MAX-ACCESS  read-write
   STATUS      current
   DESCRIPTION
      "Path: ethernet2.editConf.vlan.vlan.arp.staticArp.macAddress

       MAC address."
   ::= {er1645v2Lan2FGVlanVlanArpStaticArpEntry 16777216}

er1645v2Lan2FGVlanVlanArpStaticArpIpAddress OBJECT-TYPE
   SYNTAX      IpAddress
   MAX-ACCESS  read-write
   STATUS      current
   DESCRIPTION
      "Path: ethernet2.editConf.vlan.vlan.arp.staticArp.ipAddress"
   ::= {er1645v2Lan2FGVlanVlanArpStaticArpEntry 33554432}


er1645v2Lan2FGPppOE OBJECT IDENTIFIER ::= {er1645v2Lan2FG 35}

er1645v2Lan2FGPppOESSCTable OBJECT-TYPE
   SYNTAX      SEQUENCE OF Er1645v2Lan2FGPppOEEntry
   MAX-ACCESS  not-accessible
   STATUS      current
   DESCRIPTION
      ""
   ::= {er1645v2Lan2FGPppOE 1}

er1645v2Lan2FGPppOEEntry OBJECT-TYPE
   SYNTAX      Er1645v2Lan2FGPppOEEntry
   MAX-ACCESS  not-accessible
   STATUS      current
   DESCRIPTION
      ""
   INDEX      { er1645v2Lan2FGPppOETableIx }
   ::= {er1645v2Lan2FGPppOESSCTable 1}

Er1645v2Lan2FGPppOEEntry ::=
   SEQUENCE
      {
      er1645v2Lan2FGPppOEActions
         VariableLengthTableActions,
      er1645v2Lan2FGPppOETableIx
         TableIndex,
      er1645v2Lan2FGPppOEName
         DisplayString,
      er1645v2Lan2FGPppOERemark
         DisplayString,
      er1645v2Lan2FGPppOEAdminStatus
         INTEGER,
      er1645v2Lan2FGPppOEMode
         INTEGER,
      er1645v2Lan2FGPppOEIpVrfRouter
         DisplayString,
      er1645v2Lan2FGPppOEIpAdr
         IpAddress,
      er1645v2Lan2FGPppOEIpNetm
         IpAddress,
      er1645v2Lan2FGPppOEIpSNetName
         INTEGER,
      er1645v2Lan2FGPppOEIpSNetCust
         DisplayString,
      er1645v2Lan2FGPppOEIpRem
         IpAddress,
      er1645v2Lan2FGPppOEIpUnnumbered
         DisplayString,
      er1645v2Lan2FGPppOEIpGwPref
         Integer32,
      er1645v2Lan2FGPppOEIpRsn
         INTEGER,
      er1645v2Lan2FGPppOEIpMtu
         Integer32,
      er1645v2Lan2FGPppOEIpMssAdjust
         INTEGER,
      er1645v2Lan2FGPppOEIpRipMetric
         Integer32,
      er1645v2Lan2FGPppOEIpRipMetricOut
         Integer32,
      er1645v2Lan2FGPppOEIpRipMode
         INTEGER,
      er1645v2Lan2FGPppOEIpRipTxVer
         INTEGER,
      er1645v2Lan2FGPppOEIpRipRxVer
         INTEGER,
      er1645v2Lan2FGPppOEIpRipSplitH
         INTEGER,
      er1645v2Lan2FGPppOEIpRipAuth
         INTEGER,
      er1645v2Lan2FGPppOEIpRipFilter
         DisplayString,
      er1645v2Lan2FGPppOEIpRipFilterIn
         DisplayString,
      er1645v2Lan2FGPppOEIpRipClearNextHop
         INTEGER,
      er1645v2Lan2FGPppOEIpAccPol
         DisplayString,
      er1645v2Lan2FGPppOEIpAB
         DisplayString,
      er1645v2Lan2FGPppOEIpMA
         INTEGER,
      er1645v2Lan2FGPppOEIpMF
         Integer32,
      er1645v2Lan2FGPppOEIpDB
         INTEGER,
      er1645v2Lan2FGPppOEIpIR
         INTEGER,
      er1645v2Lan2FGPppOEIpIgmp
         INTEGER,
      er1645v2Lan2FGPppOEIpNN
         DisplayString,
      er1645v2Lan2FGPppOEIpPimMode
         INTEGER,
      er1645v2Lan2FGPppOEIpPimDrPriority
         Counter32,
      er1645v2Lan2FGPppOEIpPimHelloTime
         TimeTicks,
      er1645v2Lan2FGPppOEIpPimPropagationDelay
         TimeTicks,
      er1645v2Lan2FGPppOEIpPimOverrideInterval
         TimeTicks,
      er1645v2Lan2FGPppOEIpPimBsrBorder
         INTEGER,
      er1645v2Lan2FGPppOEIpPimTtlThreshold
         Integer32,
      er1645v2Lan2FGPppOEIpIMNetworkUnreachable
         INTEGER,
      er1645v2Lan2FGPppOEIpIMHostUnreachable
         INTEGER,
      er1645v2Lan2FGPppOEIpIMProtocolUnreachable
         INTEGER,
      er1645v2Lan2FGPppOEIpIMPortUnreachable
         INTEGER,
      er1645v2Lan2FGPppOEIpIMMtuExceeded
         INTEGER,
      er1645v2Lan2FGPppOEIpIMAdminProhibited
         INTEGER,
      er1645v2Lan2FGPppOEIpIMTtlExceeded
         INTEGER,
      er1645v2Lan2FGPppOEIpIMRedirect
         INTEGER,
      er1645v2Lan2FGPppOEIpV6VrfRouter
         DisplayString,
      er1645v2Lan2FGPppOEIpV6AddrAutoConfigNrDupAddrDetects
         Integer32,
      er1645v2Lan2FGPppOEIpV6AddrAutoConfigAcceptRa
         INTEGER,
      er1645v2Lan2FGPppOEIpV6AddrAutoConfigAcceptRaRdnss
         INTEGER,
      er1645v2Lan2FGPppOEIpV6AddrAutoConfigAcceptRaDnssl
         INTEGER,
      er1645v2Lan2FGPppOEIpV6DefaultRoute
         INTEGER,
      er1645v2Lan2FGPppOEIpV6RaSend
         INTEGER,
      er1645v2Lan2FGPppOEIpV6RaMinInterval
         TimeTicks,
      er1645v2Lan2FGPppOEIpV6RaMaxInterval
         TimeTicks,
      er1645v2Lan2FGPppOEIpV6RaManagedFlag
         INTEGER,
      er1645v2Lan2FGPppOEIpV6RaOtherConfFlag
         INTEGER,
      er1645v2Lan2FGPppOEIpV6RaLinkMtu
         Integer32,
      er1645v2Lan2FGPppOEIpV6RaReachableTime
         TimeTicks,
      er1645v2Lan2FGPppOEIpV6RaRetransmitTime
         TimeTicks,
      er1645v2Lan2FGPppOEIpV6RaHopLimit
         Integer32,
      er1645v2Lan2FGPppOEIpV6RaDefaultLifeTime
         TimeTicks,
      er1645v2Lan2FGPppOEIpV6RaDnsOptionsRdnssLifeTime
         TimeTicks,
      er1645v2Lan2FGPppOEIpV6RaDnsOptionsRdnssImportServers
         INTEGER,
      er1645v2Lan2FGPppOEIpV6RaDnsOptionsDnsslLifeTime
         TimeTicks,
      er1645v2Lan2FGPppOEIpV6RaDnsOptionsDnsslImportDomains
         INTEGER,
      er1645v2Lan2FGPppOEIpV6RsSend
         INTEGER,
      er1645v2Lan2FGPppOEIpV6RsMaxRandomDelay
         TimeTicks,
      er1645v2Lan2FGPppOEIpV6RsInterval
         TimeTicks,
      er1645v2Lan2FGPppOEIpV6RsMaxSolicitations
         Integer32,
      er1645v2Lan2FGPppOEIpV6TrafficPolicyInbound
         DisplayString,
      er1645v2Lan2FGPppOEIpV6TrafficPolicyOutbound
         DisplayString,
      er1645v2Lan2FGPppOEIpV6FirewallZone
         DisplayString,
      er1645v2Lan2FGPppOEIpV6DhcpClientAddrAC
         INTEGER,
      er1645v2Lan2FGPppOEIpV6DhcpClientPrDelMode
         INTEGER,
      er1645v2Lan2FGPppOEIpV6DhcpClientPrDelPool
         DisplayString,
      er1645v2Lan2FGPppOEIpV6DhcpClientPrDelPdExclOpt
         INTEGER,
      er1645v2Lan2FGPppOEIpV6DhcpClientDnsServerPref
         Integer32,
      er1645v2Lan2FGPppOEIpV6DhcpClientRapidCommit
         INTEGER,
      er1645v2Lan2FGPppOEIpV6DhcpClientTimersSolTimeOut
         TimeTicks,
      er1645v2Lan2FGPppOEIpV6DhcpClientTimersSolMaxRt
         TimeTicks,
      er1645v2Lan2FGPppOEIpV6DhcpClientTimersInfoRefresh
         TimeTicks,
      er1645v2Lan2FGPppOEIpV6DhcpServerMode
         INTEGER,
      er1645v2Lan2FGPppOEIpV6DhcpServerPreference
         Integer32,
      er1645v2Lan2FGPppOEIpV6DhcpServerPool
         DisplayString,
      er1645v2Lan2FGPppOEIpV6DhcpServerRapidCommit
         INTEGER,
      er1645v2Lan2FGPppOEIpV6DhcpServerTimersInfoRefresh
         TimeTicks,
      er1645v2Lan2FGPppOEIpV6DhcpRelayMode
         INTEGER,
      er1645v2Lan2FGPppOEIpV6SendRedirect
         INTEGER,
      er1645v2Lan2FGPppOEIpV6LinkMtu
         Integer32,
      er1645v2Lan2FGPppOEIpV6InterfaceId
         OCTET STRING,
      er1645v2Lan2FGPppOEIpV6MF
         Integer32,
      er1645v2Lan2FGPppOEIpV6IcmpMessagesNoRoute
         INTEGER,
      er1645v2Lan2FGPppOEIpV6IcmpMessagesBeyondScope
         INTEGER,
      er1645v2Lan2FGPppOEIpV6IcmpMessagesAddressUnreachable
         INTEGER,
      er1645v2Lan2FGPppOEIpV6IcmpMessagesPortUnreachable
         INTEGER,
      er1645v2Lan2FGPppOEIpV6IcmpMessagesPacketTooBig
         INTEGER,
      er1645v2Lan2FGPppOEIpV6IcmpMessagesHopLimitExceeded
         INTEGER,
      er1645v2Lan2FGPppOEIpV6IcmpMessagesFragTimeExceeded
         INTEGER,
      er1645v2Lan2FGPppOEIpV6IcmpMessagesHeaderFieldErr
         INTEGER,
      er1645v2Lan2FGPppOEIpV6IcmpMessagesOptionUnrecognized
         INTEGER,
      er1645v2Lan2FGPppOEIpV6IcmpMessagesRedirect
         INTEGER,
      er1645v2Lan2FGPppOEPppLnkMOperation
         INTEGER,
      er1645v2Lan2FGPppOEPppLnkMInterval
         TimeTicks,
      er1645v2Lan2FGPppOEPppLnkMRepTimeOut
         TimeTicks,
      er1645v2Lan2FGPppOEPppLnkMFailsPrmt
         Integer32,
      er1645v2Lan2FGPppOEPppAuthentication
         INTEGER,
      er1645v2Lan2FGPppOEPppAuthenPeriod
         TimeTicks,
      er1645v2Lan2FGPppOEPppSessionName
         DisplayString,
      er1645v2Lan2FGPppOEPppSessionSecret
         DisplayString,
      er1645v2Lan2FGPppOEPppEncModeSessionSecret
         INTEGER,
      er1645v2Lan2FGPppOEPppEncSessionSecret
         DisplayString,
      er1645v2Lan2FGPppOEPppServiceName
         DisplayString
      }

er1645v2Lan2FGPppOEActions OBJECT-TYPE
   SYNTAX      VariableLengthTableActions
   MAX-ACCESS  read-write
   STATUS      current
   DESCRIPTION
      "By way of this field, some manipulations
       on this table may be performed."
   ::= {er1645v2Lan2FGPppOEEntry 2}

er1645v2Lan2FGPppOETableIx OBJECT-TYPE
   SYNTAX      TableIndex
   MAX-ACCESS  not-accessible
   STATUS      current
   DESCRIPTION
      ""
   ::= {er1645v2Lan2FGPppOEEntry 11}

er1645v2Lan2FGPppOEName OBJECT-TYPE
   SYNTAX      DisplayString
   MAX-ACCESS  read-write
   STATUS      current
   DESCRIPTION
      "Path: ethernet2.editConf.pppoEClient.name"
   ::= {er1645v2Lan2FGPppOEEntry 16777216}

er1645v2Lan2FGPppOERemark OBJECT-TYPE
   SYNTAX      DisplayString
   MAX-ACCESS  read-write
   STATUS      current
   DESCRIPTION
      "Path: ethernet2.editConf.pppoEClient.remark"
   ::= {er1645v2Lan2FGPppOEEntry 1157627904}

er1645v2Lan2FGPppOEAdminStatus OBJECT-TYPE
   SYNTAX      INTEGER
               {
               up (1),
               down (2)
               }
   MAX-ACCESS  read-write
   STATUS      current
   DESCRIPTION
      "Path: ethernet2.editConf.pppoEClient.adminStatus

       Possibilities:
               up   (1)
               down   (2)"
   ::= {er1645v2Lan2FGPppOEEntry 33554432}

er1645v2Lan2FGPppOEMode OBJECT-TYPE
   SYNTAX      INTEGER
               {
               routing (1),
               multilink (8),
               ipV6 (16),
               ipV6ipV4 (17)
               }
   MAX-ACCESS  read-write
   STATUS      current
   DESCRIPTION
      "Path: ethernet2.editConf.pppoEClient.mode

       Possibilities:
               routing   (1)
               multilink   (8)
               ipV6   (16)
               ipV6/ipV4   (17)"
   ::= {er1645v2Lan2FGPppOEEntry 67108864}

er1645v2Lan2FGPppOEIpVrfRouter OBJECT-TYPE
   SYNTAX      DisplayString
   MAX-ACCESS  read-write
   STATUS      current
   DESCRIPTION
      "Path: ethernet2.editConf.pppoEClient.ip.vrfRouter"
   ::= {er1645v2Lan2FGPppOEEntry 53215232}

er1645v2Lan2FGPppOEIpAdr OBJECT-TYPE
   SYNTAX      IpAddress
   MAX-ACCESS  read-write
   STATUS      current
   DESCRIPTION
      "Path: ethernet2.editConf.pppoEClient.ip.address"
   ::= {er1645v2Lan2FGPppOEEntry 58261504}

er1645v2Lan2FGPppOEIpNetm OBJECT-TYPE
   SYNTAX      IpAddress
   MAX-ACCESS  read-write
   STATUS      current
   DESCRIPTION
      "Path: ethernet2.editConf.pppoEClient.ip.netMask"
   ::= {er1645v2Lan2FGPppOEEntry 58392576}

er1645v2Lan2FGPppOEIpSNetName OBJECT-TYPE
   SYNTAX      INTEGER
               {
               slOPTg (0),
               corp (2),
               dmz (3),
               internet (1)
               }
   MAX-ACCESS  read-write
   STATUS      current
   DESCRIPTION
      "Path: ethernet2.editConf.pppoEClient.ip.sNet.name

       Possibilities:
               <OPT>   (0)
               corp   (2)
               dmz   (3)
               internet   (1)"
   ::= {er1645v2Lan2FGPppOEEntry 53674240}

er1645v2Lan2FGPppOEIpSNetCust OBJECT-TYPE
   SYNTAX      DisplayString
   MAX-ACCESS  read-write
   STATUS      current
   DESCRIPTION
      "Path: ethernet2.editConf.pppoEClient.ip.sNet.custom"
   ::= {er1645v2Lan2FGPppOEEntry 53674496}

er1645v2Lan2FGPppOEIpRem OBJECT-TYPE
   SYNTAX      IpAddress
   MAX-ACCESS  read-write
   STATUS      current
   DESCRIPTION
      "Path: ethernet2.editConf.pppoEClient.ip.remote"
   ::= {er1645v2Lan2FGPppOEEntry 58458112}

er1645v2Lan2FGPppOEIpUnnumbered OBJECT-TYPE
   SYNTAX      DisplayString
   MAX-ACCESS  read-write
   STATUS      current
   DESCRIPTION
      "Path: ethernet2.editConf.pppoEClient.ip.unnumbered"
   ::= {er1645v2Lan2FGPppOEEntry 52625408}

er1645v2Lan2FGPppOEIpGwPref OBJECT-TYPE
   SYNTAX      Integer32
   MAX-ACCESS  read-write
   STATUS      current
   DESCRIPTION
      "Path: ethernet2.editConf.pppoEClient.ip.gatewayPreference"
   ::= {er1645v2Lan2FGPppOEEntry 52690944}

er1645v2Lan2FGPppOEIpRsn OBJECT-TYPE
   SYNTAX      INTEGER
               {
               disabled (0),
               enabled (1)
               }
   MAX-ACCESS  read-write
   STATUS      current
   DESCRIPTION
      "Path: ethernet2.editConf.pppoEClient.ip.requestSubnet

       Possibilities:
               disabled   (0)
               enabled   (1)"
   ::= {er1645v2Lan2FGPppOEEntry 56688640}

er1645v2Lan2FGPppOEIpMtu OBJECT-TYPE
   SYNTAX      Integer32
   MAX-ACCESS  read-write
   STATUS      current
   DESCRIPTION
      "Path: ethernet2.editConf.pppoEClient.ip.mtu"
   ::= {er1645v2Lan2FGPppOEEntry 52953088}

er1645v2Lan2FGPppOEIpMssAdjust OBJECT-TYPE
   SYNTAX      INTEGER
               {
               disabled (0),
               auto (65536)
               }
   MAX-ACCESS  read-write
   STATUS      current
   DESCRIPTION
      "Path: ethernet2.editConf.pppoEClient.ip.mssAdjust

       Possibilities:
               disabled   (0)
               auto   (65536)"
   ::= {er1645v2Lan2FGPppOEEntry 53280768}

er1645v2Lan2FGPppOEIpRipMetric OBJECT-TYPE
   SYNTAX      Integer32
   MAX-ACCESS  read-write
   STATUS      current
   DESCRIPTION
      "Path: ethernet2.editConf.pppoEClient.ip.rip.metric"
   ::= {er1645v2Lan2FGPppOEEntry 51712768}

er1645v2Lan2FGPppOEIpRipMetricOut OBJECT-TYPE
   SYNTAX      Integer32
   MAX-ACCESS  read-write
   STATUS      current
   DESCRIPTION
      "Path: ethernet2.editConf.pppoEClient.ip.rip.metricOut"
   ::= {er1645v2Lan2FGPppOEEntry 51713024}

er1645v2Lan2FGPppOEIpRipMode OBJECT-TYPE
   SYNTAX      INTEGER
               {
               disabled (0),
               passive (1),
               active (2)
               }
   MAX-ACCESS  read-write
   STATUS      current
   DESCRIPTION
      "Path: ethernet2.editConf.pppoEClient.ip.rip.mode

       Possibilities:
               disabled   (0)
               passive   (1)
               active   (2)"
   ::= {er1645v2Lan2FGPppOEEntry 51713280}

er1645v2Lan2FGPppOEIpRipTxVer OBJECT-TYPE
   SYNTAX      INTEGER
               {
               rip1 (0),
               rip2 (1),
               rip1mcompatible (2)
               }
   MAX-ACCESS  read-write
   STATUS      current
   DESCRIPTION
      "Path: ethernet2.editConf.pppoEClient.ip.rip.txVersion

       Possibilities:
               rip1   (0)
               rip2   (1)
               rip1-compatible   (2)"
   ::= {er1645v2Lan2FGPppOEEntry 51716864}

er1645v2Lan2FGPppOEIpRipRxVer OBJECT-TYPE
   SYNTAX      INTEGER
               {
               rip1only (0),
               rip2only (1),
               rip12 (2)
               }
   MAX-ACCESS  read-write
   STATUS      current
   DESCRIPTION
      "Path: ethernet2.editConf.pppoEClient.ip.rip.rxVersion

       Possibilities:
               rip1only   (0)
               rip2only   (1)
               rip1&2   (2)"
   ::= {er1645v2Lan2FGPppOEEntry 51717120}

er1645v2Lan2FGPppOEIpRipSplitH OBJECT-TYPE
   SYNTAX      INTEGER
               {
               disabled (0),
               enabled (1),
               poisonedReverse (2)
               }
   MAX-ACCESS  read-write
   STATUS      current
   DESCRIPTION
      "Path: ethernet2.editConf.pppoEClient.ip.rip.splitHorizon

       Possibilities:
               disabled   (0)
               enabled   (1)
               poisonedReverse   (2)"
   ::= {er1645v2Lan2FGPppOEEntry 51713792}

er1645v2Lan2FGPppOEIpRipAuth OBJECT-TYPE
   SYNTAX      INTEGER
               {
               disabled (0),
               texts (1),
               md5 (2)
               }
   MAX-ACCESS  read-write
   STATUS      current
   DESCRIPTION
      "Path: ethernet2.editConf.pppoEClient.ip.rip.authentication

       Possibilities:
               disabled   (0)
               text    (1)
               md5   (2)"
   ::= {er1645v2Lan2FGPppOEEntry 51712512}

er1645v2Lan2FGPppOEIpRipFilter OBJECT-TYPE
   SYNTAX      DisplayString
   MAX-ACCESS  read-write
   STATUS      current
   DESCRIPTION
      "Path: ethernet2.editConf.pppoEClient.ip.rip.filter"
   ::= {er1645v2Lan2FGPppOEEntry 51716096}

er1645v2Lan2FGPppOEIpRipFilterIn OBJECT-TYPE
   SYNTAX      DisplayString
   MAX-ACCESS  read-write
   STATUS      current
   DESCRIPTION
      "Path: ethernet2.editConf.pppoEClient.ip.rip.filterIn"
   ::= {er1645v2Lan2FGPppOEEntry 51716352}

er1645v2Lan2FGPppOEIpRipClearNextHop OBJECT-TYPE
   SYNTAX      INTEGER
               {
               disabled (0),
               enabled (1)
               }
   MAX-ACCESS  read-write
   STATUS      current
   DESCRIPTION
      "Path: ethernet2.editConf.pppoEClient.ip.rip.clearNextHop

       Possibilities:
               disabled   (0)
               enabled   (1)"
   ::= {er1645v2Lan2FGPppOEEntry 51708416}

er1645v2Lan2FGPppOEIpAccPol OBJECT-TYPE
   SYNTAX      DisplayString
   MAX-ACCESS  read-write
   STATUS      current
   DESCRIPTION
      "Path: ethernet2.editConf.pppoEClient.ip.accessPolicy"
   ::= {er1645v2Lan2FGPppOEEntry 53084160}

er1645v2Lan2FGPppOEIpAB OBJECT-TYPE
   SYNTAX      DisplayString
   MAX-ACCESS  read-write
   STATUS      current
   DESCRIPTION
      "Path: ethernet2.editConf.pppoEClient.ip.trafficPolicy"
   ::= {er1645v2Lan2FGPppOEEntry 51249152}

er1645v2Lan2FGPppOEIpMA OBJECT-TYPE
   SYNTAX      INTEGER
               {
               disabled (0),
               enabled (1)
               }
   MAX-ACCESS  read-write
   STATUS      current
   DESCRIPTION
      "Path: ethernet2.editConf.pppoEClient.ip.mgmtAccess

       Possibilities:
               disabled   (0)
               enabled   (1)"
   ::= {er1645v2Lan2FGPppOEEntry 51380224}

er1645v2Lan2FGPppOEIpMF OBJECT-TYPE
   SYNTAX      Integer32
   MAX-ACCESS  read-write
   STATUS      current
   DESCRIPTION
      "Path: ethernet2.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2FGPppOEEntry 51445760}

er1645v2Lan2FGPppOEIpDB OBJECT-TYPE
   SYNTAX      INTEGER
               {
               disabled (0),
               enabled (1)
               }
   MAX-ACCESS  read-write
   STATUS      current
   DESCRIPTION
      "Path: ethernet2.editConf.pppoEClient.ip.directedBroadcasts

       Possibilities:
               disabled   (0)
               enabled   (1)"
   ::= {er1645v2Lan2FGPppOEEntry 51773440}

er1645v2Lan2FGPppOEIpIR OBJECT-TYPE
   SYNTAX      INTEGER
               {
               disabled (0),
               enabled (1)
               }
   MAX-ACCESS  read-write
   STATUS      current
   DESCRIPTION
      "Path: ethernet2.editConf.pppoEClient.ip.icmpRedirects

       Possibilities:
               disabled   (0)
               enabled   (1)"
   ::= {er1645v2Lan2FGPppOEEntry 52035584}

er1645v2Lan2FGPppOEIpIgmp OBJECT-TYPE
   SYNTAX      INTEGER
               {
               disabled (0),
               proxy (1),
               router (2),
               v3Router (5)
               }
   MAX-ACCESS  read-write
   STATUS      current
   DESCRIPTION
      "Path: ethernet2.editConf.pppoEClient.ip.igmp

       Possibilities:
               disabled   (0)
               proxy   (1)
               router   (2)
               v3Router   (5)"
   ::= {er1645v2Lan2FGPppOEEntry 52428800}

er1645v2Lan2FGPppOEIpNN OBJECT-TYPE
   SYNTAX      DisplayString
   MAX-ACCESS  read-write
   STATUS      current
   DESCRIPTION
      "Path: ethernet2.editConf.pppoEClient.ip.nat"
   ::= {er1645v2Lan2FGPppOEEntry 52101120}

er1645v2Lan2FGPppOEIpPimMode OBJECT-TYPE
   SYNTAX      INTEGER
               {
               disabled (0),
               sparse (1),
               passive (2)
               }
   MAX-ACCESS  read-write
   STATUS      current
   DESCRIPTION
      "Path: ethernet2.editConf.pppoEClient.ip.pim.mode

       Possibilities:
               disabled   (0)
               sparse   (1)
               passive   (2)"
   ::= {er1645v2Lan2FGPppOEEntry 53346560}

er1645v2Lan2FGPppOEIpPimDrPriority OBJECT-TYPE
   SYNTAX      Counter32
   MAX-ACCESS  read-write
   STATUS      current
   DESCRIPTION
      "Path: ethernet2.editConf.pppoEClient.ip.pim.drPriority

       32 bit unsigned wrappable counter."
   ::= {er1645v2Lan2FGPppOEEntry 53346816}

er1645v2Lan2FGPppOEIpPimHelloTime OBJECT-TYPE
   SYNTAX      TimeTicks
   MAX-ACCESS  read-write
   STATUS      current
   DESCRIPTION
      "Path: ethernet2.editConf.pppoEClient.ip.pim.helloTime

       Time in centi-second."
   ::= {er1645v2Lan2FGPppOEEntry 53347072}

er1645v2Lan2FGPppOEIpPimPropagationDelay OBJECT-TYPE
   SYNTAX      TimeTicks
   MAX-ACCESS  read-write
   STATUS      current
   DESCRIPTION
      "Path: ethernet2.editConf.pppoEClient.ip.pim.propagationDelay

       Time in centi-second."
   ::= {er1645v2Lan2FGPppOEEntry 53347328}

er1645v2Lan2FGPppOEIpPimOverrideInterval OBJECT-TYPE
   SYNTAX      TimeTicks
   MAX-ACCESS  read-write
   STATUS      current
   DESCRIPTION
      "Path: ethernet2.editConf.pppoEClient.ip.pim.overrideInterval

       Time in centi-second."
   ::= {er1645v2Lan2FGPppOEEntry 53347584}

er1645v2Lan2FGPppOEIpPimBsrBorder OBJECT-TYPE
   SYNTAX      INTEGER
               {
               disabled (0),
               enabled (1)
               }
   MAX-ACCESS  read-write
   STATUS      current
   DESCRIPTION
      "Path: ethernet2.editConf.pppoEClient.ip.pim.bsrBorder

       Possibilities:
               disabled   (0)
               enabled   (1)"
   ::= {er1645v2Lan2FGPppOEEntry 53347840}

er1645v2Lan2FGPppOEIpPimTtlThreshold OBJECT-TYPE
   SYNTAX      Integer32
   MAX-ACCESS  read-write
   STATUS      current
   DESCRIPTION
      "Path: ethernet2.editConf.pppoEClient.ip.pim.ttlThreshold"
   ::= {er1645v2Lan2FGPppOEEntry 53348096}

er1645v2Lan2FGPppOEIpIMNetworkUnreachable OBJECT-TYPE
   SYNTAX      INTEGER
               {
               disabled (0),
               enabled (1)
               }
   MAX-ACCESS  read-write
   STATUS      current
   DESCRIPTION
      "Path: ethernet2.editConf.pppoEClient.ip.icmpMessages.networkUnreachable

       Possibilities:
               disabled   (0)
               enabled   (1)"
   ::= {er1645v2Lan2FGPppOEEntry 53412096}

er1645v2Lan2FGPppOEIpIMHostUnreachable OBJECT-TYPE
   SYNTAX      INTEGER
               {
               disabled (0),
               enabled (1)
               }
   MAX-ACCESS  read-write
   STATUS      current
   DESCRIPTION
      "Path: ethernet2.editConf.pppoEClient.ip.icmpMessages.hostUnreachable

       Possibilities:
               disabled   (0)
               enabled   (1)"
   ::= {er1645v2Lan2FGPppOEEntry 53412352}

er1645v2Lan2FGPppOEIpIMProtocolUnreachable OBJECT-TYPE
   SYNTAX      INTEGER
               {
               disabled (0),
               enabled (1)
               }
   MAX-ACCESS  read-write
   STATUS      current
   DESCRIPTION
      "Path: ethernet2.editConf.pppoEClient.ip.icmpMessages.protocolUnreachable

       Possibilities:
               disabled   (0)
               enabled   (1)"
   ::= {er1645v2Lan2FGPppOEEntry 53412608}

er1645v2Lan2FGPppOEIpIMPortUnreachable OBJECT-TYPE
   SYNTAX      INTEGER
               {
               disabled (0),
               enabled (1)
               }
   MAX-ACCESS  read-write
   STATUS      current
   DESCRIPTION
      "Path: ethernet2.editConf.pppoEClient.ip.icmpMessages.portUnreachable

       Possibilities:
               disabled   (0)
               enabled   (1)"
   ::= {er1645v2Lan2FGPppOEEntry 53412864}

er1645v2Lan2FGPppOEIpIMMtuExceeded OBJECT-TYPE
   SYNTAX      INTEGER
               {
               disabled (0),
               enabled (1)
               }
   MAX-ACCESS  read-write
   STATUS      current
   DESCRIPTION
      "Path: ethernet2.editConf.pppoEClient.ip.icmpMessages.mtuExceeded

       Possibilities:
               disabled   (0)
               enabled   (1)"
   ::= {er1645v2Lan2FGPppOEEntry 53413120}

er1645v2Lan2FGPppOEIpIMAdminProhibited OBJECT-TYPE
   SYNTAX      INTEGER
               {
               disabled (0),
               enabled (1)
               }
   MAX-ACCESS  read-write
   STATUS      current
   DESCRIPTION
      "Path: ethernet2.editConf.pppoEClient.ip.icmpMessages.adminProhibited

       Possibilities:
               disabled   (0)
               enabled   (1)"
   ::= {er1645v2Lan2FGPppOEEntry 53413376}

er1645v2Lan2FGPppOEIpIMTtlExceeded OBJECT-TYPE
   SYNTAX      INTEGER
               {
               disabled (0),
               enabled (1)
               }
   MAX-ACCESS  read-write
   STATUS      current
   DESCRIPTION
      "Path: ethernet2.editConf.pppoEClient.ip.icmpMessages.ttlExceeded

       Possibilities:
               disabled   (0)
               enabled   (1)"
   ::= {er1645v2Lan2FGPppOEEntry 53413632}

er1645v2Lan2FGPppOEIpIMRedirect OBJECT-TYPE
   SYNTAX      INTEGER
               {
               disabled (0),
               enabled (1)
               }
   MAX-ACCESS  read-write
   STATUS      current
   DESCRIPTION
      "Path: ethernet2.editConf.pppoEClient.ip.icmpMessages.redirect

       Possibilities:
               disabled   (0)
               enabled   (1)"
   ::= {er1645v2Lan2FGPppOEEntry 53413888}

er1645v2Lan2FGPppOEIpV6VrfRouter OBJECT-TYPE
   SYNTAX      DisplayString
   MAX-ACCESS  read-write
   STATUS      current
   DESCRIPTION
      "Path: ethernet2.editConf.pppoEClient.ipV6.vrfRouter"
   ::= {er1645v2Lan2FGPppOEEntry 704708608}

er1645v2Lan2FGPppOEIpV6AddrAutoConfigNrDupAddrDetects OBJECT-TYPE
   SYNTAX      Integer32
   MAX-ACCESS  read-write
   STATUS      current
   DESCRIPTION
      "Path: ethernet2.editConf.pppoEClient.ipV6.addrAutoConfig.nrDupAddrDetects"
   ::= {er1645v2Lan2FGPppOEEntry 704905472}

er1645v2Lan2FGPppOEIpV6AddrAutoConfigAcceptRa OBJECT-TYPE
   SYNTAX      INTEGER
               {
               disabled (0),
               enabled (1)
               }
   MAX-ACCESS  read-write
   STATUS      current
   DESCRIPTION
      "Path: ethernet2.editConf.pppoEClient.ipV6.addrAutoConfig.acceptRa

       Possibilities:
               disabled   (0)
               enabled   (1)"
   ::= {er1645v2Lan2FGPppOEEntry 704905728}

er1645v2Lan2FGPppOEIpV6AddrAutoConfigAcceptRaRdnss OBJECT-TYPE
   SYNTAX      INTEGER
               {
               disabled (0),
               enabled (1)
               }
   MAX-ACCESS  read-write
   STATUS      current
   DESCRIPTION
      "Path: ethernet2.editConf.pppoEClient.ipV6.addrAutoConfig.acceptRaRdnss

       Possibilities:
               disabled   (0)
               enabled   (1)"
   ::= {er1645v2Lan2FGPppOEEntry 704905984}

er1645v2Lan2FGPppOEIpV6AddrAutoConfigAcceptRaDnssl OBJECT-TYPE
   SYNTAX      INTEGER
               {
               disabled (0),
               enabled (1)
               }
   MAX-ACCESS  read-write
   STATUS      current
   DESCRIPTION
      "Path: ethernet2.editConf.pppoEClient.ipV6.addrAutoConfig.acceptRaDnssl

       Possibilities:
               disabled   (0)
               enabled   (1)"
   ::= {er1645v2Lan2FGPppOEEntry 704906240}

er1645v2Lan2FGPppOEIpV6DefaultRoute OBJECT-TYPE
   SYNTAX      INTEGER
               {
               disabled (0),
               enabled (1)
               }
   MAX-ACCESS  read-write
   STATUS      current
   DESCRIPTION
      "Path: ethernet2.editConf.pppoEClient.ipV6.defaultRoute

       Possibilities:
               disabled   (0)
               enabled   (1)"
   ::= {er1645v2Lan2FGPppOEEntry 704970752}

er1645v2Lan2FGPppOEIpV6RaSend OBJECT-TYPE
   SYNTAX      INTEGER
               {
               disabled (0),
               enabled (1)
               }
   MAX-ACCESS  read-write
   STATUS      current
   DESCRIPTION
      "Path: ethernet2.editConf.pppoEClient.ipV6.ra.send

       Possibilities:
               disabled   (0)
               enabled   (1)"
   ::= {er1645v2Lan2FGPppOEEntry 705036544}

er1645v2Lan2FGPppOEIpV6RaMinInterval OBJECT-TYPE
   SYNTAX      TimeTicks
   MAX-ACCESS  read-write
   STATUS      current
   DESCRIPTION
      "Path: ethernet2.editConf.pppoEClient.ipV6.ra.minInterval

       Time in centi-second."
   ::= {er1645v2Lan2FGPppOEEntry 705036800}

er1645v2Lan2FGPppOEIpV6RaMaxInterval OBJECT-TYPE
   SYNTAX      TimeTicks
   MAX-ACCESS  read-write
   STATUS      current
   DESCRIPTION
      "Path: ethernet2.editConf.pppoEClient.ipV6.ra.maxInterval

       Time in centi-second."
   ::= {er1645v2Lan2FGPppOEEntry 705037056}

er1645v2Lan2FGPppOEIpV6RaManagedFlag OBJECT-TYPE
   SYNTAX      INTEGER
               {
               disabled (0),
               enabled (1)
               }
   MAX-ACCESS  read-write
   STATUS      current
   DESCRIPTION
      "Path: ethernet2.editConf.pppoEClient.ipV6.ra.managedFlag

       Possibilities:
               disabled   (0)
               enabled   (1)"
   ::= {er1645v2Lan2FGPppOEEntry 705037312}

er1645v2Lan2FGPppOEIpV6RaOtherConfFlag OBJECT-TYPE
   SYNTAX      INTEGER
               {
               disabled (0),
               enabled (1)
               }
   MAX-ACCESS  read-write
   STATUS      current
   DESCRIPTION
      "Path: ethernet2.editConf.pppoEClient.ipV6.ra.otherConfFlag

       Possibilities:
               disabled   (0)
               enabled   (1)"
   ::= {er1645v2Lan2FGPppOEEntry 705037568}

er1645v2Lan2FGPppOEIpV6RaLinkMtu OBJECT-TYPE
   SYNTAX      Integer32
   MAX-ACCESS  read-write
   STATUS      current
   DESCRIPTION
      "Path: ethernet2.editConf.pppoEClient.ipV6.ra.linkMtu"
   ::= {er1645v2Lan2FGPppOEEntry 705037824}

er1645v2Lan2FGPppOEIpV6RaReachableTime OBJECT-TYPE
   SYNTAX      TimeTicks
   MAX-ACCESS  read-write
   STATUS      current
   DESCRIPTION
      "Path: ethernet2.editConf.pppoEClient.ipV6.ra.reachableTime

       Time in centi-second."
   ::= {er1645v2Lan2FGPppOEEntry 705038080}

er1645v2Lan2FGPppOEIpV6RaRetransmitTime OBJECT-TYPE
   SYNTAX      TimeTicks
   MAX-ACCESS  read-write
   STATUS      current
   DESCRIPTION
      "Path: ethernet2.editConf.pppoEClient.ipV6.ra.retransmitTime

       Time in centi-second."
   ::= {er1645v2Lan2FGPppOEEntry 705038336}

er1645v2Lan2FGPppOEIpV6RaHopLimit OBJECT-TYPE
   SYNTAX      Integer32
   MAX-ACCESS  read-write
   STATUS      current
   DESCRIPTION
      "Path: ethernet2.editConf.pppoEClient.ipV6.ra.hopLimit"
   ::= {er1645v2Lan2FGPppOEEntry 705038592}

er1645v2Lan2FGPppOEIpV6RaDefaultLifeTime OBJECT-TYPE
   SYNTAX      TimeTicks
   MAX-ACCESS  read-write
   STATUS      current
   DESCRIPTION
      "Path: ethernet2.editConf.pppoEClient.ipV6.ra.defaultLifeTime

       Time in centi-second."
   ::= {er1645v2Lan2FGPppOEEntry 705038848}

er1645v2Lan2FGPppOEIpV6RaDnsOptionsRdnssLifeTime OBJECT-TYPE
   SYNTAX      TimeTicks
   MAX-ACCESS  read-write
   STATUS      current
   DESCRIPTION
      "Path: ethernet2.editConf.pppoEClient.ipV6.ra.dnsOptions.rdnss.lifeTime

       Time in centi-second."
   ::= {er1645v2Lan2FGPppOEEntry 705039140}

er1645v2Lan2FGPppOEIpV6RaDnsOptionsRdnssImportServers OBJECT-TYPE
   SYNTAX      INTEGER
               {
               disabled (0),
               enabled (1)
               }
   MAX-ACCESS  read-write
   STATUS      current
   DESCRIPTION
      "Path: ethernet2.editConf.pppoEClient.ipV6.ra.dnsOptions.rdnss.importServers

       Possibilities:
               disabled   (0)
               enabled   (1)"
   ::= {er1645v2Lan2FGPppOEEntry 705039148}

er1645v2Lan2FGPppOEIpV6RaDnsOptionsDnsslLifeTime OBJECT-TYPE
   SYNTAX      TimeTicks
   MAX-ACCESS  read-write
   STATUS      current
   DESCRIPTION
      "Path: ethernet2.editConf.pppoEClient.ipV6.ra.dnsOptions.dnssl.lifeTime

       Time in centi-second."
   ::= {er1645v2Lan2FGPppOEEntry 705039172}

er1645v2Lan2FGPppOEIpV6RaDnsOptionsDnsslImportDomains OBJECT-TYPE
   SYNTAX      INTEGER
               {
               disabled (0),
               enabled (1)
               }
   MAX-ACCESS  read-write
   STATUS      current
   DESCRIPTION
      "Path: ethernet2.editConf.pppoEClient.ipV6.ra.dnsOptions.dnssl.importDomains

       Possibilities:
               disabled   (0)
               enabled   (1)"
   ::= {er1645v2Lan2FGPppOEEntry 705039180}

er1645v2Lan2FGPppOEIpV6RsSend OBJECT-TYPE
   SYNTAX      INTEGER
               {
               disabled (0),
               enabled (1)
               }
   MAX-ACCESS  read-write
   STATUS      current
   DESCRIPTION
      "Path: ethernet2.editConf.pppoEClient.ipV6.rs.send

       Possibilities:
               disabled   (0)
               enabled   (1)"
   ::= {er1645v2Lan2FGPppOEEntry 705954048}

er1645v2Lan2FGPppOEIpV6RsMaxRandomDelay OBJECT-TYPE
   SYNTAX      TimeTicks
   MAX-ACCESS  read-write
   STATUS      current
   DESCRIPTION
      "Path: ethernet2.editConf.pppoEClient.ipV6.rs.maxRandomDelay

       Time in centi-second."
   ::= {er1645v2Lan2FGPppOEEntry 705954304}

er1645v2Lan2FGPppOEIpV6RsInterval OBJECT-TYPE
   SYNTAX      TimeTicks
   MAX-ACCESS  read-write
   STATUS      current
   DESCRIPTION
      "Path: ethernet2.editConf.pppoEClient.ipV6.rs.interval

       Time in centi-second."
   ::= {er1645v2Lan2FGPppOEEntry 705954560}

er1645v2Lan2FGPppOEIpV6RsMaxSolicitations OBJECT-TYPE
   SYNTAX      Integer32
   MAX-ACCESS  read-write
   STATUS      current
   DESCRIPTION
      "Path: ethernet2.editConf.pppoEClient.ipV6.rs.maxSolicitations"
   ::= {er1645v2Lan2FGPppOEEntry 705954816}

er1645v2Lan2FGPppOEIpV6TrafficPolicyInbound OBJECT-TYPE
   SYNTAX      DisplayString
   MAX-ACCESS  read-write
   STATUS      current
   DESCRIPTION
      "Path: ethernet2.editConf.pppoEClient.ipV6.trafficPolicy.inbound"
   ::= {er1645v2Lan2FGPppOEEntry 705364224}

er1645v2Lan2FGPppOEIpV6TrafficPolicyOutbound OBJECT-TYPE
   SYNTAX      DisplayString
   MAX-ACCESS  read-write
   STATUS      current
   DESCRIPTION
      "Path: ethernet2.editConf.pppoEClient.ipV6.trafficPolicy.outbound"
   ::= {er1645v2Lan2FGPppOEEntry 705364480}

er1645v2Lan2FGPppOEIpV6FirewallZone OBJECT-TYPE
   SYNTAX      DisplayString
   MAX-ACCESS  read-write
   STATUS      current
   DESCRIPTION
      "Path: ethernet2.editConf.pppoEClient.ipV6.firewall.zone"
   ::= {er1645v2Lan2FGPppOEEntry 705429760}

er1645v2Lan2FGPppOEIpV6DhcpClientAddrAC OBJECT-TYPE
   SYNTAX      INTEGER
               {
               disabled (0),
               enabled (1)
               }
   MAX-ACCESS  read-write
   STATUS      current
   DESCRIPTION
      "Path: ethernet2.editConf.pppoEClient.ipV6.dhcp.client.addrAutoConfig

       Possibilities:
               disabled   (0)
               enabled   (1)"
   ::= {er1645v2Lan2FGPppOEEntry 705307648}

er1645v2Lan2FGPppOEIpV6DhcpClientPrDelMode OBJECT-TYPE
   SYNTAX      INTEGER
               {
               disabled (0),
               enabled (1)
               }
   MAX-ACCESS  read-write
   STATUS      current
   DESCRIPTION
      "Path: ethernet2.editConf.pppoEClient.ipV6.dhcp.client.pd.mode

       Possibilities:
               disabled   (0)
               enabled   (1)"
   ::= {er1645v2Lan2FGPppOEEntry 705308676}

er1645v2Lan2FGPppOEIpV6DhcpClientPrDelPool OBJECT-TYPE
   SYNTAX      DisplayString
   MAX-ACCESS  read-write
   STATUS      current
   DESCRIPTION
      "Path: ethernet2.editConf.pppoEClient.ipV6.dhcp.client.pd.pool"
   ::= {er1645v2Lan2FGPppOEEntry 705308680}

er1645v2Lan2FGPppOEIpV6DhcpClientPrDelPdExclOpt OBJECT-TYPE
   SYNTAX      INTEGER
               {
               disabled (0),
               enabled (1)
               }
   MAX-ACCESS  read-write
   STATUS      current
   DESCRIPTION
      "Path: ethernet2.editConf.pppoEClient.ipV6.dhcp.client.pd.pdExclOpt

       Possibilities:
               disabled   (0)
               enabled   (1)"
   ::= {er1645v2Lan2FGPppOEEntry 705308684}

er1645v2Lan2FGPppOEIpV6DhcpClientDnsServerPref OBJECT-TYPE
   SYNTAX      Integer32
   MAX-ACCESS  read-write
   STATUS      current
   DESCRIPTION
      "Path: ethernet2.editConf.pppoEClient.ipV6.dhcp.client.dns.serverPref"
   ::= {er1645v2Lan2FGPppOEEntry 705310724}

er1645v2Lan2FGPppOEIpV6DhcpClientRapidCommit OBJECT-TYPE
   SYNTAX      INTEGER
               {
               disabled (0),
               enabled (1)
               }
   MAX-ACCESS  read-write
   STATUS      current
   DESCRIPTION
      "Path: ethernet2.editConf.pppoEClient.ipV6.dhcp.client.rapidCommit

       Possibilities:
               disabled   (0)
               enabled   (1)"
   ::= {er1645v2Lan2FGPppOEEntry 705309696}

er1645v2Lan2FGPppOEIpV6DhcpClientTimersSolTimeOut OBJECT-TYPE
   SYNTAX      TimeTicks
   MAX-ACCESS  read-write
   STATUS      current
   DESCRIPTION
      "Path: ethernet2.editConf.pppoEClient.ipV6.dhcp.client.timers.solTimeOut

       Time in centi-second."
   ::= {er1645v2Lan2FGPppOEEntry 705311748}

er1645v2Lan2FGPppOEIpV6DhcpClientTimersSolMaxRt OBJECT-TYPE
   SYNTAX      TimeTicks
   MAX-ACCESS  read-write
   STATUS      current
   DESCRIPTION
      "Path: ethernet2.editConf.pppoEClient.ipV6.dhcp.client.timers.solMaxRt

       Time in centi-second."
   ::= {er1645v2Lan2FGPppOEEntry 705311752}

er1645v2Lan2FGPppOEIpV6DhcpClientTimersInfoRefresh OBJECT-TYPE
   SYNTAX      TimeTicks
   MAX-ACCESS  read-write
   STATUS      current
   DESCRIPTION
      "Path: ethernet2.editConf.pppoEClient.ipV6.dhcp.client.timers.infoRefresh

       Time in centi-second."
   ::= {er1645v2Lan2FGPppOEEntry 705311756}

er1645v2Lan2FGPppOEIpV6DhcpServerMode OBJECT-TYPE
   SYNTAX      INTEGER
               {
               disabled (0),
               enabled (1)
               }
   MAX-ACCESS  read-write
   STATUS      current
   DESCRIPTION
      "Path: ethernet2.editConf.pppoEClient.ipV6.dhcp.server.mode

       Possibilities:
               disabled   (0)
               enabled   (1)"
   ::= {er1645v2Lan2FGPppOEEntry 705315840}

er1645v2Lan2FGPppOEIpV6DhcpServerPreference OBJECT-TYPE
   SYNTAX      Integer32
   MAX-ACCESS  read-write
   STATUS      current
   DESCRIPTION
      "Path: ethernet2.editConf.pppoEClient.ipV6.dhcp.server.preference"
   ::= {er1645v2Lan2FGPppOEEntry 705316864}

er1645v2Lan2FGPppOEIpV6DhcpServerPool OBJECT-TYPE
   SYNTAX      DisplayString
   MAX-ACCESS  read-write
   STATUS      current
   DESCRIPTION
      "Path: ethernet2.editConf.pppoEClient.ipV6.dhcp.server.pool"
   ::= {er1645v2Lan2FGPppOEEntry 705317888}

er1645v2Lan2FGPppOEIpV6DhcpServerRapidCommit OBJECT-TYPE
   SYNTAX      INTEGER
               {
               disabled (0),
               enabled (1)
               }
   MAX-ACCESS  read-write
   STATUS      current
   DESCRIPTION
      "Path: ethernet2.editConf.pppoEClient.ipV6.dhcp.server.rapidCommit

       Possibilities:
               disabled   (0)
               enabled   (1)"
   ::= {er1645v2Lan2FGPppOEEntry 705318912}

er1645v2Lan2FGPppOEIpV6DhcpServerTimersInfoRefresh OBJECT-TYPE
   SYNTAX      TimeTicks
   MAX-ACCESS  read-write
   STATUS      current
   DESCRIPTION
      "Path: ethernet2.editConf.pppoEClient.ipV6.dhcp.server.timers.infoRefresh

       Time in centi-second."
   ::= {er1645v2Lan2FGPppOEEntry 705319940}

er1645v2Lan2FGPppOEIpV6DhcpRelayMode OBJECT-TYPE
   SYNTAX      INTEGER
               {
               disabled (0),
               enabled (1)
               }
   MAX-ACCESS  read-write
   STATUS      current
   DESCRIPTION
      "Path: ethernet2.editConf.pppoEClient.ipV6.dhcp.relay.mode

       Possibilities:
               disabled   (0)
               enabled   (1)"
   ::= {er1645v2Lan2FGPppOEEntry 705323040}

er1645v2Lan2FGPppOEIpV6SendRedirect OBJECT-TYPE
   SYNTAX      INTEGER
               {
               disabled (0),
               enabled (1)
               }
   MAX-ACCESS  read-write
   STATUS      current
   DESCRIPTION
      "Path: ethernet2.editConf.pppoEClient.ipV6.sendRedirect

       Possibilities:
               disabled   (0)
               enabled   (1)"
   ::= {er1645v2Lan2FGPppOEEntry 705101824}

er1645v2Lan2FGPppOEIpV6LinkMtu OBJECT-TYPE
   SYNTAX      Integer32
   MAX-ACCESS  read-write
   STATUS      current
   DESCRIPTION
      "Path: ethernet2.editConf.pppoEClient.ipV6.linkMtu"
   ::= {er1645v2Lan2FGPppOEEntry 705167360}

er1645v2Lan2FGPppOEIpV6InterfaceId OBJECT-TYPE
   SYNTAX      OCTET STRING
   MAX-ACCESS  read-write
   STATUS      current
   DESCRIPTION
      "Path: ethernet2.editConf.pppoEClient.ipV6.interfaceId"
   ::= {er1645v2Lan2FGPppOEEntry 705232896}

er1645v2Lan2FGPppOEIpV6MF OBJECT-TYPE
   SYNTAX      Integer32
   MAX-ACCESS  read-write
   STATUS      current
   DESCRIPTION
      "Path: ethernet2.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2FGPppOEEntry 705757184}

er1645v2Lan2FGPppOEIpV6IcmpMessagesNoRoute OBJECT-TYPE
   SYNTAX      INTEGER
               {
               disabled (0),
               enabled (1)
               }
   MAX-ACCESS  read-write
   STATUS      current
   DESCRIPTION
      "Path: ethernet2.editConf.pppoEClient.ipV6.icmpMessages.noRoute

       Possibilities:
               disabled   (0)
               enabled   (1)"
   ::= {er1645v2Lan2FGPppOEEntry 705822976}

er1645v2Lan2FGPppOEIpV6IcmpMessagesBeyondScope OBJECT-TYPE
   SYNTAX      INTEGER
               {
               disabled (0),
               enabled (1)
               }
   MAX-ACCESS  read-write
   STATUS      current
   DESCRIPTION
      "Path: ethernet2.editConf.pppoEClient.ipV6.icmpMessages.beyondScope

       Possibilities:
               disabled   (0)
               enabled   (1)"
   ::= {er1645v2Lan2FGPppOEEntry 705823488}

er1645v2Lan2FGPppOEIpV6IcmpMessagesAddressUnreachable OBJECT-TYPE
   SYNTAX      INTEGER
               {
               disabled (0),
               enabled (1)
               }
   MAX-ACCESS  read-write
   STATUS      current
   DESCRIPTION
      "Path: ethernet2.editConf.pppoEClient.ipV6.icmpMessages.addressUnreachable

       Possibilities:
               disabled   (0)
               enabled   (1)"
   ::= {er1645v2Lan2FGPppOEEntry 705823744}

er1645v2Lan2FGPppOEIpV6IcmpMessagesPortUnreachable OBJECT-TYPE
   SYNTAX      INTEGER
               {
               disabled (0),
               enabled (1)
               }
   MAX-ACCESS  read-write
   STATUS      current
   DESCRIPTION
      "Path: ethernet2.editConf.pppoEClient.ipV6.icmpMessages.portUnreachable

       Possibilities:
               disabled   (0)
               enabled   (1)"
   ::= {er1645v2Lan2FGPppOEEntry 705824000}

er1645v2Lan2FGPppOEIpV6IcmpMessagesPacketTooBig OBJECT-TYPE
   SYNTAX      INTEGER
               {
               disabled (0),
               enabled (1)
               }
   MAX-ACCESS  read-write
   STATUS      current
   DESCRIPTION
      "Path: ethernet2.editConf.pppoEClient.ipV6.icmpMessages.packetTooBig

       Possibilities:
               disabled   (0)
               enabled   (1)"
   ::= {er1645v2Lan2FGPppOEEntry 705825280}

er1645v2Lan2FGPppOEIpV6IcmpMessagesHopLimitExceeded OBJECT-TYPE
   SYNTAX      INTEGER
               {
               disabled (0),
               enabled (1)
               }
   MAX-ACCESS  read-write
   STATUS      current
   DESCRIPTION
      "Path: ethernet2.editConf.pppoEClient.ipV6.icmpMessages.hopLimitExceeded

       Possibilities:
               disabled   (0)
               enabled   (1)"
   ::= {er1645v2Lan2FGPppOEEntry 705827840}

er1645v2Lan2FGPppOEIpV6IcmpMessagesFragTimeExceeded OBJECT-TYPE
   SYNTAX      INTEGER
               {
               disabled (0),
               enabled (1)
               }
   MAX-ACCESS  read-write
   STATUS      current
   DESCRIPTION
      "Path: ethernet2.editConf.pppoEClient.ipV6.icmpMessages.fragTimeExceeded

       Possibilities:
               disabled   (0)
               enabled   (1)"
   ::= {er1645v2Lan2FGPppOEEntry 705828096}

er1645v2Lan2FGPppOEIpV6IcmpMessagesHeaderFieldErr OBJECT-TYPE
   SYNTAX      INTEGER
               {
               disabled (0),
               enabled (1)
               }
   MAX-ACCESS  read-write
   STATUS      current
   DESCRIPTION
      "Path: ethernet2.editConf.pppoEClient.ipV6.icmpMessages.headerFieldErr

       Possibilities:
               disabled   (0)
               enabled   (1)"
   ::= {er1645v2Lan2FGPppOEEntry 705830400}

er1645v2Lan2FGPppOEIpV6IcmpMessagesOptionUnrecognized OBJECT-TYPE
   SYNTAX      INTEGER
               {
               disabled (0),
               enabled (1)
               }
   MAX-ACCESS  read-write
   STATUS      current
   DESCRIPTION
      "Path: ethernet2.editConf.pppoEClient.ipV6.icmpMessages.optionUnrecognized

       Possibilities:
               disabled   (0)
               enabled   (1)"
   ::= {er1645v2Lan2FGPppOEEntry 705830912}

er1645v2Lan2FGPppOEIpV6IcmpMessagesRedirect OBJECT-TYPE
   SYNTAX      INTEGER
               {
               disabled (0),
               enabled (1)
               }
   MAX-ACCESS  read-write
   STATUS      current
   DESCRIPTION
      "Path: ethernet2.editConf.pppoEClient.ipV6.icmpMessages.redirect

       Possibilities:
               disabled   (0)
               enabled   (1)"
   ::= {er1645v2Lan2FGPppOEEntry 705832960}

er1645v2Lan2FGPppOEPppLnkMOperation OBJECT-TYPE
   SYNTAX      INTEGER
               {
               disabled (0),
               enabled (1)
               }
   MAX-ACCESS  read-write
   STATUS      current
   DESCRIPTION
      "Path: ethernet2.editConf.pppoEClient.ppp.linkMonitoring.operation

       Possibilities:
               disabled   (0)
               enabled   (1)"
   ::= {er1645v2Lan2FGPppOEEntry 251724032}

er1645v2Lan2FGPppOEPppLnkMInterval OBJECT-TYPE
   SYNTAX      TimeTicks
   MAX-ACCESS  read-write
   STATUS      current
   DESCRIPTION
      "Path: ethernet2.editConf.pppoEClient.ppp.linkMonitoring.interval

       Time in centi-second."
   ::= {er1645v2Lan2FGPppOEEntry 251724288}

er1645v2Lan2FGPppOEPppLnkMRepTimeOut OBJECT-TYPE
   SYNTAX      TimeTicks
   MAX-ACCESS  read-write
   STATUS      current
   DESCRIPTION
      "Path: ethernet2.editConf.pppoEClient.ppp.linkMonitoring.replyTimeOut

       Time in centi-second."
   ::= {er1645v2Lan2FGPppOEEntry 251724544}

er1645v2Lan2FGPppOEPppLnkMFailsPrmt OBJECT-TYPE
   SYNTAX      Integer32
   MAX-ACCESS  read-write
   STATUS      current
   DESCRIPTION
      "Path: ethernet2.editConf.pppoEClient.ppp.linkMonitoring.failsPermitted"
   ::= {er1645v2Lan2FGPppOEEntry 251724800}

er1645v2Lan2FGPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet2.editConf.pppoEClient.ppp.authentication

       Possibilities:
               disabled   (0)
               chap   (1)
               pap   (2)
               chapOrPap   (3)
               msChap   (4)
               msChapV2   (5)"
   ::= {er1645v2Lan2FGPppOEEntry 251789312}

er1645v2Lan2FGPppOEPppAuthenPeriod OBJECT-TYPE
   SYNTAX      TimeTicks
   MAX-ACCESS  read-write
   STATUS      current
   DESCRIPTION
      "Path: ethernet2.editConf.pppoEClient.ppp.authenPeriod

       Time in centi-second."
   ::= {er1645v2Lan2FGPppOEEntry 251854848}

er1645v2Lan2FGPppOEPppSessionName OBJECT-TYPE
   SYNTAX      DisplayString
   MAX-ACCESS  read-write
   STATUS      current
   DESCRIPTION
      "Path: ethernet2.editConf.pppoEClient.ppp.sessionName"
   ::= {er1645v2Lan2FGPppOEEntry 251985920}

er1645v2Lan2FGPppOEPppSessionSecret OBJECT-TYPE
   SYNTAX      DisplayString
   MAX-ACCESS  read-write
   STATUS      current
   DESCRIPTION
      "Path: ethernet2.editConf.pppoEClient.ppp.sessionSecret"
   ::= {er1645v2Lan2FGPppOEEntry 252051456}

er1645v2Lan2FGPppOEPppEncModeSessionSecret OBJECT-TYPE
   SYNTAX      INTEGER
               {
               none (1),
               encrypt (2),
               encType1 (3),
               invalid (128)
               }
   MAX-ACCESS  read-write
   STATUS      current
   DESCRIPTION
      "Path: ethernet2.editConf.pppoEClient.ppp.encModeSessionSecret

       Possibilities:
               none   (1)
               encrypt   (2)
               encType1   (3)
               invalid   (128)"
   ::= {er1645v2Lan2FGPppOEEntry 252182528}

er1645v2Lan2FGPppOEPppEncSessionSecret OBJECT-TYPE
   SYNTAX      DisplayString
   MAX-ACCESS  read-write
   STATUS      current
   DESCRIPTION
      "Path: ethernet2.editConf.pppoEClient.ppp.encSessionSecret"
   ::= {er1645v2Lan2FGPppOEEntry 252248064}

er1645v2Lan2FGPppOEPppServiceName OBJECT-TYPE
   SYNTAX      DisplayString
   MAX-ACCESS  read-write
   STATUS      current
   DESCRIPTION
      "Path: ethernet2.editConf.pppoEClient.ppp.serviceName"
   ::= {er1645v2Lan2FGPppOEEntry 252116992}

er1645v2Lan2FGPppOEIpH OBJECT-TYPE
   SYNTAX      SEQUENCE OF Er1645v2Lan2FGPppOEIpHEntry
   MAX-ACCESS  not-accessible
   STATUS      current
   DESCRIPTION
      ""
   ::= {er1645v2Lan2FGPppOE 51314688}

er1645v2Lan2FGPppOEIpHEntry OBJECT-TYPE
   SYNTAX      Er1645v2Lan2FGPppOEIpHEntry
   MAX-ACCESS  not-accessible
   STATUS      current
   DESCRIPTION
      ""
   INDEX      { er1645v2Lan2FGPppOETableIx,
                er1645v2Lan2FGPppOEIpHTableIx }
   ::= {er1645v2Lan2FGPppOEIpH 1}

Er1645v2Lan2FGPppOEIpHEntry ::=
   SEQUENCE
      {
      er1645v2Lan2FGPppOEIpHActions
         VariableLengthTableActions,
      er1645v2Lan2FGPppOEIpHTableIx
         TableIndex,
      er1645v2Lan2FGPppOEIpHAddress
         IpAddress,
      er1645v2Lan2FGPppOEIpHDhcpRelayOptionSubscriberId
         DisplayString
      }

er1645v2Lan2FGPppOEIpHActions OBJECT-TYPE
   SYNTAX      VariableLengthTableActions
   MAX-ACCESS  read-write
   STATUS      current
   DESCRIPTION
      "By way of this field, some manipulations
       on this table may be performed."
   ::= {er1645v2Lan2FGPppOEIpHEntry 2}

er1645v2Lan2FGPppOEIpHTableIx OBJECT-TYPE
   SYNTAX      TableIndex
   MAX-ACCESS  not-accessible
   STATUS      current
   DESCRIPTION
      ""
   ::= {er1645v2Lan2FGPppOEIpHEntry 11}

er1645v2Lan2FGPppOEIpHAddress OBJECT-TYPE
   SYNTAX      IpAddress
   MAX-ACCESS  read-write
   STATUS      current
   DESCRIPTION
      "Path: ethernet2.editConf.pppoEClient.ip.helpers.address"
   ::= {er1645v2Lan2FGPppOEIpHEntry 16777216}

er1645v2Lan2FGPppOEIpHDhcpRelayOptionSubscriberId OBJECT-TYPE
   SYNTAX      DisplayString
   MAX-ACCESS  read-write
   STATUS      current
   DESCRIPTION
      "Path: ethernet2.editConf.pppoEClient.ip.helpers.dhcpRelayOption.subscriberId"
   ::= {er1645v2Lan2FGPppOEIpHEntry 33947648}

er1645v2Lan2FGPppOEIpV6Addresses OBJECT-TYPE
   SYNTAX      SEQUENCE OF Er1645v2Lan2FGPppOEIpV6AddressesEntry
   MAX-ACCESS  not-accessible
   STATUS      current
   DESCRIPTION
      ""
   ::= {er1645v2Lan2FGPppOE 704839680}

er1645v2Lan2FGPppOEIpV6AddressesEntry OBJECT-TYPE
   SYNTAX      Er1645v2Lan2FGPppOEIpV6AddressesEntry
   MAX-ACCESS  not-accessible
   STATUS      current
   DESCRIPTION
      ""
   INDEX      { er1645v2Lan2FGPppOETableIx,
                er1645v2Lan2FGPppOEIpV6AddressesTableIx }
   ::= {er1645v2Lan2FGPppOEIpV6Addresses 1}

Er1645v2Lan2FGPppOEIpV6AddressesEntry ::=
   SEQUENCE
      {
      er1645v2Lan2FGPppOEIpV6AddressesActions
         VariableLengthTableActions,
      er1645v2Lan2FGPppOEIpV6AddressesTableIx
         TableIndex,
      er1645v2Lan2FGPppOEIpV6AddressesType
         INTEGER,
      er1645v2Lan2FGPppOEIpV6AddressesAddress
         Ipv6Address,
      er1645v2Lan2FGPppOEIpV6AddressesPrefixLength
         Integer32,
      er1645v2Lan2FGPppOEIpV6AddressesGeneralPrefix
         DisplayString,
      er1645v2Lan2FGPppOEIpV6AddressesRaSend
         INTEGER,
      er1645v2Lan2FGPppOEIpV6AddressesRaOnLinkFlag
         INTEGER,
      er1645v2Lan2FGPppOEIpV6AddressesRaAutoFlag
         INTEGER,
      er1645v2Lan2FGPppOEIpV6AddressesRaValidLifeTime
         TimeTicks,
      er1645v2Lan2FGPppOEIpV6AddressesRaValidLTMode
         INTEGER,
      er1645v2Lan2FGPppOEIpV6AddressesRaPrefLifeTime
         TimeTicks,
      er1645v2Lan2FGPppOEIpV6AddressesRaPrefLTMode
         INTEGER
      }

er1645v2Lan2FGPppOEIpV6AddressesActions OBJECT-TYPE
   SYNTAX      VariableLengthTableActions
   MAX-ACCESS  read-write
   STATUS      current
   DESCRIPTION
      "By way of this field, some manipulations
       on this table may be performed."
   ::= {er1645v2Lan2FGPppOEIpV6AddressesEntry 2}

er1645v2Lan2FGPppOEIpV6AddressesTableIx OBJECT-TYPE
   SYNTAX      TableIndex
   MAX-ACCESS  not-accessible
   STATUS      current
   DESCRIPTION
      ""
   ::= {er1645v2Lan2FGPppOEIpV6AddressesEntry 11}

er1645v2Lan2FGPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.pppoEClient.ipV6.addresses.type

       Possibilities:
               unicast   (0)
               eui64   (1)
               anycast   (2)
               linkLocal   (3)
               generalPrefix   (4)"
   ::= {er1645v2Lan2FGPppOEIpV6AddressesEntry 50331648}

er1645v2Lan2FGPppOEIpV6AddressesAddress OBJECT-TYPE
   SYNTAX      Ipv6Address
   MAX-ACCESS  read-write
   STATUS      current
   DESCRIPTION
      "Path: ethernet2.editConf.pppoEClient.ipV6.addresses.address

       ipv6 address"
   ::= {er1645v2Lan2FGPppOEIpV6AddressesEntry 16777216}

er1645v2Lan2FGPppOEIpV6AddressesPrefixLength OBJECT-TYPE
   SYNTAX      Integer32
   MAX-ACCESS  read-write
   STATUS      current
   DESCRIPTION
      "Path: ethernet2.editConf.pppoEClient.ipV6.addresses.prefixLength"
   ::= {er1645v2Lan2FGPppOEIpV6AddressesEntry 33554432}

er1645v2Lan2FGPppOEIpV6AddressesGeneralPrefix OBJECT-TYPE
   SYNTAX      DisplayString
   MAX-ACCESS  read-write
   STATUS      current
   DESCRIPTION
      "Path: ethernet2.editConf.pppoEClient.ipV6.addresses.generalPrefix"
   ::= {er1645v2Lan2FGPppOEIpV6AddressesEntry 83886080}

er1645v2Lan2FGPppOEIpV6AddressesRaSend OBJECT-TYPE
   SYNTAX      INTEGER
               {
               disabled (0),
               enabled (1)
               }
   MAX-ACCESS  read-write
   STATUS      current
   DESCRIPTION
      "Path: ethernet2.editConf.pppoEClient.ipV6.addresses.ra.send

       Possibilities:
               disabled   (0)
               enabled   (1)"
   ::= {er1645v2Lan2FGPppOEIpV6AddressesEntry 67174400}

er1645v2Lan2FGPppOEIpV6AddressesRaOnLinkFlag OBJECT-TYPE
   SYNTAX      INTEGER
               {
               disabled (0),
               enabled (1)
               }
   MAX-ACCESS  read-write
   STATUS      current
   DESCRIPTION
      "Path: ethernet2.editConf.pppoEClient.ipV6.addresses.ra.onLinkFlag

       Possibilities:
               disabled   (0)
               enabled   (1)"
   ::= {er1645v2Lan2FGPppOEIpV6AddressesEntry 67371008}

er1645v2Lan2FGPppOEIpV6AddressesRaAutoFlag OBJECT-TYPE
   SYNTAX      INTEGER
               {
               disabled (0),
               enabled (1)
               }
   MAX-ACCESS  read-write
   STATUS      current
   DESCRIPTION
      "Path: ethernet2.editConf.pppoEClient.ipV6.addresses.ra.autonomousFlag

       Possibilities:
               disabled   (0)
               enabled   (1)"
   ::= {er1645v2Lan2FGPppOEIpV6AddressesEntry 67567616}

er1645v2Lan2FGPppOEIpV6AddressesRaValidLifeTime OBJECT-TYPE
   SYNTAX      TimeTicks
   MAX-ACCESS  read-write
   STATUS      current
   DESCRIPTION
      "Path: ethernet2.editConf.pppoEClient.ipV6.addresses.ra.validLifeTime

       Time in centi-second."
   ::= {er1645v2Lan2FGPppOEIpV6AddressesEntry 67239936}

er1645v2Lan2FGPppOEIpV6AddressesRaValidLTMode OBJECT-TYPE
   SYNTAX      INTEGER
               {
               fixed (0),
               infinite (2)
               }
   MAX-ACCESS  read-write
   STATUS      current
   DESCRIPTION
      "Path: ethernet2.editConf.pppoEClient.ipV6.addresses.ra.validLifeTimeMode

       Possibilities:
               fixed   (0)
               infinite   (2)"
   ::= {er1645v2Lan2FGPppOEIpV6AddressesEntry 67305472}

er1645v2Lan2FGPppOEIpV6AddressesRaPrefLifeTime OBJECT-TYPE
   SYNTAX      TimeTicks
   MAX-ACCESS  read-write
   STATUS      current
   DESCRIPTION
      "Path: ethernet2.editConf.pppoEClient.ipV6.addresses.ra.prefLifeTime

       Time in centi-second."
   ::= {er1645v2Lan2FGPppOEIpV6AddressesEntry 67436544}

er1645v2Lan2FGPppOEIpV6AddressesRaPrefLTMode OBJECT-TYPE
   SYNTAX      INTEGER
               {
               fixed (0),
               infinite (2)
               }
   MAX-ACCESS  read-write
   STATUS      current
   DESCRIPTION
      "Path: ethernet2.editConf.pppoEClient.ipV6.addresses.ra.prefLifeTimeMode

       Possibilities:
               fixed   (0)
               infinite   (2)"
   ::= {er1645v2Lan2FGPppOEIpV6AddressesEntry 67502080}

er1645v2Lan2FGPppOEIpV6RaDnsOptionsRdnssServers OBJECT-TYPE
   SYNTAX      SEQUENCE OF Er1645v2Lan2FGPppOEIpV6RaDnsOptionsRdnssServersEntry
   MAX-ACCESS  not-accessible
   STATUS      current
   DESCRIPTION
      ""
   ::= {er1645v2Lan2FGPppOE 705039144}

er1645v2Lan2FGPppOEIpV6RaDnsOptionsRdnssServersEntry OBJECT-TYPE
   SYNTAX      Er1645v2Lan2FGPppOEIpV6RaDnsOptionsRdnssServersEntry
   MAX-ACCESS  not-accessible
   STATUS      current
   DESCRIPTION
      ""
   INDEX      { er1645v2Lan2FGPppOETableIx,
                er1645v2Lan2FGPppOEIpV6RaDnsOptionsRdnssServersTableIx }
   ::= {er1645v2Lan2FGPppOEIpV6RaDnsOptionsRdnssServers 1}

Er1645v2Lan2FGPppOEIpV6RaDnsOptionsRdnssServersEntry ::=
   SEQUENCE
      {
      er1645v2Lan2FGPppOEIpV6RaDnsOptionsRdnssServersActions
         VariableLengthTableActions,
      er1645v2Lan2FGPppOEIpV6RaDnsOptionsRdnssServersTableIx
         TableIndex,
      er1645v2Lan2FGPppOEIpV6RaDnsOptionsRdnssServersAddress
         Ipv6Address
      }

er1645v2Lan2FGPppOEIpV6RaDnsOptionsRdnssServersActions OBJECT-TYPE
   SYNTAX      VariableLengthTableActions
   MAX-ACCESS  read-write
   STATUS      current
   DESCRIPTION
      "By way of this field, some manipulations
       on this table may be performed."
   ::= {er1645v2Lan2FGPppOEIpV6RaDnsOptionsRdnssServersEntry 2}

er1645v2Lan2FGPppOEIpV6RaDnsOptionsRdnssServersTableIx OBJECT-TYPE
   SYNTAX      TableIndex
   MAX-ACCESS  not-accessible
   STATUS      current
   DESCRIPTION
      ""
   ::= {er1645v2Lan2FGPppOEIpV6RaDnsOptionsRdnssServersEntry 11}

er1645v2Lan2FGPppOEIpV6RaDnsOptionsRdnssServersAddress OBJECT-TYPE
   SYNTAX      Ipv6Address
   MAX-ACCESS  read-write
   STATUS      current
   DESCRIPTION
      "Path: ethernet2.editConf.pppoEClient.ipV6.ra.dnsOptions.rdnss.servers.address

       ipv6 address"
   ::= {er1645v2Lan2FGPppOEIpV6RaDnsOptionsRdnssServersEntry 16777216}

er1645v2Lan2FGPppOEIpV6RaDnsOptionsDnsslDomains OBJECT-TYPE
   SYNTAX      SEQUENCE OF Er1645v2Lan2FGPppOEIpV6RaDnsOptionsDnsslDomainsEntry
   MAX-ACCESS  not-accessible
   STATUS      current
   DESCRIPTION
      ""
   ::= {er1645v2Lan2FGPppOE 705039176}

er1645v2Lan2FGPppOEIpV6RaDnsOptionsDnsslDomainsEntry OBJECT-TYPE
   SYNTAX      Er1645v2Lan2FGPppOEIpV6RaDnsOptionsDnsslDomainsEntry
   MAX-ACCESS  not-accessible
   STATUS      current
   DESCRIPTION
      ""
   INDEX      { er1645v2Lan2FGPppOETableIx,
                er1645v2Lan2FGPppOEIpV6RaDnsOptionsDnsslDomainsTableIx }
   ::= {er1645v2Lan2FGPppOEIpV6RaDnsOptionsDnsslDomains 1}

Er1645v2Lan2FGPppOEIpV6RaDnsOptionsDnsslDomainsEntry ::=
   SEQUENCE
      {
      er1645v2Lan2FGPppOEIpV6RaDnsOptionsDnsslDomainsActions
         VariableLengthTableActions,
      er1645v2Lan2FGPppOEIpV6RaDnsOptionsDnsslDomainsTableIx
         TableIndex,
      er1645v2Lan2FGPppOEIpV6RaDnsOptionsDnsslDomainsName
         DisplayString
      }

er1645v2Lan2FGPppOEIpV6RaDnsOptionsDnsslDomainsActions OBJECT-TYPE
   SYNTAX      VariableLengthTableActions
   MAX-ACCESS  read-write
   STATUS      current
   DESCRIPTION
      "By way of this field, some manipulations
       on this table may be performed."
   ::= {er1645v2Lan2FGPppOEIpV6RaDnsOptionsDnsslDomainsEntry 2}

er1645v2Lan2FGPppOEIpV6RaDnsOptionsDnsslDomainsTableIx OBJECT-TYPE
   SYNTAX      TableIndex
   MAX-ACCESS  not-accessible
   STATUS      current
   DESCRIPTION
      ""
   ::= {er1645v2Lan2FGPppOEIpV6RaDnsOptionsDnsslDomainsEntry 11}

er1645v2Lan2FGPppOEIpV6RaDnsOptionsDnsslDomainsName OBJECT-TYPE
   SYNTAX      DisplayString
   MAX-ACCESS  read-write
   STATUS      current
   DESCRIPTION
      "Path: ethernet2.editConf.pppoEClient.ipV6.ra.dnsOptions.dnssl.domains.name"
   ::= {er1645v2Lan2FGPppOEIpV6RaDnsOptionsDnsslDomainsEntry 16777216}

er1645v2Lan2FGPppOEIpV6DhcpClientUserClassOpt OBJECT-TYPE
   SYNTAX      SEQUENCE OF Er1645v2Lan2FGPppOEIpV6DhcpClientUserClassOptEntry
   MAX-ACCESS  not-accessible
   STATUS      current
   DESCRIPTION
      ""
   ::= {er1645v2Lan2FGPppOE 705312768}

er1645v2Lan2FGPppOEIpV6DhcpClientUserClassOptEntry OBJECT-TYPE
   SYNTAX      Er1645v2Lan2FGPppOEIpV6DhcpClientUserClassOptEntry
   MAX-ACCESS  not-accessible
   STATUS      current
   DESCRIPTION
      ""
   INDEX      { er1645v2Lan2FGPppOETableIx,
                er1645v2Lan2FGPppOEIpV6DhcpClientUserClassOptTableIx }
   ::= {er1645v2Lan2FGPppOEIpV6DhcpClientUserClassOpt 1}

Er1645v2Lan2FGPppOEIpV6DhcpClientUserClassOptEntry ::=
   SEQUENCE
      {
      er1645v2Lan2FGPppOEIpV6DhcpClientUserClassOptActions
         VariableLengthTableActions,
      er1645v2Lan2FGPppOEIpV6DhcpClientUserClassOptTableIx
         TableIndex,
      er1645v2Lan2FGPppOEIpV6DhcpClientUserClassOptValueAscii
         DisplayString,
      er1645v2Lan2FGPppOEIpV6DhcpClientUserClassOptValueDecimal
         Integer32,
      er1645v2Lan2FGPppOEIpV6DhcpClientUserClassOptValueHexData
         OCTET STRING
      }

er1645v2Lan2FGPppOEIpV6DhcpClientUserClassOptActions OBJECT-TYPE
   SYNTAX      VariableLengthTableActions
   MAX-ACCESS  read-write
   STATUS      current
   DESCRIPTION
      "By way of this field, some manipulations
       on this table may be performed."
   ::= {er1645v2Lan2FGPppOEIpV6DhcpClientUserClassOptEntry 2}

er1645v2Lan2FGPppOEIpV6DhcpClientUserClassOptTableIx OBJECT-TYPE
   SYNTAX      TableIndex
   MAX-ACCESS  not-accessible
   STATUS      current
   DESCRIPTION
      ""
   ::= {er1645v2Lan2FGPppOEIpV6DhcpClientUserClassOptEntry 11}

er1645v2Lan2FGPppOEIpV6DhcpClientUserClassOptValueAscii OBJECT-TYPE
   SYNTAX      DisplayString
   MAX-ACCESS  read-write
   STATUS      current
   DESCRIPTION
      "Path: ethernet2.editConf.pppoEClient.ipV6.dhcp.client.userClassOpt.value.ascii"
   ::= {er1645v2Lan2FGPppOEIpV6DhcpClientUserClassOptEntry 16842752}

er1645v2Lan2FGPppOEIpV6DhcpClientUserClassOptValueDecimal OBJECT-TYPE
   SYNTAX      Integer32
   MAX-ACCESS  read-write
   STATUS      current
   DESCRIPTION
      "Path: ethernet2.editConf.pppoEClient.ipV6.dhcp.client.userClassOpt.value.decimal"
   ::= {er1645v2Lan2FGPppOEIpV6DhcpClientUserClassOptEntry 16908288}

er1645v2Lan2FGPppOEIpV6DhcpClientUserClassOptValueHexData OBJECT-TYPE
   SYNTAX      OCTET STRING
   MAX-ACCESS  read-write
   STATUS      current
   DESCRIPTION
      "Path: ethernet2.editConf.pppoEClient.ipV6.dhcp.client.userClassOpt.value.hexData"
   ::= {er1645v2Lan2FGPppOEIpV6DhcpClientUserClassOptEntry 16973824}

er1645v2Lan2FGPppOEIpV6DhcpClientVendorCl OBJECT-TYPE
   SYNTAX      SEQUENCE OF Er1645v2Lan2FGPppOEIpV6DhcpClientVendorClEntry
   MAX-ACCESS  not-accessible
   STATUS      current
   DESCRIPTION
      ""
   ::= {er1645v2Lan2FGPppOE 705313792}

er1645v2Lan2FGPppOEIpV6DhcpClientVendorClEntry OBJECT-TYPE
   SYNTAX      Er1645v2Lan2FGPppOEIpV6DhcpClientVendorClEntry
   MAX-ACCESS  not-accessible
   STATUS      current
   DESCRIPTION
      ""
   INDEX      { er1645v2Lan2FGPppOETableIx,
                er1645v2Lan2FGPppOEIpV6DhcpClientVendorClTableIx }
   ::= {er1645v2Lan2FGPppOEIpV6DhcpClientVendorCl 1}

Er1645v2Lan2FGPppOEIpV6DhcpClientVendorClEntry ::=
   SEQUENCE
      {
      er1645v2Lan2FGPppOEIpV6DhcpClientVendorClActions
         VariableLengthTableActions,
      er1645v2Lan2FGPppOEIpV6DhcpClientVendorClTableIx
         TableIndex,
      er1645v2Lan2FGPppOEIpV6DhcpClientVendorClValueAscii
         DisplayString,
      er1645v2Lan2FGPppOEIpV6DhcpClientVendorClValueDecimal
         Integer32,
      er1645v2Lan2FGPppOEIpV6DhcpClientVendorClValueHexData
         OCTET STRING
      }

er1645v2Lan2FGPppOEIpV6DhcpClientVendorClActions OBJECT-TYPE
   SYNTAX      VariableLengthTableActions
   MAX-ACCESS  read-write
   STATUS      current
   DESCRIPTION
      "By way of this field, some manipulations
       on this table may be performed."
   ::= {er1645v2Lan2FGPppOEIpV6DhcpClientVendorClEntry 2}

er1645v2Lan2FGPppOEIpV6DhcpClientVendorClTableIx OBJECT-TYPE
   SYNTAX      TableIndex
   MAX-ACCESS  not-accessible
   STATUS      current
   DESCRIPTION
      ""
   ::= {er1645v2Lan2FGPppOEIpV6DhcpClientVendorClEntry 11}

er1645v2Lan2FGPppOEIpV6DhcpClientVendorClValueAscii OBJECT-TYPE
   SYNTAX      DisplayString
   MAX-ACCESS  read-write
   STATUS      current
   DESCRIPTION
      "Path: ethernet2.editConf.pppoEClient.ipV6.dhcp.client.vendorClassOpt.value.ascii"
   ::= {er1645v2Lan2FGPppOEIpV6DhcpClientVendorClEntry 16842752}

er1645v2Lan2FGPppOEIpV6DhcpClientVendorClValueDecimal OBJECT-TYPE
   SYNTAX      Integer32
   MAX-ACCESS  read-write
   STATUS      current
   DESCRIPTION
      "Path: ethernet2.editConf.pppoEClient.ipV6.dhcp.client.vendorClassOpt.value.decimal"
   ::= {er1645v2Lan2FGPppOEIpV6DhcpClientVendorClEntry 16908288}

er1645v2Lan2FGPppOEIpV6DhcpClientVendorClValueHexData OBJECT-TYPE
   SYNTAX      OCTET STRING
   MAX-ACCESS  read-write
   STATUS      current
   DESCRIPTION
      "Path: ethernet2.editConf.pppoEClient.ipV6.dhcp.client.vendorClassOpt.value.hexData"
   ::= {er1645v2Lan2FGPppOEIpV6DhcpClientVendorClEntry 16973824}

er1645v2Lan2FGPppOEIpV6DhcpRelayDestinations OBJECT-TYPE
   SYNTAX      SEQUENCE OF Er1645v2Lan2FGPppOEIpV6DhcpRelayDestinationsEntry
   MAX-ACCESS  not-accessible
   STATUS      current
   DESCRIPTION
      ""
   ::= {er1645v2Lan2FGPppOE 705323072}

er1645v2Lan2FGPppOEIpV6DhcpRelayDestinationsEntry OBJECT-TYPE
   SYNTAX      Er1645v2Lan2FGPppOEIpV6DhcpRelayDestinationsEntry
   MAX-ACCESS  not-accessible
   STATUS      current
   DESCRIPTION
      ""
   INDEX      { er1645v2Lan2FGPppOETableIx,
                er1645v2Lan2FGPppOEIpV6DhcpRelayDestinationsTableIx }
   ::= {er1645v2Lan2FGPppOEIpV6DhcpRelayDestinations 1}

Er1645v2Lan2FGPppOEIpV6DhcpRelayDestinationsEntry ::=
   SEQUENCE
      {
      er1645v2Lan2FGPppOEIpV6DhcpRelayDestinationsActions
         VariableLengthTableActions,
      er1645v2Lan2FGPppOEIpV6DhcpRelayDestinationsTableIx
         TableIndex,
      er1645v2Lan2FGPppOEIpV6DhcpRelayDestinationsAddress
         Ipv6Address,
      er1645v2Lan2FGPppOEIpV6DhcpRelayDestinationsInterface
         DisplayString
      }

er1645v2Lan2FGPppOEIpV6DhcpRelayDestinationsActions OBJECT-TYPE
   SYNTAX      VariableLengthTableActions
   MAX-ACCESS  read-write
   STATUS      current
   DESCRIPTION
      "By way of this field, some manipulations
       on this table may be performed."
   ::= {er1645v2Lan2FGPppOEIpV6DhcpRelayDestinationsEntry 2}

er1645v2Lan2FGPppOEIpV6DhcpRelayDestinationsTableIx OBJECT-TYPE
   SYNTAX      TableIndex
   MAX-ACCESS  not-accessible
   STATUS      current
   DESCRIPTION
      ""
   ::= {er1645v2Lan2FGPppOEIpV6DhcpRelayDestinationsEntry 11}

er1645v2Lan2FGPppOEIpV6DhcpRelayDestinationsAddress OBJECT-TYPE
   SYNTAX      Ipv6Address
   MAX-ACCESS  read-write
   STATUS      current
   DESCRIPTION
      "Path: ethernet2.editConf.pppoEClient.ipV6.dhcp.relay.destinations.address

       ipv6 address"
   ::= {er1645v2Lan2FGPppOEIpV6DhcpRelayDestinationsEntry 16777216}

er1645v2Lan2FGPppOEIpV6DhcpRelayDestinationsInterface OBJECT-TYPE
   SYNTAX      DisplayString
   MAX-ACCESS  read-write
   STATUS      current
   DESCRIPTION
      "Path: ethernet2.editConf.pppoEClient.ipV6.dhcp.relay.destinations.interface"
   ::= {er1645v2Lan2FGPppOEIpV6DhcpRelayDestinationsEntry 33554432}


er1645v2Lan2FGPppoEServer OBJECT-TYPE
   SYNTAX      DisplayString
   MAX-ACCESS  read-write
   STATUS      current
   DESCRIPTION
      "Path: ethernet2.editConf.pppoEServer
       Info: ppp server name on interface"
   ::= {er1645v2Lan2FG 37}


er1645v2Lan2FGMediaType OBJECT-TYPE
   SYNTAX      INTEGER
               {
               utp (1),
               sfp (2),
               auto (3)
               }
   MAX-ACCESS  read-write
   STATUS      current
   DESCRIPTION
      "Path: ethernet2.editConf.mediaType

       Possibilities:
               utp   (1)
               sfp   (2)
               auto   (3)"
   ::= {er1645v2Lan2FG 38}


er1645v2Lan2FGInboundHwPriority OBJECT IDENTIFIER ::= {er1645v2Lan2FG 231}

er1645v2Lan2FGInboundHwPrioritySSC OBJECT IDENTIFIER ::= {er1645v2Lan2FGInboundHwPriority 1}

er1645v2Lan2FGInboundHwPriorityEntry OBJECT IDENTIFIER ::= {er1645v2Lan2FGInboundHwPrioritySSC 1}

er1645v2Lan2FGInboundHwPriorityNone OBJECT-TYPE
   SYNTAX      OCTET STRING
   MAX-ACCESS  read-write
   STATUS      current
   DESCRIPTION
      "Path: ethernet2.editConf.inboundHwPriority.none"
   ::= {er1645v2Lan2FGInboundHwPriorityEntry 16777216}

er1645v2Lan2FGInboundHwPriorityMapCosToQueueP0 OBJECT-TYPE
   SYNTAX      INTEGER
               {
               queue1 (1),
               queue2 (2)
               }
   MAX-ACCESS  read-write
   STATUS      current
   DESCRIPTION
      "Path: ethernet2.editConf.inboundHwPriority.mapCosToQueue.p0

       Possibilities:
               queue1   (1)
               queue2   (2)"
   ::= {er1645v2Lan2FGInboundHwPriorityEntry 33619968}

er1645v2Lan2FGInboundHwPriorityMapCosToQueueP1 OBJECT-TYPE
   SYNTAX      INTEGER
               {
               queue1 (1),
               queue2 (2)
               }
   MAX-ACCESS  read-write
   STATUS      current
   DESCRIPTION
      "Path: ethernet2.editConf.inboundHwPriority.mapCosToQueue.p1

       Possibilities:
               queue1   (1)
               queue2   (2)"
   ::= {er1645v2Lan2FGInboundHwPriorityEntry 33685504}

er1645v2Lan2FGInboundHwPriorityMapCosToQueueP2 OBJECT-TYPE
   SYNTAX      INTEGER
               {
               queue1 (1),
               queue2 (2)
               }
   MAX-ACCESS  read-write
   STATUS      current
   DESCRIPTION
      "Path: ethernet2.editConf.inboundHwPriority.mapCosToQueue.p2

       Possibilities:
               queue1   (1)
               queue2   (2)"
   ::= {er1645v2Lan2FGInboundHwPriorityEntry 33751040}

er1645v2Lan2FGInboundHwPriorityMapCosToQueueP3 OBJECT-TYPE
   SYNTAX      INTEGER
               {
               queue1 (1),
               queue2 (2)
               }
   MAX-ACCESS  read-write
   STATUS      current
   DESCRIPTION
      "Path: ethernet2.editConf.inboundHwPriority.mapCosToQueue.p3

       Possibilities:
               queue1   (1)
               queue2   (2)"
   ::= {er1645v2Lan2FGInboundHwPriorityEntry 33816576}

er1645v2Lan2FGInboundHwPriorityMapCosToQueueP4 OBJECT-TYPE
   SYNTAX      INTEGER
               {
               queue1 (1),
               queue2 (2)
               }
   MAX-ACCESS  read-write
   STATUS      current
   DESCRIPTION
      "Path: ethernet2.editConf.inboundHwPriority.mapCosToQueue.p4

       Possibilities:
               queue1   (1)
               queue2   (2)"
   ::= {er1645v2Lan2FGInboundHwPriorityEntry 33882112}

er1645v2Lan2FGInboundHwPriorityMapCosToQueueP5 OBJECT-TYPE
   SYNTAX      INTEGER
               {
               queue1 (1),
               queue2 (2)
               }
   MAX-ACCESS  read-write
   STATUS      current
   DESCRIPTION
      "Path: ethernet2.editConf.inboundHwPriority.mapCosToQueue.p5

       Possibilities:
               queue1   (1)
               queue2   (2)"
   ::= {er1645v2Lan2FGInboundHwPriorityEntry 33947648}

er1645v2Lan2FGInboundHwPriorityMapCosToQueueP6 OBJECT-TYPE
   SYNTAX      INTEGER
               {
               queue1 (1),
               queue2 (2)
               }
   MAX-ACCESS  read-write
   STATUS      current
   DESCRIPTION
      "Path: ethernet2.editConf.inboundHwPriority.mapCosToQueue.p6

       Possibilities:
               queue1   (1)
               queue2   (2)"
   ::= {er1645v2Lan2FGInboundHwPriorityEntry 34013184}

er1645v2Lan2FGInboundHwPriorityMapCosToQueueP7 OBJECT-TYPE
   SYNTAX      INTEGER
               {
               queue1 (1),
               queue2 (2)
               }
   MAX-ACCESS  read-write
   STATUS      current
   DESCRIPTION
      "Path: ethernet2.editConf.inboundHwPriority.mapCosToQueue.p7

       Possibilities:
               queue1   (1)
               queue2   (2)"
   ::= {er1645v2Lan2FGInboundHwPriorityEntry 34078720}

er1645v2Lan2FGInboundHwPriorityMapDscpToQueue OBJECT-TYPE
   SYNTAX      SEQUENCE OF Er1645v2Lan2FGInboundHwPriorityMapDscpToQueueEntry
   MAX-ACCESS  not-accessible
   STATUS      current
   DESCRIPTION
      ""
   ::= {er1645v2Lan2FGInboundHwPriority 50331648}

er1645v2Lan2FGInboundHwPriorityMapDscpToQueueEntry OBJECT-TYPE
   SYNTAX      Er1645v2Lan2FGInboundHwPriorityMapDscpToQueueEntry
   MAX-ACCESS  not-accessible
   STATUS      current
   DESCRIPTION
      ""
   INDEX      { er1645v2Lan2FGInboundHwPriorityMapDscpToQueueTableIx }
   ::= {er1645v2Lan2FGInboundHwPriorityMapDscpToQueue 1}

Er1645v2Lan2FGInboundHwPriorityMapDscpToQueueEntry ::=
   SEQUENCE
      {
      er1645v2Lan2FGInboundHwPriorityMapDscpToQueueActions
         VariableLengthTableActions,
      er1645v2Lan2FGInboundHwPriorityMapDscpToQueueTableIx
         TableIndex,
      er1645v2Lan2FGInboundHwPriorityMapDscpToQueueStartDscp
         INTEGER,
      er1645v2Lan2FGInboundHwPriorityMapDscpToQueueEndDscp
         INTEGER,
      er1645v2Lan2FGInboundHwPriorityMapDscpToQueueQueue
         INTEGER
      }

er1645v2Lan2FGInboundHwPriorityMapDscpToQueueActions OBJECT-TYPE
   SYNTAX      VariableLengthTableActions
   MAX-ACCESS  read-write
   STATUS      current
   DESCRIPTION
      "By way of this field, some manipulations
       on this table may be performed."
   ::= {er1645v2Lan2FGInboundHwPriorityMapDscpToQueueEntry 2}

er1645v2Lan2FGInboundHwPriorityMapDscpToQueueTableIx OBJECT-TYPE
   SYNTAX      TableIndex
   MAX-ACCESS  not-accessible
   STATUS      current
   DESCRIPTION
      ""
   ::= {er1645v2Lan2FGInboundHwPriorityMapDscpToQueueEntry 11}

er1645v2Lan2FGInboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet2.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan2FGInboundHwPriorityMapDscpToQueueEntry 16777216}

er1645v2Lan2FGInboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet2.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan2FGInboundHwPriorityMapDscpToQueueEntry 33554432}

er1645v2Lan2FGInboundHwPriorityMapDscpToQueueQueue OBJECT-TYPE
   SYNTAX      INTEGER
               {
               queue1 (1),
               queue2 (2)
               }
   MAX-ACCESS  read-write
   STATUS      current
   DESCRIPTION
      "Path: ethernet2.editConf.inboundHwPriority.mapDscpToQueue.queue

       Possibilities:
               queue1   (1)
               queue2   (2)"
   ::= {er1645v2Lan2FGInboundHwPriorityMapDscpToQueueEntry 50331648}


er1645v2Lan2FGName OBJECT-TYPE
   SYNTAX      DisplayString
   MAX-ACCESS  read-write
   STATUS      current
   DESCRIPTION
      "Path: ethernet2.editConf.name
       Info: config interface name"
   ::= {er1645v2Lan2FG 2}



sr1645v2Lan2FG OBJECT IDENTIFIER ::= {r1645v2Lan2FG 14}


sr1645v2Lan2FGDescr OBJECT-TYPE
   SYNTAX      DisplayString
   MAX-ACCESS  read-only
   STATUS      current
   DESCRIPTION
      "Path: ethernet2.status.ifDescr
       Info: ifDescr"
   ::= {sr1645v2Lan2FG 101}


sr1645v2Lan2FGType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet2.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2Lan2FG 102}


sr1645v2Lan2FGMtu OBJECT-TYPE
   SYNTAX      Integer32
   MAX-ACCESS  read-only
   STATUS      current
   DESCRIPTION
      "Path: ethernet2.status.ifMtu
       Info: ifMtu"
   ::= {sr1645v2Lan2FG 103}


sr1645v2Lan2FGOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.ifOperStatus
       Info: ifOperStatus

       Possibilities:
               up   (1)
               down   (2)
               testing   (3)
               unknown   (4)
               dormant   (5)
               notPresent   (6)
               lowerLayerDown   (7)"
   ::= {sr1645v2Lan2FG 107}


sr1645v2Lan2FGLastChange OBJECT-TYPE
   SYNTAX      TimeTicks
   MAX-ACCESS  read-only
   STATUS      current
   DESCRIPTION
      "Path: ethernet2.status.ifLastChange
       Info: ifLastChange

       Time in centi-second."
   ::= {sr1645v2Lan2FG 108}


sr1645v2Lan2FGLastChangeD OBJECT-TYPE
   SYNTAX      DisplayString
   MAX-ACCESS  read-only
   STATUS      current
   DESCRIPTION
      "Path: ethernet2.status.ifLastChangeDate
       Info: ifLastChangeDate"
   ::= {sr1645v2Lan2FG 183}


sr1645v2Lan2FGSpeed OBJECT-TYPE
   SYNTAX      Gauge32
   MAX-ACCESS  read-only
   STATUS      current
   DESCRIPTION
      "Path: ethernet2.status.ifSpeed
       Info: ifSpeed

       32 bit unsigned gauge value."
   ::= {sr1645v2Lan2FG 104}


sr1645v2Lan2FGSnmpIndex OBJECT-TYPE
   SYNTAX      Integer32
   MAX-ACCESS  read-only
   STATUS      current
   DESCRIPTION
      "Path: ethernet2.status.snmpIndex
       Info: SNMP index assigned to this object"
   ::= {sr1645v2Lan2FG 269}


sr1645v2Lan2FGIp OBJECT IDENTIFIER ::= {sr1645v2Lan2FG 16}

sr1645v2Lan2FGIpSSC OBJECT IDENTIFIER ::= {sr1645v2Lan2FGIp 1}

sr1645v2Lan2FGIpEntry OBJECT IDENTIFIER ::= {sr1645v2Lan2FGIpSSC 1}

sr1645v2Lan2FGIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.ip.status

       Possibilities:
               up   (1)
               down   (2)
               testing   (3)
               unknown   (4)
               dormant   (5)
               notPresent   (6)
               lowerLayerDown   (7)"
   ::= {sr1645v2Lan2FGIpEntry 1795162112}

sr1645v2Lan2FGIpAddress OBJECT-TYPE
   SYNTAX      IpAddress
   MAX-ACCESS  read-only
   STATUS      current
   DESCRIPTION
      "Path: ethernet2.status.ip.address"
   ::= {sr1645v2Lan2FGIpEntry 2030043136}

sr1645v2Lan2FGIpNetMask OBJECT-TYPE
   SYNTAX      IpAddress
   MAX-ACCESS  read-only
   STATUS      current
   DESCRIPTION
      "Path: ethernet2.status.ip.netMask"
   ::= {sr1645v2Lan2FGIpEntry 2063597568}

sr1645v2Lan2FGIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet2.status.ip.dhcp.status

       Possibilities:
               none   (0)
               selecting   (1)
               requesting   (2)
               rebinding   (3)
               bound   (4)
               renewing   (5)
               rebooting   (6)
               initreboot   (7)"
   ::= {sr1645v2Lan2FGIpEntry 402718720}

sr1645v2Lan2FGIpDhcpLeaseTime OBJECT-TYPE
   SYNTAX      TimeTicks
   MAX-ACCESS  read-only
   STATUS      current
   DESCRIPTION
      "Path: ethernet2.status.ip.dhcp.leaseTime

       Time in centi-second."
   ::= {sr1645v2Lan2FGIpEntry 402784256}

sr1645v2Lan2FGIpSecondaryIp OBJECT-TYPE
   SYNTAX      SEQUENCE OF Sr1645v2Lan2FGIpSecondaryIpEntry
   MAX-ACCESS  not-accessible
   STATUS      current
   DESCRIPTION
      ""
   ::= {sr1645v2Lan2FGIp 385875968}

sr1645v2Lan2FGIpSecondaryIpEntry OBJECT-TYPE
   SYNTAX      Sr1645v2Lan2FGIpSecondaryIpEntry
   MAX-ACCESS  not-accessible
   STATUS      current
   DESCRIPTION
      ""
   INDEX      { sr1645v2Lan2FGIpSecondaryIpTableIx }
   ::= {sr1645v2Lan2FGIpSecondaryIp 1}

Sr1645v2Lan2FGIpSecondaryIpEntry ::=
   SEQUENCE
      {
      sr1645v2Lan2FGIpSecondaryIpTableIx
         TableIndex,
      sr1645v2Lan2FGIpSecondaryIpAddress
         IpAddress,
      sr1645v2Lan2FGIpSecondaryIpNetMask
         IpAddress
      }

sr1645v2Lan2FGIpSecondaryIpTableIx OBJECT-TYPE
   SYNTAX      TableIndex
   MAX-ACCESS  not-accessible
   STATUS      current
   DESCRIPTION
      ""
   ::= {sr1645v2Lan2FGIpSecondaryIpEntry 11}

sr1645v2Lan2FGIpSecondaryIpAddress OBJECT-TYPE
   SYNTAX      IpAddress
   MAX-ACCESS  read-only
   STATUS      current
   DESCRIPTION
      "Path: ethernet2.status.ip.secondaryIp.address"
   ::= {sr1645v2Lan2FGIpSecondaryIpEntry 2030043136}

sr1645v2Lan2FGIpSecondaryIpNetMask OBJECT-TYPE
   SYNTAX      IpAddress
   MAX-ACCESS  read-only
   STATUS      current
   DESCRIPTION
      "Path: ethernet2.status.ip.secondaryIp.netMask"
   ::= {sr1645v2Lan2FGIpSecondaryIpEntry 2063597568}


sr1645v2Lan2FGArpCache OBJECT IDENTIFIER ::= {sr1645v2Lan2FG 11}

sr1645v2Lan2FGArpCacheSSCTable OBJECT-TYPE
   SYNTAX      SEQUENCE OF Sr1645v2Lan2FGArpCacheEntry
   MAX-ACCESS  not-accessible
   STATUS      current
   DESCRIPTION
      "arp cache of ethernet interface"
   ::= {sr1645v2Lan2FGArpCache 1}

sr1645v2Lan2FGArpCacheEntry OBJECT-TYPE
   SYNTAX      Sr1645v2Lan2FGArpCacheEntry
   MAX-ACCESS  not-accessible
   STATUS      current
   DESCRIPTION
      ""
   INDEX      { sr1645v2Lan2FGArpCacheTableIx }
   ::= {sr1645v2Lan2FGArpCacheSSCTable 1}

Sr1645v2Lan2FGArpCacheEntry ::=
   SEQUENCE
      {
      sr1645v2Lan2FGArpCacheTableIx
         TableIndex,
      sr1645v2Lan2FGArpCacheMacAddress
         OCTET STRING,
      sr1645v2Lan2FGArpCacheIpAddress
         IpAddress,
      sr1645v2Lan2FGArpCacheType
         INTEGER,
      sr1645v2Lan2FGArpCacheTimeOut
         TimeTicks
      }

sr1645v2Lan2FGArpCacheTableIx OBJECT-TYPE
   SYNTAX      TableIndex
   MAX-ACCESS  not-accessible
   STATUS      current
   DESCRIPTION
      ""
   ::= {sr1645v2Lan2FGArpCacheEntry 11}

sr1645v2Lan2FGArpCacheMacAddress OBJECT-TYPE
   SYNTAX      OCTET STRING
   MAX-ACCESS  read-only
   STATUS      current
   DESCRIPTION
      "Path: ethernet2.status.arpCache.macAddress

       MAC address."
   ::= {sr1645v2Lan2FGArpCacheEntry 16777216}

sr1645v2Lan2FGArpCacheIpAddress OBJECT-TYPE
   SYNTAX      IpAddress
   MAX-ACCESS  read-only
   STATUS      current
   DESCRIPTION
      "Path: ethernet2.status.arpCache.ipAddress"
   ::= {sr1645v2Lan2FGArpCacheEntry 33554432}

sr1645v2Lan2FGArpCacheType OBJECT-TYPE
   SYNTAX      INTEGER
               {
               static (0),
               dynamic (1)
               }
   MAX-ACCESS  read-only
   STATUS      current
   DESCRIPTION
      "Path: ethernet2.status.arpCache.type

       Possibilities:
               static   (0)
               dynamic   (1)"
   ::= {sr1645v2Lan2FGArpCacheEntry 50331648}

sr1645v2Lan2FGArpCacheTimeOut OBJECT-TYPE
   SYNTAX      TimeTicks
   MAX-ACCESS  read-only
   STATUS      current
   DESCRIPTION
      "Path: ethernet2.status.arpCache.timeOut

       Time in centi-second."
   ::= {sr1645v2Lan2FGArpCacheEntry 67108864}


sr1645v2Lan2FGBrS OBJECT IDENTIFIER ::= {sr1645v2Lan2FG 28}

sr1645v2Lan2FGBrSSSC OBJECT IDENTIFIER ::= {sr1645v2Lan2FGBrS 1}

sr1645v2Lan2FGBrSEntry OBJECT IDENTIFIER ::= {sr1645v2Lan2FGBrSSSC 1}

sr1645v2Lan2FGBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet2.status.bridging.status

       Possibilities:
               disabled   (0)
               discarding   (1)
               learning   (2)
               forwarding   (3)
               backupBlockedIntfDown   (256)
               backupBlockedIntfUp   (259)
               shutdown   (255)"
   ::= {sr1645v2Lan2FGBrSEntry 16777216}

sr1645v2Lan2FGBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: ethernet2.status.bridging.spanningTree.portRole

       Possibilities:
               none   (0)
               root   (1)
               designated   (2)
               alternate   (3)
               backup   (4)
               disabled   (5)
               master   (6)"
   ::= {sr1645v2Lan2FGBrSEntry 33619968}

sr1645v2Lan2FGBrSStPortId OBJECT-TYPE
   SYNTAX      Integer32
   MAX-ACCESS  read-only
   STATUS      current
   DESCRIPTION
      "Path: ethernet2.status.bridging.spanningTree.portId"
   ::= {sr1645v2Lan2FGBrSEntry 33685504}

sr1645v2Lan2FGBrSStPpCostExtPathCost OBJECT-TYPE
   SYNTAX      Integer32
   MAX-ACCESS  read-only
   STATUS      current
   DESCRIPTION
      "Path: ethernet2.status.bridging.spanningTree.portPathCosts.extPathCost"
   ::= {sr1645v2Lan2FGBrSEntry 33751296}

sr1645v2Lan2FGBrSStPpCostIntPathCost OBJECT-TYPE
   SYNTAX      Integer32
   MAX-ACCESS  read-only
   STATUS      current
   DESCRIPTION
      "Path: ethernet2.status.bridging.spanningTree.portPathCosts.intPathCost"
   ::= {sr1645v2Lan2FGBrSEntry 33751552}

sr1645v2Lan2FGBrSStExtRpCost OBJECT-TYPE
   SYNTAX      Integer32
   MAX-ACCESS  read-only
   STATUS      current
   DESCRIPTION
      "Path: ethernet2.status.bridging.spanningTree.extRootPathCost"
   ::= {sr1645v2Lan2FGBrSEntry 33816576}

sr1645v2Lan2FGBrSStIntRpCost OBJECT-TYPE
   SYNTAX      Integer32
   MAX-ACCESS  read-only
   STATUS      current
   DESCRIPTION
      "Path: ethernet2.status.bridging.spanningTree.intRootPathCost"
   ::= {sr1645v2Lan2FGBrSEntry 33882112}

sr1645v2Lan2FGBrSStDesBrIdPriority OBJECT-TYPE
   SYNTAX      Integer32
   MAX-ACCESS  read-only
   STATUS      current
   DESCRIPTION
      "Path: ethernet2.status.bridging.spanningTree.designatedBridgeId.priority"
   ::= {sr1645v2Lan2FGBrSEntry 33947904}

sr1645v2Lan2FGBrSStDesBrIdMacAddress OBJECT-TYPE
   SYNTAX      OCTET STRING
   MAX-ACCESS  read-only
   STATUS      current
   DESCRIPTION
      "Path: ethernet2.status.bridging.spanningTree.designatedBridgeId.macAddress

       MAC address."
   ::= {sr1645v2Lan2FGBrSEntry 33948160}

sr1645v2Lan2FGBrSStDesPrtId OBJECT-TYPE
   SYNTAX      Integer32
   MAX-ACCESS  read-only
   STATUS      current
   DESCRIPTION
      "Path: ethernet2.status.bridging.spanningTree.designatedPortId"
   ::= {sr1645v2Lan2FGBrSEntry 34013184}

sr1645v2Lan2FGBrSStDesInt OBJECT-TYPE
   SYNTAX      INTEGER
               {
               no (0),
               yes (1)
               }
   MAX-ACCESS  read-only
   STATUS      current
   DESCRIPTION
      "Path: ethernet2.status.bridging.spanningTree.designatedOrInternal

       Possibilities:
               no   (0)
               yes   (1)"
   ::= {sr1645v2Lan2FGBrSEntry 34078720}

sr1645v2Lan2FGBrSStEdgeDetection OBJECT-TYPE
   SYNTAX      INTEGER
               {
               none (0),
               edge (1),
               notEdge (2)
               }
   MAX-ACCESS  read-only
   STATUS      current
   DESCRIPTION
      "Path: ethernet2.status.bridging.spanningTree.edgeDetection

       Possibilities:
               none   (0)
               edge   (1)
               notEdge   (2)"
   ::= {sr1645v2Lan2FGBrSEntry 34144256}


sr1645v2Lan2FGMacAddress OBJECT-TYPE
   SYNTAX      OCTET STRING
   MAX-ACCESS  read-only
   STATUS      current
   DESCRIPTION
      "Path: ethernet2.status.macAddress
       Info: ifPhysAddress

       MAC address."
   ::= {sr1645v2Lan2FG 105}


sr1645v2Lan2FGIpAdEntBcastAddr OBJECT-TYPE
   SYNTAX      Integer32
   MAX-ACCESS  read-only
   STATUS      current
   DESCRIPTION
      "Path: ethernet2.status.ipAdEntBcastAddr
       Info: ipAdEntBcastAddr"
   ::= {sr1645v2Lan2FG 124}


sr1645v2Lan2FGIpAdEntReasmMaxSize OBJECT-TYPE
   SYNTAX      Integer32
   MAX-ACCESS  read-only
   STATUS      current
   DESCRIPTION
      "Path: ethernet2.status.ipAdEntReasmMaxSize
       Info: ipAdEntReasmMaxSize"
   ::= {sr1645v2Lan2FG 125}


sr1645v2Lan2FGAdapter OBJECT IDENTIFIER ::= {sr1645v2Lan2FG 145}

sr1645v2Lan2FGAdapterSSC OBJECT IDENTIFIER ::= {sr1645v2Lan2FGAdapter 1}

sr1645v2Lan2FGAdapterEntry OBJECT IDENTIFIER ::= {sr1645v2Lan2FGAdapterSSC 1}

sr1645v2Lan2FGAdapterSpeed OBJECT-TYPE
   SYNTAX      INTEGER
               {
               s10 (0),
               s100 (1),
               s1000 (2),
               s200 (3)
               }
   MAX-ACCESS  read-only
   STATUS      current
   DESCRIPTION
      "Path: ethernet2.status.adapter.speed

       Possibilities:
               10   (0)
               100   (1)
               1000   (2)
               200   (3)"
   ::= {sr1645v2Lan2FGAdapterEntry 16777216}

sr1645v2Lan2FGAdapterDuplex OBJECT-TYPE
   SYNTAX      INTEGER
               {
               halfDuplex (0),
               fullDuplex (1)
               }
   MAX-ACCESS  read-only
   STATUS      current
   DESCRIPTION
      "Path: ethernet2.status.adapter.duplex

       Possibilities:
               halfDuplex   (0)
               fullDuplex   (1)"
   ::= {sr1645v2Lan2FGAdapterEntry 33554432}


sr1645v2Lan2FGOam OBJECT IDENTIFIER ::= {sr1645v2Lan2FG 901}

sr1645v2Lan2FGOamSSC OBJECT IDENTIFIER ::= {sr1645v2Lan2FGOam 1}

sr1645v2Lan2FGOamEntry OBJECT IDENTIFIER ::= {sr1645v2Lan2FGOamSSC 1}

sr1645v2Lan2FGOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: ethernet2.status.oam.discovery

       Possibilities:
               fault   (0)
               sendLocal   (1)
               passiveWait   (2)
               sendLocalRemote   (3)
               sendLocalRemoteOk   (4)
               sendAny   (5)"
   ::= {sr1645v2Lan2FGOamEntry 16777216}

sr1645v2Lan2FGOamLoopback OBJECT-TYPE
   SYNTAX      INTEGER
               {
               idle (0),
               waiting (1),
               localRunning (2),
               remoteRunning (3)
               }
   MAX-ACCESS  read-only
   STATUS      current
   DESCRIPTION
      "Path: ethernet2.status.oam.loopback

       Possibilities:
               idle   (0)
               waiting   (1)
               localRunning   (2)
               remoteRunning   (3)"
   ::= {sr1645v2Lan2FGOamEntry 33554432}

sr1645v2Lan2FGOamLocalInfoVersion OBJECT-TYPE
   SYNTAX      Integer32
   MAX-ACCESS  read-only
   STATUS      current
   DESCRIPTION
      "Path: ethernet2.status.oam.localInfo.version"
   ::= {sr1645v2Lan2FGOamEntry 50397184}

sr1645v2Lan2FGOamLocalInfoRevision OBJECT-TYPE
   SYNTAX      Integer32
   MAX-ACCESS  read-only
   STATUS      current
   DESCRIPTION
      "Path: ethernet2.status.oam.localInfo.revision"
   ::= {sr1645v2Lan2FGOamEntry 50462720}

sr1645v2Lan2FGOamLocalInfoStateMuxAction OBJECT-TYPE
   SYNTAX      INTEGER
               {
               forwarding (0),
               discarding (1)
               }
   MAX-ACCESS  read-only
   STATUS      current
   DESCRIPTION
      "Path: ethernet2.status.oam.localInfo.state.muxAction

       Possibilities:
               forwarding   (0)
               discarding   (1)"
   ::= {sr1645v2Lan2FGOamEntry 50528512}

sr1645v2Lan2FGOamLocalInfoStateParserAction OBJECT-TYPE
   SYNTAX      INTEGER
               {
               forwarding (0),
               loopback (1),
               discarding (2),
               reserved (3)
               }
   MAX-ACCESS  read-only
   STATUS      current
   DESCRIPTION
      "Path: ethernet2.status.oam.localInfo.state.parserAction

       Possibilities:
               forwarding   (0)
               loopback   (1)
               discarding   (2)
               reserved   (3)"
   ::= {sr1645v2Lan2FGOamEntry 50528768}

sr1645v2Lan2FGOamLocalInfoOui OBJECT-TYPE
   SYNTAX      OCTET STRING
   MAX-ACCESS  read-only
   STATUS      current
   DESCRIPTION
      "Path: ethernet2.status.oam.localInfo.oui"
   ::= {sr1645v2Lan2FGOamEntry 50593792}

sr1645v2Lan2FGOamLocalInfoVendorInfo OBJECT-TYPE
   SYNTAX      OCTET STRING
   MAX-ACCESS  read-only
   STATUS      current
   DESCRIPTION
      "Path: ethernet2.status.oam.localInfo.vendorInfo"
   ::= {sr1645v2Lan2FGOamEntry 50659328}

sr1645v2Lan2FGOamLocalInfoVarRetrieval OBJECT-TYPE
   SYNTAX      INTEGER
               {
               notSupported (0),
               supported (1)
               }
   MAX-ACCESS  read-only
   STATUS      current
   DESCRIPTION
      "Path: ethernet2.status.oam.localInfo.varRetrieval

       Possibilities:
               notSupported   (0)
               supported   (1)"
   ::= {sr1645v2Lan2FGOamEntry 50724864}

sr1645v2Lan2FGOamLocalInfoLinkEvents OBJECT-TYPE
   SYNTAX      INTEGER
               {
               ignored (0),
               interpreted (1)
               }
   MAX-ACCESS  read-only
   STATUS      current
   DESCRIPTION
      "Path: ethernet2.status.oam.localInfo.linkEvents

       Possibilities:
               ignored   (0)
               interpreted   (1)"
   ::= {sr1645v2Lan2FGOamEntry 50790400}

sr1645v2Lan2FGOamLocalInfoLoopback OBJECT-TYPE
   SYNTAX      INTEGER
               {
               notSupported (0),
               supported (1)
               }
   MAX-ACCESS  read-only
   STATUS      current
   DESCRIPTION
      "Path: ethernet2.status.oam.localInfo.loopback

       Possibilities:
               notSupported   (0)
               supported   (1)"
   ::= {sr1645v2Lan2FGOamEntry 50855936}

sr1645v2Lan2FGOamLocalInfoUnidirectional OBJECT-TYPE
   SYNTAX      INTEGER
               {
               notSupported (0),
               supported (1)
               }
   MAX-ACCESS  read-only
   STATUS      current
   DESCRIPTION
      "Path: ethernet2.status.oam.localInfo.unidirectional

       Possibilities:
               notSupported   (0)
               supported   (1)"
   ::= {sr1645v2Lan2FGOamEntry 50921472}

sr1645v2Lan2FGOamLocalInfoMode OBJECT-TYPE
   SYNTAX      INTEGER
               {
               passive (0),
               active (1)
               }
   MAX-ACCESS  read-only
   STATUS      current
   DESCRIPTION
      "Path: ethernet2.status.oam.localInfo.mode

       Possibilities:
               passive   (0)
               active   (1)"
   ::= {sr1645v2Lan2FGOamEntry 50987008}

sr1645v2Lan2FGOamLocalInfoMaxPduSize OBJECT-TYPE
   SYNTAX      Integer32
   MAX-ACCESS  read-only
   STATUS      current
   DESCRIPTION
      "Path: ethernet2.status.oam.localInfo.maxPduSize"
   ::= {sr1645v2Lan2FGOamEntry 51052544}

sr1645v2Lan2FGOamRemoteInfoVersion OBJECT-TYPE
   SYNTAX      Integer32
   MAX-ACCESS  read-only
   STATUS      current
   DESCRIPTION
      "Path: ethernet2.status.oam.remoteInfo.version"
   ::= {sr1645v2Lan2FGOamEntry 67174400}

sr1645v2Lan2FGOamRemoteInfoRevision OBJECT-TYPE
   SYNTAX      Integer32
   MAX-ACCESS  read-only
   STATUS      current
   DESCRIPTION
      "Path: ethernet2.status.oam.remoteInfo.revision"
   ::= {sr1645v2Lan2FGOamEntry 67239936}

sr1645v2Lan2FGOamRemoteInfoStateMuxAction OBJECT-TYPE
   SYNTAX      INTEGER
               {
               forwarding (0),
               discarding (1)
               }
   MAX-ACCESS  read-only
   STATUS      current
   DESCRIPTION
      "Path: ethernet2.status.oam.remoteInfo.state.muxAction

       Possibilities:
               forwarding   (0)
               discarding   (1)"
   ::= {sr1645v2Lan2FGOamEntry 67305728}

sr1645v2Lan2FGOamRemoteInfoStateParserAction OBJECT-TYPE
   SYNTAX      INTEGER
               {
               forwarding (0),
               loopback (1),
               discarding (2),
               reserved (3)
               }
   MAX-ACCESS  read-only
   STATUS      current
   DESCRIPTION
      "Path: ethernet2.status.oam.remoteInfo.state.parserAction

       Possibilities:
               forwarding   (0)
               loopback   (1)
               discarding   (2)
               reserved   (3)"
   ::= {sr1645v2Lan2FGOamEntry 67305984}

sr1645v2Lan2FGOamRemoteInfoOui OBJECT-TYPE
   SYNTAX      OCTET STRING
   MAX-ACCESS  read-only
   STATUS      current
   DESCRIPTION
      "Path: ethernet2.status.oam.remoteInfo.oui"
   ::= {sr1645v2Lan2FGOamEntry 67371008}

sr1645v2Lan2FGOamRemoteInfoVendorInfo OBJECT-TYPE
   SYNTAX      OCTET STRING
   MAX-ACCESS  read-only
   STATUS      current
   DESCRIPTION
      "Path: ethernet2.status.oam.remoteInfo.vendorInfo"
   ::= {sr1645v2Lan2FGOamEntry 67436544}

sr1645v2Lan2FGOamRemoteInfoVarRetrieval OBJECT-TYPE
   SYNTAX      INTEGER
               {
               notSupported (0),
               supported (1)
               }
   MAX-ACCESS  read-only
   STATUS      current
   DESCRIPTION
      "Path: ethernet2.status.oam.remoteInfo.varRetrieval

       Possibilities:
               notSupported   (0)
               supported   (1)"
   ::= {sr1645v2Lan2FGOamEntry 67502080}

sr1645v2Lan2FGOamRemoteInfoLinkEvents OBJECT-TYPE
   SYNTAX      INTEGER
               {
               ignored (0),
               interpreted (1)
               }
   MAX-ACCESS  read-only
   STATUS      current
   DESCRIPTION
      "Path: ethernet2.status.oam.remoteInfo.linkEvents

       Possibilities:
               ignored   (0)
               interpreted   (1)"
   ::= {sr1645v2Lan2FGOamEntry 67567616}

sr1645v2Lan2FGOamRemoteInfoLoopback OBJECT-TYPE
   SYNTAX      INTEGER
               {
               notSupported (0),
               supported (1)
               }
   MAX-ACCESS  read-only
   STATUS      current
   DESCRIPTION
      "Path: ethernet2.status.oam.remoteInfo.loopback

       Possibilities:
               notSupported   (0)
               supported   (1)"
   ::= {sr1645v2Lan2FGOamEntry 67633152}

sr1645v2Lan2FGOamRemoteInfoUnidirectional OBJECT-TYPE
   SYNTAX      INTEGER
               {
               notSupported (0),
               supported (1)
               }
   MAX-ACCESS  read-only
   STATUS      current
   DESCRIPTION
      "Path: ethernet2.status.oam.remoteInfo.unidirectional

       Possibilities:
               notSupported   (0)
               supported   (1)"
   ::= {sr1645v2Lan2FGOamEntry 67698688}

sr1645v2Lan2FGOamRemoteInfoMode OBJECT-TYPE
   SYNTAX      INTEGER
               {
               passive (0),
               active (1)
               }
   MAX-ACCESS  read-only
   STATUS      current
   DESCRIPTION
      "Path: ethernet2.status.oam.remoteInfo.mode

       Possibilities:
               passive   (0)
               active   (1)"
   ::= {sr1645v2Lan2FGOamEntry 67764224}

sr1645v2Lan2FGOamRemoteInfoMaxPduSize OBJECT-TYPE
   SYNTAX      Integer32
   MAX-ACCESS  read-only
   STATUS      current
   DESCRIPTION
      "Path: ethernet2.status.oam.remoteInfo.maxPduSize"
   ::= {sr1645v2Lan2FGOamEntry 67829760}

sr1645v2Lan2FGOamEventsErroredSymbolWindow OBJECT-TYPE
   SYNTAX      Integer32
   UNITS       "symbols"
   MAX-ACCESS  read-only
   STATUS      current
   DESCRIPTION
      "Path: ethernet2.status.oam.events.erroredSymbol.window

       unit name = symbols"
   ::= {sr1645v2Lan2FGOamEntry 83951872}

sr1645v2Lan2FGOamEventsErroredSymbolThreshold OBJECT-TYPE
   SYNTAX      OCTET STRING
   UNITS       "symbols"
   MAX-ACCESS  read-only
   STATUS      current
   DESCRIPTION
      "Path: ethernet2.status.oam.events.erroredSymbol.threshold

       unit name = symbols"
   ::= {sr1645v2Lan2FGOamEntry 83952128}

sr1645v2Lan2FGOamEventsErroredFramePeriodWindow OBJECT-TYPE
   SYNTAX      INTEGER
               {
               default (0)
               }
   UNITS       "frames"
   MAX-ACCESS  read-only
   STATUS      current
   DESCRIPTION
      "Path: ethernet2.status.oam.events.erroredFramePeriod.window

       unit name = frames

       Possibilities:
               default   (0)"
   ::= {sr1645v2Lan2FGOamEntry 84017408}

sr1645v2Lan2FGOamEventsErroredFramePeriodThreshold OBJECT-TYPE
   SYNTAX      Integer32
   UNITS       "frames"
   MAX-ACCESS  read-only
   STATUS      current
   DESCRIPTION
      "Path: ethernet2.status.oam.events.erroredFramePeriod.threshold

       unit name = frames"
   ::= {sr1645v2Lan2FGOamEntry 84017664}

sr1645v2Lan2FGOamEventsErroredFrameWindow OBJECT-TYPE
   SYNTAX      Integer32
   UNITS       "100msec"
   MAX-ACCESS  read-only
   STATUS      current
   DESCRIPTION
      "Path: ethernet2.status.oam.events.erroredFrame.window

       unit name = 100msec"
   ::= {sr1645v2Lan2FGOamEntry 84082944}

sr1645v2Lan2FGOamEventsErroredFrameThreshold OBJECT-TYPE
   SYNTAX      Integer32
   UNITS       "frames"
   MAX-ACCESS  read-only
   STATUS      current
   DESCRIPTION
      "Path: ethernet2.status.oam.events.erroredFrame.threshold

       unit name = frames"
   ::= {sr1645v2Lan2FGOamEntry 84083200}

sr1645v2Lan2FGOamEventsErroredFrameSecondsWindow OBJECT-TYPE
   SYNTAX      Integer32
   UNITS       "100msec"
   MAX-ACCESS  read-only
   STATUS      current
   DESCRIPTION
      "Path: ethernet2.status.oam.events.erroredFrameSeconds.window

       unit name = 100msec"
   ::= {sr1645v2Lan2FGOamEntry 84148480}

sr1645v2Lan2FGOamEventsErroredFrameSecondsThreshold OBJECT-TYPE
   SYNTAX      Integer32
   UNITS       "frames"
   MAX-ACCESS  read-only
   STATUS      current
   DESCRIPTION
      "Path: ethernet2.status.oam.events.erroredFrameSeconds.threshold

       unit name = frames"
   ::= {sr1645v2Lan2FGOamEntry 84148736}


sr1645v2Lan2FGOamEventLog OBJECT IDENTIFIER ::= {sr1645v2Lan2FG 911}

sr1645v2Lan2FGOamEventLogSSCTable OBJECT-TYPE
   SYNTAX      SEQUENCE OF Sr1645v2Lan2FGOamEventLogEntry
   MAX-ACCESS  not-accessible
   STATUS      current
   DESCRIPTION
      "OAM event log"
   ::= {sr1645v2Lan2FGOamEventLog 1}

sr1645v2Lan2FGOamEventLogEntry OBJECT-TYPE
   SYNTAX      Sr1645v2Lan2FGOamEventLogEntry
   MAX-ACCESS  not-accessible
   STATUS      current
   DESCRIPTION
      ""
   INDEX      { sr1645v2Lan2FGOamEventLogTableIx }
   ::= {sr1645v2Lan2FGOamEventLogSSCTable 1}

Sr1645v2Lan2FGOamEventLogEntry ::=
   SEQUENCE
      {
      sr1645v2Lan2FGOamEventLogTableIx
         TableIndex,
      sr1645v2Lan2FGOamEventLogSysUpTime
         TimeTicks,
      sr1645v2Lan2FGOamEventLogLocation
         INTEGER,
      sr1645v2Lan2FGOamEventLogType
         INTEGER,
      sr1645v2Lan2FGOamEventLogOui
         OCTET STRING,
      sr1645v2Lan2FGOamEventLogWindow
         Counter64,
      sr1645v2Lan2FGOamEventLogThreshold
         Counter64,
      sr1645v2Lan2FGOamEventLogTotal
         Counter32,
      sr1645v2Lan2FGOamEventLogValue
         Counter64,
      sr1645v2Lan2FGOamEventLogRunningTotal
         Counter64
      }

sr1645v2Lan2FGOamEventLogTableIx OBJECT-TYPE
   SYNTAX      TableIndex
   MAX-ACCESS  not-accessible
   STATUS      current
   DESCRIPTION
      ""
   ::= {sr1645v2Lan2FGOamEventLogEntry 11}

sr1645v2Lan2FGOamEventLogSysUpTime OBJECT-TYPE
   SYNTAX      TimeTicks
   MAX-ACCESS  read-only
   STATUS      current
   DESCRIPTION
      "Path: ethernet2.status.oamEventLog.sysUpTime

       Time in centi-second."
   ::= {sr1645v2Lan2FGOamEventLogEntry 16777216}

sr1645v2Lan2FGOamEventLogLocation OBJECT-TYPE
   SYNTAX      INTEGER
               {
               local (1),
               remote (2)
               }
   MAX-ACCESS  read-only
   STATUS      current
   DESCRIPTION
      "Path: ethernet2.status.oamEventLog.location

       Possibilities:
               local   (1)
               remote   (2)"
   ::= {sr1645v2Lan2FGOamEventLogEntry 33554432}

sr1645v2Lan2FGOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: ethernet2.status.oamEventLog.type

       Possibilities:
               erroredSymbols   (1)
               erroredFramePeriod   (2)
               erroredFrame   (3)
               erroredFrameSeconds   (4)
               linkFault   (256)
               dyingGasp   (257)
               criticalLink   (258)"
   ::= {sr1645v2Lan2FGOamEventLogEntry 50331648}

sr1645v2Lan2FGOamEventLogOui OBJECT-TYPE
   SYNTAX      OCTET STRING
   MAX-ACCESS  read-only
   STATUS      current
   DESCRIPTION
      "Path: ethernet2.status.oamEventLog.oui"
   ::= {sr1645v2Lan2FGOamEventLogEntry 67108864}

sr1645v2Lan2FGOamEventLogWindow OBJECT-TYPE
   SYNTAX      Counter64
   MAX-ACCESS  read-only
   STATUS      current
   DESCRIPTION
      "Path: ethernet2.status.oamEventLog.window

       64 bit unsigned wrappable counter."
   ::= {sr1645v2Lan2FGOamEventLogEntry 83886080}

sr1645v2Lan2FGOamEventLogThreshold OBJECT-TYPE
   SYNTAX      Counter64
   MAX-ACCESS  read-only
   STATUS      current
   DESCRIPTION
      "Path: ethernet2.status.oamEventLog.threshold

       64 bit unsigned wrappable counter."
   ::= {sr1645v2Lan2FGOamEventLogEntry 100663296}

sr1645v2Lan2FGOamEventLogTotal OBJECT-TYPE
   SYNTAX      Counter32
   MAX-ACCESS  read-only
   STATUS      current
   DESCRIPTION
      "Path: ethernet2.status.oamEventLog.total

       32 bit unsigned wrappable counter."
   ::= {sr1645v2Lan2FGOamEventLogEntry 117440512}

sr1645v2Lan2FGOamEventLogValue OBJECT-TYPE
   SYNTAX      Counter64
   MAX-ACCESS  read-only
   STATUS      current
   DESCRIPTION
      "Path: ethernet2.status.oamEventLog.value

       64 bit unsigned wrappable counter."
   ::= {sr1645v2Lan2FGOamEventLogEntry 134217728}

sr1645v2Lan2FGOamEventLogRunningTotal OBJECT-TYPE
   SYNTAX      Counter64
   MAX-ACCESS  read-only
   STATUS      current
   DESCRIPTION
      "Path: ethernet2.status.oamEventLog.runningTotal

       64 bit unsigned wrappable counter."
   ::= {sr1645v2Lan2FGOamEventLogEntry 150994944}


sr1645v2Lan2FGLst OBJECT IDENTIFIER ::= {sr1645v2Lan2FG 18}

sr1645v2Lan2FGLstSSC OBJECT IDENTIFIER ::= {sr1645v2Lan2FGLst 1}

sr1645v2Lan2FGLstEntry OBJECT IDENTIFIER ::= {sr1645v2Lan2FGLstSSC 1}

sr1645v2Lan2FGLstTrackedInterface OBJECT-TYPE
   SYNTAX      DisplayString
   MAX-ACCESS  read-only
   STATUS      current
   DESCRIPTION
      "Path: ethernet2.status.linkStateTracking.trackedInterface"
   ::= {sr1645v2Lan2FGLstEntry 16777216}

sr1645v2Lan2FGLstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: ethernet2.status.linkStateTracking.ifOperStatus

       Possibilities:
               up   (1)
               down   (2)
               testing   (3)
               unknown   (4)
               dormant   (5)
               notPresent   (6)
               lowerLayerDown   (7)
                  (255)"
   ::= {sr1645v2Lan2FGLstEntry 50331648}


sr1645v2Lan2FGVlan OBJECT IDENTIFIER ::= {sr1645v2Lan2FG 34}

sr1645v2Lan2FGVlanSSCTable OBJECT-TYPE
   SYNTAX      SEQUENCE OF Sr1645v2Lan2FGVlanEntry
   MAX-ACCESS  not-accessible
   STATUS      current
   DESCRIPTION
      ""
   ::= {sr1645v2Lan2FGVlan 1}

sr1645v2Lan2FGVlanEntry OBJECT-TYPE
   SYNTAX      Sr1645v2Lan2FGVlanEntry
   MAX-ACCESS  not-accessible
   STATUS      current
   DESCRIPTION
      ""
   INDEX      { sr1645v2Lan2FGVlanTableIx }
   ::= {sr1645v2Lan2FGVlanSSCTable 1}

Sr1645v2Lan2FGVlanEntry ::=
   SEQUENCE
      {
      sr1645v2Lan2FGVlanTableIx
         TableIndex,
      sr1645v2Lan2FGVlanName
         DisplayString,
      sr1645v2Lan2FGVlanMode
         INTEGER,
      sr1645v2Lan2FGVlanIfOperStatus
         INTEGER,
      sr1645v2Lan2FGVlanIfLastChange
         TimeTicks,
      sr1645v2Lan2FGVlanIfLastChangeDate
         DisplayString,
      sr1645v2Lan2FGVlanIpAddress
         IpAddress,
      sr1645v2Lan2FGVlanIpNetMask
         IpAddress,
      sr1645v2Lan2FGVlanIpRemote
         IpAddress,
      sr1645v2Lan2FGVlanIpDhcpStatus
         INTEGER,
      sr1645v2Lan2FGVlanIpDhcpLeaseTime
         TimeTicks,
      sr1645v2Lan2FGVlanIpV6State
         INTEGER,
      sr1645v2Lan2FGVlanIpV6InterfaceId
         OCTET STRING,
      sr1645v2Lan2FGVlanIpV6LinkMtu
         Integer32,
      sr1645v2Lan2FGVlanIpV6HopLimit
         Integer32,
      sr1645v2Lan2FGVlanIpV6DhcpIaid
         Counter32,
      sr1645v2Lan2FGVlanIpV6RaRcvOption
         Integer32,
      sr1645v2Lan2FGVlanBridgingStatus
         INTEGER,
      sr1645v2Lan2FGVlanBridgingSpanningTreePortRole
         INTEGER,
      sr1645v2Lan2FGVlanBridgingSpanningTreePortId
         Integer32,
      sr1645v2Lan2FGVlanBridgingSpanningTreePpCostExtPathCost
         Integer32,
      sr1645v2Lan2FGVlanBridgingSpanningTreePpCostIntPathCost
         Integer32,
      sr1645v2Lan2FGVlanBridgingSpanningTreeExtRpCost
         Integer32,
      sr1645v2Lan2FGVlanBridgingSpanningTreeIntRpCost
         Integer32,
      sr1645v2Lan2FGVlanBridgingSpanningTreeDesBrIdPriority
         Integer32,
      sr1645v2Lan2FGVlanBridgingSpanningTreeDesBrIdMacAddress
         OCTET STRING,
      sr1645v2Lan2FGVlanBridgingSpanningTreeDesPrtId
         Integer32,
      sr1645v2Lan2FGVlanBridgingSpanningTreeDesInt
         INTEGER,
      sr1645v2Lan2FGVlanBridgingSpanningTreeEdgeDetection
         INTEGER,
      sr1645v2Lan2FGVlanVlanVid
         Integer32,
      sr1645v2Lan2FGVlanPppOEthDiscState
         INTEGER,
      sr1645v2Lan2FGVlanPppOEthPeerMac
         OCTET STRING,
      sr1645v2Lan2FGVlanPppOEthServiceName
         DisplayString,
      sr1645v2Lan2FGVlanPppLcpState
         INTEGER,
      sr1645v2Lan2FGVlanPppIpcpState
         INTEGER,
      sr1645v2Lan2FGVlanPppIp6cpState
         INTEGER,
      sr1645v2Lan2FGVlanPppMyAutSt
         INTEGER,
      sr1645v2Lan2FGVlanPppHisAutSt
         INTEGER,
      sr1645v2Lan2FGVlanPppMru
         Integer32
      }

sr1645v2Lan2FGVlanTableIx OBJECT-TYPE
   SYNTAX      TableIndex
   MAX-ACCESS  not-accessible
   STATUS      current
   DESCRIPTION
      ""
   ::= {sr1645v2Lan2FGVlanEntry 11}

sr1645v2Lan2FGVlanName OBJECT-TYPE
   SYNTAX      DisplayString
   MAX-ACCESS  read-only
   STATUS      current
   DESCRIPTION
      "Path: ethernet2.status.vlan.name"
   ::= {sr1645v2Lan2FGVlanEntry 16777216}

sr1645v2Lan2FGVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet2.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan2FGVlanEntry 335544320}

sr1645v2Lan2FGVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.vlan.ifOperStatus

       Possibilities:
               up   (1)
               down   (2)
               testing   (3)
               unknown   (4)
               dormant   (5)
               notPresent   (6)
               lowerLayerDown   (7)"
   ::= {sr1645v2Lan2FGVlanEntry 1795162112}

sr1645v2Lan2FGVlanIfLastChange OBJECT-TYPE
   SYNTAX      TimeTicks
   MAX-ACCESS  read-only
   STATUS      current
   DESCRIPTION
      "Path: ethernet2.status.vlan.ifLastChange

       Time in centi-second."
   ::= {sr1645v2Lan2FGVlanEntry 1811939328}

sr1645v2Lan2FGVlanIfLastChangeDate OBJECT-TYPE
   SYNTAX      DisplayString
   MAX-ACCESS  read-only
   STATUS      current
   DESCRIPTION
      "Path: ethernet2.status.vlan.ifLastChangeDate"
   ::= {sr1645v2Lan2FGVlanEntry 3070230528}

sr1645v2Lan2FGVlanIpAddress OBJECT-TYPE
   SYNTAX      IpAddress
   MAX-ACCESS  read-only
   STATUS      current
   DESCRIPTION
      "Path: ethernet2.status.vlan.ip.address"
   ::= {sr1645v2Lan2FGVlanEntry 51380224}

sr1645v2Lan2FGVlanIpNetMask OBJECT-TYPE
   SYNTAX      IpAddress
   MAX-ACCESS  read-only
   STATUS      current
   DESCRIPTION
      "Path: ethernet2.status.vlan.ip.netMask"
   ::= {sr1645v2Lan2FGVlanEntry 51445760}

sr1645v2Lan2FGVlanIpRemote OBJECT-TYPE
   SYNTAX      IpAddress
   MAX-ACCESS  read-only
   STATUS      current
   DESCRIPTION
      "Path: ethernet2.status.vlan.ip.remote"
   ::= {sr1645v2Lan2FGVlanEntry 51511296}

sr1645v2Lan2FGVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet2.status.vlan.ip.dhcp.status

       Possibilities:
               none   (0)
               selecting   (1)
               requesting   (2)
               rebinding   (3)
               bound   (4)
               renewing   (5)
               rebooting   (6)
               initreboot   (7)"
   ::= {sr1645v2Lan2FGVlanEntry 51904768}

sr1645v2Lan2FGVlanIpDhcpLeaseTime OBJECT-TYPE
   SYNTAX      TimeTicks
   MAX-ACCESS  read-only
   STATUS      current
   DESCRIPTION
      "Path: ethernet2.status.vlan.ip.dhcp.leaseTime

       Time in centi-second."
   ::= {sr1645v2Lan2FGVlanEntry 51905024}

sr1645v2Lan2FGVlanIpV6State OBJECT-TYPE
   SYNTAX      INTEGER
               {
               disabled (0),
               enabled (1)
               }
   MAX-ACCESS  read-only
   STATUS      current
   DESCRIPTION
      "Path: ethernet2.status.vlan.ipV6.state

       Possibilities:
               disabled   (0)
               enabled   (1)"
   ::= {sr1645v2Lan2FGVlanEntry 100728832}

sr1645v2Lan2FGVlanIpV6InterfaceId OBJECT-TYPE
   SYNTAX      OCTET STRING
   MAX-ACCESS  read-only
   STATUS      current
   DESCRIPTION
      "Path: ethernet2.status.vlan.ipV6.interfaceId"
   ::= {sr1645v2Lan2FGVlanEntry 100794368}

sr1645v2Lan2FGVlanIpV6LinkMtu OBJECT-TYPE
   SYNTAX      Integer32
   MAX-ACCESS  read-only
   STATUS      current
   DESCRIPTION
      "Path: ethernet2.status.vlan.ipV6.linkMtu"
   ::= {sr1645v2Lan2FGVlanEntry 100925440}

sr1645v2Lan2FGVlanIpV6HopLimit OBJECT-TYPE
   SYNTAX      Integer32
   MAX-ACCESS  read-only
   STATUS      current
   DESCRIPTION
      "Path: ethernet2.status.vlan.ipV6.hopLimit"
   ::= {sr1645v2Lan2FGVlanEntry 100990976}

sr1645v2Lan2FGVlanIpV6DhcpIaid OBJECT-TYPE
   SYNTAX      Counter32
   MAX-ACCESS  read-only
   STATUS      current
   DESCRIPTION
      "Path: ethernet2.status.vlan.ipV6.dhcp.iaid

       32 bit unsigned wrappable counter."
   ::= {sr1645v2Lan2FGVlanEntry 101056768}

sr1645v2Lan2FGVlanIpV6RaRcvOption OBJECT-TYPE
   SYNTAX      Integer32
   MAX-ACCESS  read-only
   STATUS      current
   DESCRIPTION
      "Path: ethernet2.status.vlan.ipV6.raRcvOption

       Bit meanings:
               bit 0 = linkMtu,
               bit 1 = srcLinkLayer,
               bit 2 = prefixInfo,
               bit 3 = rdnss,
               bit 4 = dnssl"
   ::= {sr1645v2Lan2FGVlanEntry 101122048}

sr1645v2Lan2FGVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet2.status.vlan.bridging.status

       Possibilities:
               disabled   (0)
               discarding   (1)
               learning   (2)
               forwarding   (3)
               backupBlockedIntfDown   (256)
               backupBlockedIntfUp   (259)
               shutdown   (255)"
   ::= {sr1645v2Lan2FGVlanEntry 453050368}

sr1645v2Lan2FGVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: ethernet2.status.vlan.bridging.spanningTree.portRole

       Possibilities:
               none   (0)
               root   (1)
               designated   (2)
               alternate   (3)
               backup   (4)
               disabled   (5)
               master   (6)"
   ::= {sr1645v2Lan2FGVlanEntry 453116160}

sr1645v2Lan2FGVlanBridgingSpanningTreePortId OBJECT-TYPE
   SYNTAX      Integer32
   MAX-ACCESS  read-only
   STATUS      current
   DESCRIPTION
      "Path: ethernet2.status.vlan.bridging.spanningTree.portId"
   ::= {sr1645v2Lan2FGVlanEntry 453116416}

sr1645v2Lan2FGVlanBridgingSpanningTreePpCostExtPathCost OBJECT-TYPE
   SYNTAX      Integer32
   MAX-ACCESS  read-only
   STATUS      current
   DESCRIPTION
      "Path: ethernet2.status.vlan.bridging.spanningTree.portPathCosts.extPathCost"
   ::= {sr1645v2Lan2FGVlanEntry 453116673}

sr1645v2Lan2FGVlanBridgingSpanningTreePpCostIntPathCost OBJECT-TYPE
   SYNTAX      Integer32
   MAX-ACCESS  read-only
   STATUS      current
   DESCRIPTION
      "Path: ethernet2.status.vlan.bridging.spanningTree.portPathCosts.intPathCost"
   ::= {sr1645v2Lan2FGVlanEntry 453116674}

sr1645v2Lan2FGVlanBridgingSpanningTreeExtRpCost OBJECT-TYPE
   SYNTAX      Integer32
   MAX-ACCESS  read-only
   STATUS      current
   DESCRIPTION
      "Path: ethernet2.status.vlan.bridging.spanningTree.extRootPathCost"
   ::= {sr1645v2Lan2FGVlanEntry 453116928}

sr1645v2Lan2FGVlanBridgingSpanningTreeIntRpCost OBJECT-TYPE
   SYNTAX      Integer32
   MAX-ACCESS  read-only
   STATUS      current
   DESCRIPTION
      "Path: ethernet2.status.vlan.bridging.spanningTree.intRootPathCost"
   ::= {sr1645v2Lan2FGVlanEntry 453117184}

sr1645v2Lan2FGVlanBridgingSpanningTreeDesBrIdPriority OBJECT-TYPE
   SYNTAX      Integer32
   MAX-ACCESS  read-only
   STATUS      current
   DESCRIPTION
      "Path: ethernet2.status.vlan.bridging.spanningTree.designatedBridgeId.priority"
   ::= {sr1645v2Lan2FGVlanEntry 453117441}

sr1645v2Lan2FGVlanBridgingSpanningTreeDesBrIdMacAddress OBJECT-TYPE
   SYNTAX      OCTET STRING
   MAX-ACCESS  read-only
   STATUS      current
   DESCRIPTION
      "Path: ethernet2.status.vlan.bridging.spanningTree.designatedBridgeId.macAddress

       MAC address."
   ::= {sr1645v2Lan2FGVlanEntry 453117442}

sr1645v2Lan2FGVlanBridgingSpanningTreeDesPrtId OBJECT-TYPE
   SYNTAX      Integer32
   MAX-ACCESS  read-only
   STATUS      current
   DESCRIPTION
      "Path: ethernet2.status.vlan.bridging.spanningTree.designatedPortId"
   ::= {sr1645v2Lan2FGVlanEntry 453117696}

sr1645v2Lan2FGVlanBridgingSpanningTreeDesInt OBJECT-TYPE
   SYNTAX      INTEGER
               {
               no (0),
               yes (1)
               }
   MAX-ACCESS  read-only
   STATUS      current
   DESCRIPTION
      "Path: ethernet2.status.vlan.bridging.spanningTree.designatedOrInternal

       Possibilities:
               no   (0)
               yes   (1)"
   ::= {sr1645v2Lan2FGVlanEntry 453117952}

sr1645v2Lan2FGVlanBridgingSpanningTreeEdgeDetection OBJECT-TYPE
   SYNTAX      INTEGER
               {
               none (0),
               edge (1),
               notEdge (2)
               }
   MAX-ACCESS  read-only
   STATUS      current
   DESCRIPTION
      "Path: ethernet2.status.vlan.bridging.spanningTree.edgeDetection

       Possibilities:
               none   (0)
               edge   (1)
               notEdge   (2)"
   ::= {sr1645v2Lan2FGVlanEntry 453118208}

sr1645v2Lan2FGVlanVlanVid OBJECT-TYPE
   SYNTAX      Integer32
   MAX-ACCESS  read-only
   STATUS      current
   DESCRIPTION
      "Path: ethernet2.status.vlan.vlan.vid"
   ::= {sr1645v2Lan2FGVlanEntry 234946560}

sr1645v2Lan2FGVlanPppOEthDiscState OBJECT-TYPE
   SYNTAX      INTEGER
               {
               idle (0),
               waitForPADO (1),
               waitForPADS (2),
               established (3)
               }
   MAX-ACCESS  read-only
   STATUS      current
   DESCRIPTION
      "Path: ethernet2.status.vlan.pppOverEth.discState

       Possibilities:
               idle   (0)
               waitForPADO   (1)
               waitForPADS   (2)
               established   (3)"
   ::= {sr1645v2Lan2FGVlanEntry 67174400}

sr1645v2Lan2FGVlanPppOEthPeerMac OBJECT-TYPE
   SYNTAX      OCTET STRING
   MAX-ACCESS  read-only
   STATUS      current
   DESCRIPTION
      "Path: ethernet2.status.vlan.pppOverEth.remoteMacAddress

       MAC address."
   ::= {sr1645v2Lan2FGVlanEntry 67239936}

sr1645v2Lan2FGVlanPppOEthServiceName OBJECT-TYPE
   SYNTAX      DisplayString
   MAX-ACCESS  read-only
   STATUS      current
   DESCRIPTION
      "Path: ethernet2.status.vlan.pppOverEth.serviceName"
   ::= {sr1645v2Lan2FGVlanEntry 67305472}

sr1645v2Lan2FGVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGVlanEntry 83951616}

sr1645v2Lan2FGVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGVlanEntry 84017152}

sr1645v2Lan2FGVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGVlanEntry 84869120}

sr1645v2Lan2FGVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet2.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan2FGVlanEntry 84541440}

sr1645v2Lan2FGVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet2.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan2FGVlanEntry 84606976}

sr1645v2Lan2FGVlanPppMru OBJECT-TYPE
   SYNTAX      Integer32
   MAX-ACCESS  read-only
   STATUS      current
   DESCRIPTION
      "Path: ethernet2.status.vlan.ppp.mru"
   ::= {sr1645v2Lan2FGVlanEntry 84934656}

sr1645v2Lan2FGVlanIpSecondaryIp OBJECT-TYPE
   SYNTAX      SEQUENCE OF Sr1645v2Lan2FGVlanIpSecondaryIpEntry
   MAX-ACCESS  not-accessible
   STATUS      current
   DESCRIPTION
      ""
   ::= {sr1645v2Lan2FGVlan 51838976}

sr1645v2Lan2FGVlanIpSecondaryIpEntry OBJECT-TYPE
   SYNTAX      Sr1645v2Lan2FGVlanIpSecondaryIpEntry
   MAX-ACCESS  not-accessible
   STATUS      current
   DESCRIPTION
      ""
   INDEX      { sr1645v2Lan2FGVlanTableIx,
                sr1645v2Lan2FGVlanIpSecondaryIpTableIx }
   ::= {sr1645v2Lan2FGVlanIpSecondaryIp 1}

Sr1645v2Lan2FGVlanIpSecondaryIpEntry ::=
   SEQUENCE
      {
      sr1645v2Lan2FGVlanIpSecondaryIpTableIx
         TableIndex,
      sr1645v2Lan2FGVlanIpSecondaryIpAddress
         IpAddress,
      sr1645v2Lan2FGVlanIpSecondaryIpNetMask
         IpAddress
      }

sr1645v2Lan2FGVlanIpSecondaryIpTableIx OBJECT-TYPE
   SYNTAX      TableIndex
   MAX-ACCESS  not-accessible
   STATUS      current
   DESCRIPTION
      ""
   ::= {sr1645v2Lan2FGVlanIpSecondaryIpEntry 11}

sr1645v2Lan2FGVlanIpSecondaryIpAddress OBJECT-TYPE
   SYNTAX      IpAddress
   MAX-ACCESS  read-only
   STATUS      current
   DESCRIPTION
      "Path: ethernet2.status.vlan.ip.secondaryIp.address"
   ::= {sr1645v2Lan2FGVlanIpSecondaryIpEntry 2030043136}

sr1645v2Lan2FGVlanIpSecondaryIpNetMask OBJECT-TYPE
   SYNTAX      IpAddress
   MAX-ACCESS  read-only
   STATUS      current
   DESCRIPTION
      "Path: ethernet2.status.vlan.ip.secondaryIp.netMask"
   ::= {sr1645v2Lan2FGVlanIpSecondaryIpEntry 2063597568}

sr1645v2Lan2FGVlanIpV6Addresses OBJECT-TYPE
   SYNTAX      SEQUENCE OF Sr1645v2Lan2FGVlanIpV6AddressesEntry
   MAX-ACCESS  not-accessible
   STATUS      current
   DESCRIPTION
      ""
   ::= {sr1645v2Lan2FGVlan 100859904}

sr1645v2Lan2FGVlanIpV6AddressesEntry OBJECT-TYPE
   SYNTAX      Sr1645v2Lan2FGVlanIpV6AddressesEntry
   MAX-ACCESS  not-accessible
   STATUS      current
   DESCRIPTION
      ""
   INDEX      { sr1645v2Lan2FGVlanTableIx,
                sr1645v2Lan2FGVlanIpV6AddressesTableIx }
   ::= {sr1645v2Lan2FGVlanIpV6Addresses 1}

Sr1645v2Lan2FGVlanIpV6AddressesEntry ::=
   SEQUENCE
      {
      sr1645v2Lan2FGVlanIpV6AddressesTableIx
         TableIndex,
      sr1645v2Lan2FGVlanIpV6AddressesAddress
         Ipv6Address,
      sr1645v2Lan2FGVlanIpV6AddressesPrefixLength
         Integer32,
      sr1645v2Lan2FGVlanIpV6AddressesStatus
         INTEGER,
      sr1645v2Lan2FGVlanIpV6AddressesOrigin
         INTEGER,
      sr1645v2Lan2FGVlanIpV6AddressesFlagsInterfaceId
         INTEGER,
      sr1645v2Lan2FGVlanIpV6AddressesFlagsAnycast
         INTEGER,
      sr1645v2Lan2FGVlanIpV6AddressesTimersValidLifeTime
         TimeTicks,
      sr1645v2Lan2FGVlanIpV6AddressesTimersPrefLifeTime
         TimeTicks
      }

sr1645v2Lan2FGVlanIpV6AddressesTableIx OBJECT-TYPE
   SYNTAX      TableIndex
   MAX-ACCESS  not-accessible
   STATUS      current
   DESCRIPTION
      ""
   ::= {sr1645v2Lan2FGVlanIpV6AddressesEntry 11}

sr1645v2Lan2FGVlanIpV6AddressesAddress OBJECT-TYPE
   SYNTAX      Ipv6Address
   MAX-ACCESS  read-only
   STATUS      current
   DESCRIPTION
      "Path: ethernet2.status.vlan.ipV6.addresses.address

       ipv6 address"
   ::= {sr1645v2Lan2FGVlanIpV6AddressesEntry 16777216}

sr1645v2Lan2FGVlanIpV6AddressesPrefixLength OBJECT-TYPE
   SYNTAX      Integer32
   MAX-ACCESS  read-only
   STATUS      current
   DESCRIPTION
      "Path: ethernet2.status.vlan.ipV6.addresses.prefixLength"
   ::= {sr1645v2Lan2FGVlanIpV6AddressesEntry 33554432}

sr1645v2Lan2FGVlanIpV6AddressesStatus OBJECT-TYPE
   SYNTAX      INTEGER
               {
               invalid (0),
               tentative (1),
               deprecated (2),
               preferred (3)
               }
   MAX-ACCESS  read-only
   STATUS      current
   DESCRIPTION
      "Path: ethernet2.status.vlan.ipV6.addresses.status

       Possibilities:
               invalid   (0)
               tentative   (1)
               deprecated   (2)
               preferred   (3)"
   ::= {sr1645v2Lan2FGVlanIpV6AddressesEntry 50331648}

sr1645v2Lan2FGVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.vlan.ipV6.addresses.origin

       Possibilities:
               unknown   (0)
               manual   (1)
               generalPrefix   (2)
               statelessAuto   (3)
               statefullAuto   (4)"
   ::= {sr1645v2Lan2FGVlanIpV6AddressesEntry 67108864}

sr1645v2Lan2FGVlanIpV6AddressesFlagsInterfaceId OBJECT-TYPE
   SYNTAX      INTEGER
               {
               no (0),
               yes (1)
               }
   MAX-ACCESS  read-only
   STATUS      current
   DESCRIPTION
      "Path: ethernet2.status.vlan.ipV6.addresses.flags.interfaceId

       Possibilities:
               no   (0)
               yes   (1)"
   ::= {sr1645v2Lan2FGVlanIpV6AddressesEntry 83951616}

sr1645v2Lan2FGVlanIpV6AddressesFlagsAnycast OBJECT-TYPE
   SYNTAX      INTEGER
               {
               no (0),
               yes (1)
               }
   MAX-ACCESS  read-only
   STATUS      current
   DESCRIPTION
      "Path: ethernet2.status.vlan.ipV6.addresses.flags.anycast

       Possibilities:
               no   (0)
               yes   (1)"
   ::= {sr1645v2Lan2FGVlanIpV6AddressesEntry 84017152}

sr1645v2Lan2FGVlanIpV6AddressesTimersValidLifeTime OBJECT-TYPE
   SYNTAX      TimeTicks
   MAX-ACCESS  read-only
   STATUS      current
   DESCRIPTION
      "Path: ethernet2.status.vlan.ipV6.addresses.timers.validLifeTime

       Time in centi-second."
   ::= {sr1645v2Lan2FGVlanIpV6AddressesEntry 100794368}

sr1645v2Lan2FGVlanIpV6AddressesTimersPrefLifeTime OBJECT-TYPE
   SYNTAX      TimeTicks
   MAX-ACCESS  read-only
   STATUS      current
   DESCRIPTION
      "Path: ethernet2.status.vlan.ipV6.addresses.timers.prefLifeTime

       Time in centi-second."
   ::= {sr1645v2Lan2FGVlanIpV6AddressesEntry 100728832}

sr1645v2Lan2FGVlanVlanArpCache OBJECT-TYPE
   SYNTAX      SEQUENCE OF Sr1645v2Lan2FGVlanVlanArpCacheEntry
   MAX-ACCESS  not-accessible
   STATUS      current
   DESCRIPTION
      ""
   ::= {sr1645v2Lan2FGVlan 235601920}

sr1645v2Lan2FGVlanVlanArpCacheEntry OBJECT-TYPE
   SYNTAX      Sr1645v2Lan2FGVlanVlanArpCacheEntry
   MAX-ACCESS  not-accessible
   STATUS      current
   DESCRIPTION
      ""
   INDEX      { sr1645v2Lan2FGVlanTableIx,
                sr1645v2Lan2FGVlanVlanArpCacheTableIx }
   ::= {sr1645v2Lan2FGVlanVlanArpCache 1}

Sr1645v2Lan2FGVlanVlanArpCacheEntry ::=
   SEQUENCE
      {
      sr1645v2Lan2FGVlanVlanArpCacheTableIx
         TableIndex,
      sr1645v2Lan2FGVlanVlanArpCacheMacAddress
         OCTET STRING,
      sr1645v2Lan2FGVlanVlanArpCacheIpAddress
         IpAddress,
      sr1645v2Lan2FGVlanVlanArpCacheType
         INTEGER,
      sr1645v2Lan2FGVlanVlanArpCacheTimeOut
         TimeTicks
      }

sr1645v2Lan2FGVlanVlanArpCacheTableIx OBJECT-TYPE
   SYNTAX      TableIndex
   MAX-ACCESS  not-accessible
   STATUS      current
   DESCRIPTION
      ""
   ::= {sr1645v2Lan2FGVlanVlanArpCacheEntry 11}

sr1645v2Lan2FGVlanVlanArpCacheMacAddress OBJECT-TYPE
   SYNTAX      OCTET STRING
   MAX-ACCESS  read-only
   STATUS      current
   DESCRIPTION
      "Path: ethernet2.status.vlan.vlan.arpCache.macAddress

       MAC address."
   ::= {sr1645v2Lan2FGVlanVlanArpCacheEntry 16777216}

sr1645v2Lan2FGVlanVlanArpCacheIpAddress OBJECT-TYPE
   SYNTAX      IpAddress
   MAX-ACCESS  read-only
   STATUS      current
   DESCRIPTION
      "Path: ethernet2.status.vlan.vlan.arpCache.ipAddress"
   ::= {sr1645v2Lan2FGVlanVlanArpCacheEntry 33554432}

sr1645v2Lan2FGVlanVlanArpCacheType OBJECT-TYPE
   SYNTAX      INTEGER
               {
               static (0),
               dynamic (1)
               }
   MAX-ACCESS  read-only
   STATUS      current
   DESCRIPTION
      "Path: ethernet2.status.vlan.vlan.arpCache.type

       Possibilities:
               static   (0)
               dynamic   (1)"
   ::= {sr1645v2Lan2FGVlanVlanArpCacheEntry 50331648}

sr1645v2Lan2FGVlanVlanArpCacheTimeOut OBJECT-TYPE
   SYNTAX      TimeTicks
   MAX-ACCESS  read-only
   STATUS      current
   DESCRIPTION
      "Path: ethernet2.status.vlan.vlan.arpCache.timeOut

       Time in centi-second."
   ::= {sr1645v2Lan2FGVlanVlanArpCacheEntry 67108864}


sr1645v2Lan2FGPppOE OBJECT IDENTIFIER ::= {sr1645v2Lan2FG 36}

sr1645v2Lan2FGPppOESSCTable OBJECT-TYPE
   SYNTAX      SEQUENCE OF Sr1645v2Lan2FGPppOEEntry
   MAX-ACCESS  not-accessible
   STATUS      current
   DESCRIPTION
      ""
   ::= {sr1645v2Lan2FGPppOE 1}

sr1645v2Lan2FGPppOEEntry OBJECT-TYPE
   SYNTAX      Sr1645v2Lan2FGPppOEEntry
   MAX-ACCESS  not-accessible
   STATUS      current
   DESCRIPTION
      ""
   INDEX      { sr1645v2Lan2FGPppOETableIx }
   ::= {sr1645v2Lan2FGPppOESSCTable 1}

Sr1645v2Lan2FGPppOEEntry ::=
   SEQUENCE
      {
      sr1645v2Lan2FGPppOETableIx
         TableIndex,
      sr1645v2Lan2FGPppOEName
         DisplayString,
      sr1645v2Lan2FGPppOEMode
         INTEGER,
      sr1645v2Lan2FGPppOEIfOperStatus
         INTEGER,
      sr1645v2Lan2FGPppOEIfLastChange
         TimeTicks,
      sr1645v2Lan2FGPppOEIfLastChangeDate
         DisplayString,
      sr1645v2Lan2FGPppOEIpAddress
         IpAddress,
      sr1645v2Lan2FGPppOEIpNetMask
         IpAddress,
      sr1645v2Lan2FGPppOEIpRemote
         IpAddress,
      sr1645v2Lan2FGPppOEPppOEthDiscState
         INTEGER,
      sr1645v2Lan2FGPppOEPppOEthPeerMac
         OCTET STRING,
      sr1645v2Lan2FGPppOEPppOEthServiceName
         DisplayString,
      sr1645v2Lan2FGPppOEPppLcpState
         INTEGER,
      sr1645v2Lan2FGPppOEPppIpcpState
         INTEGER,
      sr1645v2Lan2FGPppOEPppIp6cpState
         INTEGER,
      sr1645v2Lan2FGPppOEPppMyAutSt
         INTEGER,
      sr1645v2Lan2FGPppOEPppHisAutSt
         INTEGER,
      sr1645v2Lan2FGPppOEPppMru
         Integer32,
      sr1645v2Lan2FGPppOEIpV6State
         INTEGER,
      sr1645v2Lan2FGPppOEIpV6InterfaceId
         OCTET STRING,
      sr1645v2Lan2FGPppOEIpV6LinkMtu
         Integer32,
      sr1645v2Lan2FGPppOEIpV6HopLimit
         Integer32,
      sr1645v2Lan2FGPppOEIpV6DhcpIaid
         Counter32,
      sr1645v2Lan2FGPppOEIpV6RaRcvOption
         Integer32
      }

sr1645v2Lan2FGPppOETableIx OBJECT-TYPE
   SYNTAX      TableIndex
   MAX-ACCESS  not-accessible
   STATUS      current
   DESCRIPTION
      ""
   ::= {sr1645v2Lan2FGPppOEEntry 11}

sr1645v2Lan2FGPppOEName OBJECT-TYPE
   SYNTAX      DisplayString
   MAX-ACCESS  read-only
   STATUS      current
   DESCRIPTION
      "Path: ethernet2.status.pppoEClient.name"
   ::= {sr1645v2Lan2FGPppOEEntry 16777216}

sr1645v2Lan2FGPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet2.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan2FGPppOEEntry 335544320}

sr1645v2Lan2FGPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.pppoEClient.ifOperStatus

       Possibilities:
               up   (1)
               down   (2)
               testing   (3)
               unknown   (4)
               dormant   (5)
               notPresent   (6)
               lowerLayerDown   (7)"
   ::= {sr1645v2Lan2FGPppOEEntry 1795162112}

sr1645v2Lan2FGPppOEIfLastChange OBJECT-TYPE
   SYNTAX      TimeTicks
   MAX-ACCESS  read-only
   STATUS      current
   DESCRIPTION
      "Path: ethernet2.status.pppoEClient.ifLastChange

       Time in centi-second."
   ::= {sr1645v2Lan2FGPppOEEntry 1811939328}

sr1645v2Lan2FGPppOEIfLastChangeDate OBJECT-TYPE
   SYNTAX      DisplayString
   MAX-ACCESS  read-only
   STATUS      current
   DESCRIPTION
      "Path: ethernet2.status.pppoEClient.ifLastChangeDate"
   ::= {sr1645v2Lan2FGPppOEEntry 3070230528}

sr1645v2Lan2FGPppOEIpAddress OBJECT-TYPE
   SYNTAX      IpAddress
   MAX-ACCESS  read-only
   STATUS      current
   DESCRIPTION
      "Path: ethernet2.status.pppoEClient.ip.address"
   ::= {sr1645v2Lan2FGPppOEEntry 51380224}

sr1645v2Lan2FGPppOEIpNetMask OBJECT-TYPE
   SYNTAX      IpAddress
   MAX-ACCESS  read-only
   STATUS      current
   DESCRIPTION
      "Path: ethernet2.status.pppoEClient.ip.netMask"
   ::= {sr1645v2Lan2FGPppOEEntry 51445760}

sr1645v2Lan2FGPppOEIpRemote OBJECT-TYPE
   SYNTAX      IpAddress
   MAX-ACCESS  read-only
   STATUS      current
   DESCRIPTION
      "Path: ethernet2.status.pppoEClient.ip.remote"
   ::= {sr1645v2Lan2FGPppOEEntry 51511296}

sr1645v2Lan2FGPppOEPppOEthDiscState OBJECT-TYPE
   SYNTAX      INTEGER
               {
               idle (0),
               waitForPADO (1),
               waitForPADS (2),
               established (3)
               }
   MAX-ACCESS  read-only
   STATUS      current
   DESCRIPTION
      "Path: ethernet2.status.pppoEClient.pppOverEth.discState

       Possibilities:
               idle   (0)
               waitForPADO   (1)
               waitForPADS   (2)
               established   (3)"
   ::= {sr1645v2Lan2FGPppOEEntry 67174400}

sr1645v2Lan2FGPppOEPppOEthPeerMac OBJECT-TYPE
   SYNTAX      OCTET STRING
   MAX-ACCESS  read-only
   STATUS      current
   DESCRIPTION
      "Path: ethernet2.status.pppoEClient.pppOverEth.remoteMacAddress

       MAC address."
   ::= {sr1645v2Lan2FGPppOEEntry 67239936}

sr1645v2Lan2FGPppOEPppOEthServiceName OBJECT-TYPE
   SYNTAX      DisplayString
   MAX-ACCESS  read-only
   STATUS      current
   DESCRIPTION
      "Path: ethernet2.status.pppoEClient.pppOverEth.serviceName"
   ::= {sr1645v2Lan2FGPppOEEntry 67305472}

sr1645v2Lan2FGPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGPppOEEntry 83951616}

sr1645v2Lan2FGPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGPppOEEntry 84017152}

sr1645v2Lan2FGPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2FGPppOEEntry 84869120}

sr1645v2Lan2FGPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet2.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan2FGPppOEEntry 84541440}

sr1645v2Lan2FGPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet2.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan2FGPppOEEntry 84606976}

sr1645v2Lan2FGPppOEPppMru OBJECT-TYPE
   SYNTAX      Integer32
   MAX-ACCESS  read-only
   STATUS      current
   DESCRIPTION
      "Path: ethernet2.status.pppoEClient.ppp.mru"
   ::= {sr1645v2Lan2FGPppOEEntry 84934656}

sr1645v2Lan2FGPppOEIpV6State OBJECT-TYPE
   SYNTAX      INTEGER
               {
               disabled (0),
               enabled (1)
               }
   MAX-ACCESS  read-only
   STATUS      current
   DESCRIPTION
      "Path: ethernet2.status.pppoEClient.ipV6.state

       Possibilities:
               disabled   (0)
               enabled   (1)"
   ::= {sr1645v2Lan2FGPppOEEntry 100728832}

sr1645v2Lan2FGPppOEIpV6InterfaceId OBJECT-TYPE
   SYNTAX      OCTET STRING
   MAX-ACCESS  read-only
   STATUS      current
   DESCRIPTION
      "Path: ethernet2.status.pppoEClient.ipV6.interfaceId"
   ::= {sr1645v2Lan2FGPppOEEntry 100794368}

sr1645v2Lan2FGPppOEIpV6LinkMtu OBJECT-TYPE
   SYNTAX      Integer32
   MAX-ACCESS  read-only
   STATUS      current
   DESCRIPTION
      "Path: ethernet2.status.pppoEClient.ipV6.linkMtu"
   ::= {sr1645v2Lan2FGPppOEEntry 100925440}

sr1645v2Lan2FGPppOEIpV6HopLimit OBJECT-TYPE
   SYNTAX      Integer32
   MAX-ACCESS  read-only
   STATUS      current
   DESCRIPTION
      "Path: ethernet2.status.pppoEClient.ipV6.hopLimit"
   ::= {sr1645v2Lan2FGPppOEEntry 100990976}

sr1645v2Lan2FGPppOEIpV6DhcpIaid OBJECT-TYPE
   SYNTAX      Counter32
   MAX-ACCESS  read-only
   STATUS      current
   DESCRIPTION
      "Path: ethernet2.status.pppoEClient.ipV6.dhcp.iaid

       32 bit unsigned wrappable counter."
   ::= {sr1645v2Lan2FGPppOEEntry 101056768}

sr1645v2Lan2FGPppOEIpV6RaRcvOption OBJECT-TYPE
   SYNTAX      Integer32
   MAX-ACCESS  read-only
   STATUS      current
   DESCRIPTION
      "Path: ethernet2.status.pppoEClient.ipV6.raRcvOption

       Bit meanings:
               bit 0 = linkMtu,
               bit 1 = srcLinkLayer,
               bit 2 = prefixInfo,
               bit 3 = rdnss,
               bit 4 = dnssl"
   ::= {sr1645v2Lan2FGPppOEEntry 101122048}

sr1645v2Lan2FGPppOEIpV6Addresses OBJECT-TYPE
   SYNTAX      SEQUENCE OF Sr1645v2Lan2FGPppOEIpV6AddressesEntry
   MAX-ACCESS  not-accessible
   STATUS      current
   DESCRIPTION
      ""
   ::= {sr1645v2Lan2FGPppOE 100859904}

sr1645v2Lan2FGPppOEIpV6AddressesEntry OBJECT-TYPE
   SYNTAX      Sr1645v2Lan2FGPppOEIpV6AddressesEntry
   MAX-ACCESS  not-accessible
   STATUS      current
   DESCRIPTION
      ""
   INDEX      { sr1645v2Lan2FGPppOETableIx,
                sr1645v2Lan2FGPppOEIpV6AddressesTableIx }
   ::= {sr1645v2Lan2FGPppOEIpV6Addresses 1}

Sr1645v2Lan2FGPppOEIpV6AddressesEntry ::=
   SEQUENCE
      {
      sr1645v2Lan2FGPppOEIpV6AddressesTableIx
         TableIndex,
      sr1645v2Lan2FGPppOEIpV6AddressesAddress
         Ipv6Address,
      sr1645v2Lan2FGPppOEIpV6AddressesPrefixLength
         Integer32,
      sr1645v2Lan2FGPppOEIpV6AddressesStatus
         INTEGER,
      sr1645v2Lan2FGPppOEIpV6AddressesOrigin
         INTEGER,
      sr1645v2Lan2FGPppOEIpV6AddressesFlagsInterfaceId
         INTEGER,
      sr1645v2Lan2FGPppOEIpV6AddressesFlagsAnycast
         INTEGER,
      sr1645v2Lan2FGPppOEIpV6AddressesTimersValidLifeTime
         TimeTicks,
      sr1645v2Lan2FGPppOEIpV6AddressesTimersPrefLifeTime
         TimeTicks
      }

sr1645v2Lan2FGPppOEIpV6AddressesTableIx OBJECT-TYPE
   SYNTAX      TableIndex
   MAX-ACCESS  not-accessible
   STATUS      current
   DESCRIPTION
      ""
   ::= {sr1645v2Lan2FGPppOEIpV6AddressesEntry 11}

sr1645v2Lan2FGPppOEIpV6AddressesAddress OBJECT-TYPE
   SYNTAX      Ipv6Address
   MAX-ACCESS  read-only
   STATUS      current
   DESCRIPTION
      "Path: ethernet2.status.pppoEClient.ipV6.addresses.address

       ipv6 address"
   ::= {sr1645v2Lan2FGPppOEIpV6AddressesEntry 16777216}

sr1645v2Lan2FGPppOEIpV6AddressesPrefixLength OBJECT-TYPE
   SYNTAX      Integer32
   MAX-ACCESS  read-only
   STATUS      current
   DESCRIPTION
      "Path: ethernet2.status.pppoEClient.ipV6.addresses.prefixLength"
   ::= {sr1645v2Lan2FGPppOEIpV6AddressesEntry 33554432}

sr1645v2Lan2FGPppOEIpV6AddressesStatus OBJECT-TYPE
   SYNTAX      INTEGER
               {
               invalid (0),
               tentative (1),
               deprecated (2),
               preferred (3)
               }
   MAX-ACCESS  read-only
   STATUS      current
   DESCRIPTION
      "Path: ethernet2.status.pppoEClient.ipV6.addresses.status

       Possibilities:
               invalid   (0)
               tentative   (1)
               deprecated   (2)
               preferred   (3)"
   ::= {sr1645v2Lan2FGPppOEIpV6AddressesEntry 50331648}

sr1645v2Lan2FGPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.pppoEClient.ipV6.addresses.origin

       Possibilities:
               unknown   (0)
               manual   (1)
               generalPrefix   (2)
               statelessAuto   (3)
               statefullAuto   (4)"
   ::= {sr1645v2Lan2FGPppOEIpV6AddressesEntry 67108864}

sr1645v2Lan2FGPppOEIpV6AddressesFlagsInterfaceId OBJECT-TYPE
   SYNTAX      INTEGER
               {
               no (0),
               yes (1)
               }
   MAX-ACCESS  read-only
   STATUS      current
   DESCRIPTION
      "Path: ethernet2.status.pppoEClient.ipV6.addresses.flags.interfaceId

       Possibilities:
               no   (0)
               yes   (1)"
   ::= {sr1645v2Lan2FGPppOEIpV6AddressesEntry 83951616}

sr1645v2Lan2FGPppOEIpV6AddressesFlagsAnycast OBJECT-TYPE
   SYNTAX      INTEGER
               {
               no (0),
               yes (1)
               }
   MAX-ACCESS  read-only
   STATUS      current
   DESCRIPTION
      "Path: ethernet2.status.pppoEClient.ipV6.addresses.flags.anycast

       Possibilities:
               no   (0)
               yes   (1)"
   ::= {sr1645v2Lan2FGPppOEIpV6AddressesEntry 84017152}

sr1645v2Lan2FGPppOEIpV6AddressesTimersValidLifeTime OBJECT-TYPE
   SYNTAX      TimeTicks
   MAX-ACCESS  read-only
   STATUS      current
   DESCRIPTION
      "Path: ethernet2.status.pppoEClient.ipV6.addresses.timers.validLifeTime

       Time in centi-second."
   ::= {sr1645v2Lan2FGPppOEIpV6AddressesEntry 100794368}

sr1645v2Lan2FGPppOEIpV6AddressesTimersPrefLifeTime OBJECT-TYPE
   SYNTAX      TimeTicks
   MAX-ACCESS  read-only
   STATUS      current
   DESCRIPTION
      "Path: ethernet2.status.pppoEClient.ipV6.addresses.timers.prefLifeTime

       Time in centi-second."
   ::= {sr1645v2Lan2FGPppOEIpV6AddressesEntry 100728832}


sr1645v2Lan2FGDot1x OBJECT IDENTIFIER ::= {sr1645v2Lan2FG 190}

sr1645v2Lan2FGDot1xSSCTable OBJECT-TYPE
   SYNTAX      SEQUENCE OF Sr1645v2Lan2FGDot1xEntry
   MAX-ACCESS  not-accessible
   STATUS      current
   DESCRIPTION
      "Ethernet Switch VLAN Table"
   ::= {sr1645v2Lan2FGDot1x 1}

sr1645v2Lan2FGDot1xEntry OBJECT-TYPE
   SYNTAX      Sr1645v2Lan2FGDot1xEntry
   MAX-ACCESS  not-accessible
   STATUS      current
   DESCRIPTION
      ""
   INDEX      { sr1645v2Lan2FGDot1xTableIx }
   ::= {sr1645v2Lan2FGDot1xSSCTable 1}

Sr1645v2Lan2FGDot1xEntry ::=
   SEQUENCE
      {
      sr1645v2Lan2FGDot1xTableIx
         TableIndex,
      sr1645v2Lan2FGDot1xRemote
         OCTET STRING,
      sr1645v2Lan2FGDot1xAuthorized
         INTEGER,
      sr1645v2Lan2FGDot1xAuthenticator
         INTEGER,
      sr1645v2Lan2FGDot1xBackEnd
         INTEGER,
      sr1645v2Lan2FGDot1xRetries
         Integer32,
      sr1645v2Lan2FGDot1xReAuthTime
         TimeTicks,
      sr1645v2Lan2FGDot1xHoldTime
         TimeTicks
      }

sr1645v2Lan2FGDot1xTableIx OBJECT-TYPE
   SYNTAX      TableIndex
   MAX-ACCESS  not-accessible
   STATUS      current
   DESCRIPTION
      ""
   ::= {sr1645v2Lan2FGDot1xEntry 11}

sr1645v2Lan2FGDot1xRemote OBJECT-TYPE
   SYNTAX      OCTET STRING
   MAX-ACCESS  read-only
   STATUS      current
   DESCRIPTION
      "Path: ethernet2.status.dot1x.remote

       MAC address."
   ::= {sr1645v2Lan2FGDot1xEntry 16777216}

sr1645v2Lan2FGDot1xAuthorized OBJECT-TYPE
   SYNTAX      INTEGER
               {
               no (0),
               yes (1)
               }
   MAX-ACCESS  read-only
   STATUS      current
   DESCRIPTION
      "Path: ethernet2.status.dot1x.authorized

       Possibilities:
               no   (0)
               yes   (1)"
   ::= {sr1645v2Lan2FGDot1xEntry 33554432}

sr1645v2Lan2FGDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: ethernet2.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1645v2Lan2FGDot1xEntry 50331648}

sr1645v2Lan2FGDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: ethernet2.status.dot1x.backEnd

       Possibilities:
               preInit   (0)
               initialize   (1)
               idle   (2)
               request   (3)
               response   (4)
               success   (5)
               failure   (6)
               radiusTimeout   (7)
               timeout   (8)"
   ::= {sr1645v2Lan2FGDot1xEntry 67108864}

sr1645v2Lan2FGDot1xRetries OBJECT-TYPE
   SYNTAX      Integer32
   MAX-ACCESS  read-only
   STATUS      current
   DESCRIPTION
      "Path: ethernet2.status.dot1x.retries"
   ::= {sr1645v2Lan2FGDot1xEntry 83886080}

sr1645v2Lan2FGDot1xReAuthTime OBJECT-TYPE
   SYNTAX      TimeTicks
   MAX-ACCESS  read-only
   STATUS      current
   DESCRIPTION
      "Path: ethernet2.status.dot1x.reAuthTime

       Time in centi-second."
   ::= {sr1645v2Lan2FGDot1xEntry 100663296}

sr1645v2Lan2FGDot1xHoldTime OBJECT-TYPE
   SYNTAX      TimeTicks
   MAX-ACCESS  read-only
   STATUS      current
   DESCRIPTION
      "Path: ethernet2.status.dot1x.holdTime

       Time in centi-second."
   ::= {sr1645v2Lan2FGDot1xEntry 117440512}


sr1645v2Lan2FGIpV6 OBJECT IDENTIFIER ::= {sr1645v2Lan2FG 17}

sr1645v2Lan2FGIpV6SSC OBJECT IDENTIFIER ::= {sr1645v2Lan2FGIpV6 1}

sr1645v2Lan2FGIpV6Entry OBJECT IDENTIFIER ::= {sr1645v2Lan2FGIpV6SSC 1}

sr1645v2Lan2FGIpV6State OBJECT-TYPE
   SYNTAX      INTEGER
               {
               disabled (0),
               enabled (1)
               }
   MAX-ACCESS  read-only
   STATUS      current
   DESCRIPTION
      "Path: ethernet2.status.ipV6.state

       Possibilities:
               disabled   (0)
               enabled   (1)"
   ::= {sr1645v2Lan2FGIpV6Entry 16777216}

sr1645v2Lan2FGIpV6InterfaceId OBJECT-TYPE
   SYNTAX      OCTET STRING
   MAX-ACCESS  read-only
   STATUS      current
   DESCRIPTION
      "Path: ethernet2.status.ipV6.interfaceId"
   ::= {sr1645v2Lan2FGIpV6Entry 33554432}

sr1645v2Lan2FGIpV6LinkMtu OBJECT-TYPE
   SYNTAX      Integer32
   MAX-ACCESS  read-only
   STATUS      current
   DESCRIPTION
      "Path: ethernet2.status.ipV6.linkMtu"
   ::= {sr1645v2Lan2FGIpV6Entry 67108864}

sr1645v2Lan2FGIpV6HopLimit OBJECT-TYPE
   SYNTAX      Integer32
   MAX-ACCESS  read-only
   STATUS      current
   DESCRIPTION
      "Path: ethernet2.status.ipV6.hopLimit"
   ::= {sr1645v2Lan2FGIpV6Entry 83886080}

sr1645v2Lan2FGIpV6DhcpIaid OBJECT-TYPE
   SYNTAX      Counter32
   MAX-ACCESS  read-only
   STATUS      current
   DESCRIPTION
      "Path: ethernet2.status.ipV6.dhcp.iaid

       32 bit unsigned wrappable counter."
   ::= {sr1645v2Lan2FGIpV6Entry 100728832}

sr1645v2Lan2FGIpV6RaRcvOption OBJECT-TYPE
   SYNTAX      Integer32
   MAX-ACCESS  read-only
   STATUS      current
   DESCRIPTION
      "Path: ethernet2.status.ipV6.raRcvOption

       Bit meanings:
               bit 0 = linkMtu,
               bit 1 = srcLinkLayer,
               bit 2 = prefixInfo,
               bit 3 = rdnss,
               bit 4 = dnssl"
   ::= {sr1645v2Lan2FGIpV6Entry 117440512}

sr1645v2Lan2FGIpV6Addresses OBJECT-TYPE
   SYNTAX      SEQUENCE OF Sr1645v2Lan2FGIpV6AddressesEntry
   MAX-ACCESS  not-accessible
   STATUS      current
   DESCRIPTION
      ""
   ::= {sr1645v2Lan2FGIpV6 50331648}

sr1645v2Lan2FGIpV6AddressesEntry OBJECT-TYPE
   SYNTAX      Sr1645v2Lan2FGIpV6AddressesEntry
   MAX-ACCESS  not-accessible
   STATUS      current
   DESCRIPTION
      ""
   INDEX      { sr1645v2Lan2FGIpV6AddressesTableIx }
   ::= {sr1645v2Lan2FGIpV6Addresses 1}

Sr1645v2Lan2FGIpV6AddressesEntry ::=
   SEQUENCE
      {
      sr1645v2Lan2FGIpV6AddressesTableIx
         TableIndex,
      sr1645v2Lan2FGIpV6AddressesAddress
         Ipv6Address,
      sr1645v2Lan2FGIpV6AddressesPrefixLength
         Integer32,
      sr1645v2Lan2FGIpV6AddressesStatus
         INTEGER,
      sr1645v2Lan2FGIpV6AddressesOrigin
         INTEGER,
      sr1645v2Lan2FGIpV6AddressesFlagsInterfaceId
         INTEGER,
      sr1645v2Lan2FGIpV6AddressesFlagsAnycast
         INTEGER,
      sr1645v2Lan2FGIpV6AddressesTimersValidLifeTime
         TimeTicks,
      sr1645v2Lan2FGIpV6AddressesTimersPrefLifeTime
         TimeTicks
      }

sr1645v2Lan2FGIpV6AddressesTableIx OBJECT-TYPE
   SYNTAX      TableIndex
   MAX-ACCESS  not-accessible
   STATUS      current
   DESCRIPTION
      ""
   ::= {sr1645v2Lan2FGIpV6AddressesEntry 11}

sr1645v2Lan2FGIpV6AddressesAddress OBJECT-TYPE
   SYNTAX      Ipv6Address
   MAX-ACCESS  read-only
   STATUS      current
   DESCRIPTION
      "Path: ethernet2.status.ipV6.addresses.address

       ipv6 address"
   ::= {sr1645v2Lan2FGIpV6AddressesEntry 16777216}

sr1645v2Lan2FGIpV6AddressesPrefixLength OBJECT-TYPE
   SYNTAX      Integer32
   MAX-ACCESS  read-only
   STATUS      current
   DESCRIPTION
      "Path: ethernet2.status.ipV6.addresses.prefixLength"
   ::= {sr1645v2Lan2FGIpV6AddressesEntry 33554432}

sr1645v2Lan2FGIpV6AddressesStatus OBJECT-TYPE
   SYNTAX      INTEGER
               {
               invalid (0),
               tentative (1),
               deprecated (2),
               preferred (3)
               }
   MAX-ACCESS  read-only
   STATUS      current
   DESCRIPTION
      "Path: ethernet2.status.ipV6.addresses.status

       Possibilities:
               invalid   (0)
               tentative   (1)
               deprecated   (2)
               preferred   (3)"
   ::= {sr1645v2Lan2FGIpV6AddressesEntry 50331648}

sr1645v2Lan2FGIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.ipV6.addresses.origin

       Possibilities:
               unknown   (0)
               manual   (1)
               generalPrefix   (2)
               statelessAuto   (3)
               statefullAuto   (4)"
   ::= {sr1645v2Lan2FGIpV6AddressesEntry 67108864}

sr1645v2Lan2FGIpV6AddressesFlagsInterfaceId OBJECT-TYPE
   SYNTAX      INTEGER
               {
               no (0),
               yes (1)
               }
   MAX-ACCESS  read-only
   STATUS      current
   DESCRIPTION
      "Path: ethernet2.status.ipV6.addresses.flags.interfaceId

       Possibilities:
               no   (0)
               yes   (1)"
   ::= {sr1645v2Lan2FGIpV6AddressesEntry 83951616}

sr1645v2Lan2FGIpV6AddressesFlagsAnycast OBJECT-TYPE
   SYNTAX      INTEGER
               {
               no (0),
               yes (1)
               }
   MAX-ACCESS  read-only
   STATUS      current
   DESCRIPTION
      "Path: ethernet2.status.ipV6.addresses.flags.anycast

       Possibilities:
               no   (0)
               yes   (1)"
   ::= {sr1645v2Lan2FGIpV6AddressesEntry 84017152}

sr1645v2Lan2FGIpV6AddressesTimersValidLifeTime OBJECT-TYPE
   SYNTAX      TimeTicks
   MAX-ACCESS  read-only
   STATUS      current
   DESCRIPTION
      "Path: ethernet2.status.ipV6.addresses.timers.validLifeTime

       Time in centi-second."
   ::= {sr1645v2Lan2FGIpV6AddressesEntry 100794368}

sr1645v2Lan2FGIpV6AddressesTimersPrefLifeTime OBJECT-TYPE
   SYNTAX      TimeTicks
   MAX-ACCESS  read-only
   STATUS      current
   DESCRIPTION
      "Path: ethernet2.status.ipV6.addresses.timers.prefLifeTime

       Time in centi-second."
   ::= {sr1645v2Lan2FGIpV6AddressesEntry 100728832}


sr1645v2Lan2FGMediaType OBJECT-TYPE
   SYNTAX      INTEGER
               {
               utp (1),
               sfp (2),
               down (255)
               }
   MAX-ACCESS  read-only
   STATUS      current
   DESCRIPTION
      "Path: ethernet2.status.mediaType

       Possibilities:
               utp   (1)
               sfp   (2)
               down   (255)"
   ::= {sr1645v2Lan2FG 500}



pr1645v2Lan2FG OBJECT IDENTIFIER ::= {r1645v2Lan2FG 12}


pr1645v2Lan2FGInOctets OBJECT-TYPE
   SYNTAX      Counter64
   MAX-ACCESS  read-only
   STATUS      current
   DESCRIPTION
      "Path: ethernet2.performance.ifInOctets
       Info: ifInOctets

       64 bit unsigned wrappable counter."
   ::= {pr1645v2Lan2FG 109}


pr1645v2Lan2FGInUcast OBJECT-TYPE
   SYNTAX      Counter64
   MAX-ACCESS  read-only
   STATUS      current
   DESCRIPTION
      "Path: ethernet2.performance.ifInUcastPkts
       Info: ifInUcastPkts

       64 bit unsigned wrappable counter."
   ::= {pr1645v2Lan2FG 110}


pr1645v2Lan2FGInNUcastPkts OBJECT-TYPE
   SYNTAX      Counter64
   MAX-ACCESS  read-only
   STATUS      current
   DESCRIPTION
      "Path: ethernet2.performance.ifInNUcastPkts
       Info: ifInNUcastPkts

       64 bit unsigned wrappable counter."
   ::= {pr1645v2Lan2FG 111}


pr1645v2Lan2FGInBcastPkts OBJECT-TYPE
   SYNTAX      Counter64
   MAX-ACCESS  read-only
   STATUS      current
   DESCRIPTION
      "Path: ethernet2.performance.ifInBcastPkts
       Info: ifInBcastPkts

       64 bit unsigned wrappable counter."
   ::= {pr1645v2Lan2FG 211}


pr1645v2Lan2FGInMcastPkts OBJECT-TYPE
   SYNTAX      Counter64
   MAX-ACCESS  read-only
   STATUS      current
   DESCRIPTION
      "Path: ethernet2.performance.ifInMcastPkts
       Info: ifInNUcastPkts

       64 bit unsigned wrappable counter."
   ::= {pr1645v2Lan2FG 221}


pr1645v2Lan2FGInDiscards OBJECT-TYPE
   SYNTAX      Counter64
   MAX-ACCESS  read-only
   STATUS      current
   DESCRIPTION
      "Path: ethernet2.performance.ifInDiscards
       Info: ifInDiscards

       64 bit unsigned wrappable counter."
   ::= {pr1645v2Lan2FG 112}


pr1645v2Lan2FGInErrors OBJECT-TYPE
   SYNTAX      Counter64
   MAX-ACCESS  read-only
   STATUS      current
   DESCRIPTION
      "Path: ethernet2.performance.ifInErrors
       Info: ifInErrors

       64 bit unsigned wrappable counter."
   ::= {pr1645v2Lan2FG 113}


pr1645v2Lan2FGInUnknownProtos OBJECT-TYPE
   SYNTAX      Counter64
   MAX-ACCESS  read-only
   STATUS      current
   DESCRIPTION
      "Path: ethernet2.performance.ifInUnknownProtos
       Info: ifInUnknownprotos

       64 bit unsigned wrappable counter."
   ::= {pr1645v2Lan2FG 114}


pr1645v2Lan2FGInQLen OBJECT-TYPE
   SYNTAX      Gauge32
   MAX-ACCESS  read-only
   STATUS      current
   DESCRIPTION
      "Path: ethernet2.performance.ifInQLen
       Info: ifInQLen

       32 bit unsigned gauge value."
   ::= {pr1645v2Lan2FG 128}


pr1645v2Lan2FGInDropEx OBJECT-TYPE
   SYNTAX      Counter64
   MAX-ACCESS  read-only
   STATUS      current
   DESCRIPTION
      "Path: ethernet2.performance.ifInDropLevelExceeded
       Info: ifInDiscards

       64 bit unsigned wrappable counter."
   ::= {pr1645v2Lan2FG 130}


pr1645v2Lan2FGInDropNoMac OBJECT-TYPE
   SYNTAX      Counter64
   MAX-ACCESS  read-only
   STATUS      current
   DESCRIPTION
      "Path: ethernet2.performance.ifInDiscardsNoMacFit
       Info: ifInDiscards

       64 bit unsigned wrappable counter."
   ::= {pr1645v2Lan2FG 133}


pr1645v2Lan2FGInDropNUCast OBJECT-TYPE
   SYNTAX      Counter64
   MAX-ACCESS  read-only
   STATUS      current
   DESCRIPTION
      "Path: ethernet2.performance.ifInDiscardsNUCast
       Info: ifInDiscards

       64 bit unsigned wrappable counter."
   ::= {pr1645v2Lan2FG 136}


pr1645v2Lan2FGInDropFilter OBJECT-TYPE
   SYNTAX      Counter64
   MAX-ACCESS  read-only
   STATUS      current
   DESCRIPTION
      "Path: ethernet2.performance.ifInDiscardsFilter
       Info: ifInDiscards

       64 bit unsigned wrappable counter."
   ::= {pr1645v2Lan2FG 137}


pr1645v2Lan2FGInQueues OBJECT IDENTIFIER ::= {pr1645v2Lan2FG 131}

pr1645v2Lan2FGInQueuesSSCTable OBJECT-TYPE
   SYNTAX      SEQUENCE OF Pr1645v2Lan2FGInQueuesEntry
   MAX-ACCESS  not-accessible
   STATUS      current
   DESCRIPTION
      "Queue Lengths"
   ::= {pr1645v2Lan2FGInQueues 1}

pr1645v2Lan2FGInQueuesEntry OBJECT-TYPE
   SYNTAX      Pr1645v2Lan2FGInQueuesEntry
   MAX-ACCESS  not-accessible
   STATUS      current
   DESCRIPTION
      ""
   INDEX      { pr1645v2Lan2FGInQueuesTableIx }
   ::= {pr1645v2Lan2FGInQueuesSSCTable 1}

Pr1645v2Lan2FGInQueuesEntry ::=
   SEQUENCE
      {
      pr1645v2Lan2FGInQueuesTableIx
         TableIndex,
      pr1645v2Lan2FGInQueuesName
         INTEGER,
      pr1645v2Lan2FGInQueuesLength
         Integer32,
      pr1645v2Lan2FGInQueuesOctetLength
         Integer32,
      pr1645v2Lan2FGInQueuesRedLength
         Integer32,
      pr1645v2Lan2FGInQueuesPacketsTotal
         Counter64,
      pr1645v2Lan2FGInQueuesPacketsDirectTx
         Counter64,
      pr1645v2Lan2FGInQueuesPacketsQueued
         Counter64,
      pr1645v2Lan2FGInQueuesPacketsDropped
         Counter64,
      pr1645v2Lan2FGInQueuesPacketsRedDropped
         Counter64,
      pr1645v2Lan2FGInQueuesPacketsCirTx
         Counter64,
      pr1645v2Lan2FGInQueuesPacketsEirTx
         Counter64,
      pr1645v2Lan2FGInQueuesPacketsViolateTx
         Counter64,
      pr1645v2Lan2FGInQueuesOctetsTotal
         Counter64,
      pr1645v2Lan2FGInQueuesOctetsDirectTx
         Counter64,
      pr1645v2Lan2FGInQueuesOctetsQueued
         Counter64,
      pr1645v2Lan2FGInQueuesOctetsDropped
         Counter64,
      pr1645v2Lan2FGInQueuesOctetsRedDropped
         Counter64,
      pr1645v2Lan2FGInQueuesOctetsCirTx
         Counter64,
      pr1645v2Lan2FGInQueuesOctetsEirTx
         Counter64,
      pr1645v2Lan2FGInQueuesOctetsViolateTx
         Counter64,
      pr1645v2Lan2FGInQueuesOctetsBandwidth15sec
         Integer32,
      pr1645v2Lan2FGInQueuesOctetsBandwidth30sec
         Integer32,
      pr1645v2Lan2FGInQueuesOctetsBandwidth1min
         Integer32,
      pr1645v2Lan2FGInQueuesOctetsBandwidth2min
         Integer32,
      pr1645v2Lan2FGInQueuesOctetsBandwidth5min
         Integer32
      }

pr1645v2Lan2FGInQueuesTableIx OBJECT-TYPE
   SYNTAX      TableIndex
   MAX-ACCESS  not-accessible
   STATUS      current
   DESCRIPTION
      ""
   ::= {pr1645v2Lan2FGInQueuesEntry 11}

pr1645v2Lan2FGInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGInQueuesEntry 16777216}

pr1645v2Lan2FGInQueuesLength OBJECT-TYPE
   SYNTAX      Integer32
   MAX-ACCESS  read-only
   STATUS      current
   DESCRIPTION
      "Path: ethernet2.performance.ifInPriorityQueues.length"
   ::= {pr1645v2Lan2FGInQueuesEntry 33554432}

pr1645v2Lan2FGInQueuesOctetLength OBJECT-TYPE
   SYNTAX      Integer32
   MAX-ACCESS  read-only
   STATUS      current
   DESCRIPTION
      "Path: ethernet2.performance.ifInPriorityQueues.octetLength"
   ::= {pr1645v2Lan2FGInQueuesEntry 150994944}

pr1645v2Lan2FGInQueuesRedLength OBJECT-TYPE
   SYNTAX      Integer32
   MAX-ACCESS  read-only
   STATUS      current
   DESCRIPTION
      "Path: ethernet2.performance.ifInPriorityQueues.redLength"
   ::= {pr1645v2Lan2FGInQueuesEntry 134217728}

pr1645v2Lan2FGInQueuesPacketsTotal OBJECT-TYPE
   SYNTAX      Counter64
   MAX-ACCESS  read-only
   STATUS      current
   DESCRIPTION
      "Path: ethernet2.performance.ifInPriorityQueues.packets.total

       64 bit unsigned wrappable counter."
   ::= {pr1645v2Lan2FGInQueuesEntry 50790400}

pr1645v2Lan2FGInQueuesPacketsDirectTx OBJECT-TYPE
   SYNTAX      Counter64
   MAX-ACCESS  read-only
   STATUS      current
   DESCRIPTION
      "Path: ethernet2.performance.ifInPriorityQueues.packets.directTx

       64 bit unsigned wrappable counter."
   ::= {pr1645v2Lan2FGInQueuesEntry 50397184}

pr1645v2Lan2FGInQueuesPacketsQueued OBJECT-TYPE
   SYNTAX      Counter64
   MAX-ACCESS  read-only
   STATUS      current
   DESCRIPTION
      "Path: ethernet2.performance.ifInPriorityQueues.packets.queued

       64 bit unsigned wrappable counter."
   ::= {pr1645v2Lan2FGInQueuesEntry 50462720}

pr1645v2Lan2FGInQueuesPacketsDropped OBJECT-TYPE
   SYNTAX      Counter64
   MAX-ACCESS  read-only
   STATUS      current
   DESCRIPTION
      "Path: ethernet2.performance.ifInPriorityQueues.packets.dropped

       64 bit unsigned wrappable counter."
   ::= {pr1645v2Lan2FGInQueuesEntry 50528256}

pr1645v2Lan2FGInQueuesPacketsRedDropped OBJECT-TYPE
   SYNTAX      Counter64
   MAX-ACCESS  read-only
   STATUS      current
   DESCRIPTION
      "Path: ethernet2.performance.ifInPriorityQueues.packets.redDropped

       64 bit unsigned wrappable counter."
   ::= {pr1645v2Lan2FGInQueuesEntry 50724864}

pr1645v2Lan2FGInQueuesPacketsCirTx OBJECT-TYPE
   SYNTAX      Counter64
   MAX-ACCESS  read-only
   STATUS      current
   DESCRIPTION
      "Path: ethernet2.performance.ifInPriorityQueues.packets.cirTx

       64 bit unsigned wrappable counter."
   ::= {pr1645v2Lan2FGInQueuesEntry 50593792}

pr1645v2Lan2FGInQueuesPacketsEirTx OBJECT-TYPE
   SYNTAX      Counter64
   MAX-ACCESS  read-only
   STATUS      current
   DESCRIPTION
      "Path: ethernet2.performance.ifInPriorityQueues.packets.eirTx

       64 bit unsigned wrappable counter."
   ::= {pr1645v2Lan2FGInQueuesEntry 50659328}

pr1645v2Lan2FGInQueuesPacketsViolateTx OBJECT-TYPE
   SYNTAX      Counter64
   MAX-ACCESS  read-only
   STATUS      current
   DESCRIPTION
      "Path: ethernet2.performance.ifInPriorityQueues.packets.violateTx

       64 bit unsigned wrappable counter."
   ::= {pr1645v2Lan2FGInQueuesEntry 50855936}

pr1645v2Lan2FGInQueuesOctetsTotal OBJECT-TYPE
   SYNTAX      Counter64
   MAX-ACCESS  read-only
   STATUS      current
   DESCRIPTION
      "Path: ethernet2.performance.ifInPriorityQueues.octets.total

       64 bit unsigned wrappable counter."
   ::= {pr1645v2Lan2FGInQueuesEntry 67567616}

pr1645v2Lan2FGInQueuesOctetsDirectTx OBJECT-TYPE
   SYNTAX      Counter64
   MAX-ACCESS  read-only
   STATUS      current
   DESCRIPTION
      "Path: ethernet2.performance.ifInPriorityQueues.octets.directTx

       64 bit unsigned wrappable counter."
   ::= {pr1645v2Lan2FGInQueuesEntry 67174400}

pr1645v2Lan2FGInQueuesOctetsQueued OBJECT-TYPE
   SYNTAX      Counter64
   MAX-ACCESS  read-only
   STATUS      current
   DESCRIPTION
      "Path: ethernet2.performance.ifInPriorityQueues.octets.queued

       64 bit unsigned wrappable counter."
   ::= {pr1645v2Lan2FGInQueuesEntry 67239936}

pr1645v2Lan2FGInQueuesOctetsDropped OBJECT-TYPE
   SYNTAX      Counter64
   MAX-ACCESS  read-only
   STATUS      current
   DESCRIPTION
      "Path: ethernet2.performance.ifInPriorityQueues.octets.dropped

       64 bit unsigned wrappable counter."
   ::= {pr1645v2Lan2FGInQueuesEntry 67305472}

pr1645v2Lan2FGInQueuesOctetsRedDropped OBJECT-TYPE
   SYNTAX      Counter64
   MAX-ACCESS  read-only
   STATUS      current
   DESCRIPTION
      "Path: ethernet2.performance.ifInPriorityQueues.octets.redDropped

       64 bit unsigned wrappable counter."
   ::= {pr1645v2Lan2FGInQueuesEntry 67502080}

pr1645v2Lan2FGInQueuesOctetsCirTx OBJECT-TYPE
   SYNTAX      Counter64
   MAX-ACCESS  read-only
   STATUS      current
   DESCRIPTION
      "Path: ethernet2.performance.ifInPriorityQueues.octets.cirTx

       64 bit unsigned wrappable counter."
   ::= {pr1645v2Lan2FGInQueuesEntry 67371008}

pr1645v2Lan2FGInQueuesOctetsEirTx OBJECT-TYPE
   SYNTAX      Counter64
   MAX-ACCESS  read-only
   STATUS      current
   DESCRIPTION
      "Path: ethernet2.performance.ifInPriorityQueues.octets.eirTx

       64 bit unsigned wrappable counter."
   ::= {pr1645v2Lan2FGInQueuesEntry 67436544}

pr1645v2Lan2FGInQueuesOctetsViolateTx OBJECT-TYPE
   SYNTAX      Counter64
   MAX-ACCESS  read-only
   STATUS      current
   DESCRIPTION
      "Path: ethernet2.performance.ifInPriorityQueues.octets.violateTx

       64 bit unsigned wrappable counter."
   ::= {pr1645v2Lan2FGInQueuesEntry 67633152}

pr1645v2Lan2FGInQueuesOctetsBandwidth15sec OBJECT-TYPE
   SYNTAX      Integer32
   MAX-ACCESS  read-only
   STATUS      current
   DESCRIPTION
      "Path: ethernet2.performance.ifInPriorityQueues.octets.bandwidth.15sec

       unit name = bps
       formula = 8 * ; 8 /"
   ::= {pr1645v2Lan2FGInQueuesEntry 70386944}

pr1645v2Lan2FGInQueuesOctetsBandwidth30sec OBJECT-TYPE
   SYNTAX      Integer32
   MAX-ACCESS  read-only
   STATUS      current
   DESCRIPTION
      "Path: ethernet2.performance.ifInPriorityQueues.octets.bandwidth.30sec

       unit name = bps
       formula = 8 * ; 8 /"
   ::= {pr1645v2Lan2FGInQueuesEntry 70388224}

pr1645v2Lan2FGInQueuesOctetsBandwidth1min OBJECT-TYPE
   SYNTAX      Integer32
   MAX-ACCESS  read-only
   STATUS      current
   DESCRIPTION
      "Path: ethernet2.performance.ifInPriorityQueues.octets.bandwidth.1min

       unit name = bps
       formula = 8 * ; 8 /"
   ::= {pr1645v2Lan2FGInQueuesEntry 70390784}

pr1645v2Lan2FGInQueuesOctetsBandwidth2min OBJECT-TYPE
   SYNTAX      Integer32
   MAX-ACCESS  read-only
   STATUS      current
   DESCRIPTION
      "Path: ethernet2.performance.ifInPriorityQueues.octets.bandwidth.2min

       unit name = bps
       formula = 8 * ; 8 /"
   ::= {pr1645v2Lan2FGInQueuesEntry 70395904}

pr1645v2Lan2FGInQueuesOctetsBandwidth5min OBJECT-TYPE
   SYNTAX      Integer32
   MAX-ACCESS  read-only
   STATUS      current
   DESCRIPTION
      "Path: ethernet2.performance.ifInPriorityQueues.octets.bandwidth.5min

       unit name = bps
       formula = 8 * ; 8 /"
   ::= {pr1645v2Lan2FGInQueuesEntry 70411264}

pr1645v2Lan2FGInQueuesH2Performance OBJECT-TYPE
   SYNTAX      SEQUENCE OF Pr1645v2Lan2FGInQueuesH2PerformanceEntry
   MAX-ACCESS  not-accessible
   STATUS      current
   DESCRIPTION
      ""
   ::= {pr1645v2Lan2FGInQueues 83886080}

pr1645v2Lan2FGInQueuesH2PerformanceEntry OBJECT-TYPE
   SYNTAX      Pr1645v2Lan2FGInQueuesH2PerformanceEntry
   MAX-ACCESS  not-accessible
   STATUS      current
   DESCRIPTION
      ""
   INDEX      { pr1645v2Lan2FGInQueuesTableIx,
                pr1645v2Lan2FGInQueuesH2PerformanceTableIx }
   ::= {pr1645v2Lan2FGInQueuesH2Performance 1}

Pr1645v2Lan2FGInQueuesH2PerformanceEntry ::=
   SEQUENCE
      {
      pr1645v2Lan2FGInQueuesH2PerformanceTableIx
         TableIndex,
      pr1645v2Lan2FGInQueuesH2PerformanceSysUpTime
         TimeTicks,
      pr1645v2Lan2FGInQueuesH2PerformanceTotPkts
         Counter64,
      pr1645v2Lan2FGInQueuesH2PerformanceDirTxPkts
         Counter64,
      pr1645v2Lan2FGInQueuesH2PerformanceQdPkts
         Counter64,
      pr1645v2Lan2FGInQueuesH2PerformanceDropPkts
         Counter64,
      pr1645v2Lan2FGInQueuesH2PerformanceRDropPkts
         Counter64,
      pr1645v2Lan2FGInQueuesH2PerformanceCirTxPkts
         Counter64,
      pr1645v2Lan2FGInQueuesH2PerformanceEirTxPkts
         Counter64,
      pr1645v2Lan2FGInQueuesH2PerformanceViolTxPkts
         Counter64,
      pr1645v2Lan2FGInQueuesH2PerformanceTotOcts
         Counter64,
      pr1645v2Lan2FGInQueuesH2PerformanceDirTxOcts
         Counter64,
      pr1645v2Lan2FGInQueuesH2PerformanceQdOcts
         Counter64,
      pr1645v2Lan2FGInQueuesH2PerformanceDropOcts
         Counter64,
      pr1645v2Lan2FGInQueuesH2PerformanceRDropOcts
         Counter64,
      pr1645v2Lan2FGInQueuesH2PerformanceCirTxOcts
         Counter64,
      pr1645v2Lan2FGInQueuesH2PerformanceEirTxOcts
         Counter64,
      pr1645v2Lan2FGInQueuesH2PerformanceViolTxOcts
         Counter64,
      pr1645v2Lan2FGInQueuesH2PerformanceBandwidth
         Integer32
      }

pr1645v2Lan2FGInQueuesH2PerformanceTableIx OBJECT-TYPE
   SYNTAX      TableIndex
   MAX-ACCESS  not-accessible
   STATUS      current
   DESCRIPTION
      ""
   ::= {pr1645v2Lan2FGInQueuesH2PerformanceEntry 11}

pr1645v2Lan2FGInQueuesH2PerformanceSysUpTime OBJECT-TYPE
   SYNTAX      TimeTicks
   MAX-ACCESS  read-only
   STATUS      current
   DESCRIPTION
      "Path: ethernet2.performance.ifInPriorityQueues.h2Performance.sysUpTime

       Time in centi-second."
   ::= {pr1645v2Lan2FGInQueuesH2PerformanceEntry 16777216}

pr1645v2Lan2FGInQueuesH2PerformanceTotPkts OBJECT-TYPE
   SYNTAX      Counter64
   MAX-ACCESS  read-only
   STATUS      current
   DESCRIPTION
      "Path: ethernet2.performance.ifInPriorityQueues.h2Performance.totalPkts

       64 bit unsigned wrappable counter."
   ::= {pr1645v2Lan2FGInQueuesH2PerformanceEntry 234881024}

pr1645v2Lan2FGInQueuesH2PerformanceDirTxPkts OBJECT-TYPE
   SYNTAX      Counter64
   MAX-ACCESS  read-only
   STATUS      current
   DESCRIPTION
      "Path: ethernet2.performance.ifInPriorityQueues.h2Performance.directTxPkts

       64 bit unsigned wrappable counter."
   ::= {pr1645v2Lan2FGInQueuesH2PerformanceEntry 33554432}

pr1645v2Lan2FGInQueuesH2PerformanceQdPkts OBJECT-TYPE
   SYNTAX      Counter64
   MAX-ACCESS  read-only
   STATUS      current
   DESCRIPTION
      "Path: ethernet2.performance.ifInPriorityQueues.h2Performance.queuedPkts

       64 bit unsigned wrappable counter."
   ::= {pr1645v2Lan2FGInQueuesH2PerformanceEntry 50331648}

pr1645v2Lan2FGInQueuesH2PerformanceDropPkts OBJECT-TYPE
   SYNTAX      Counter64
   MAX-ACCESS  read-only
   STATUS      current
   DESCRIPTION
      "Path: ethernet2.performance.ifInPriorityQueues.h2Performance.droppedPkts

       64 bit unsigned wrappable counter."
   ::= {pr1645v2Lan2FGInQueuesH2PerformanceEntry 67108864}

pr1645v2Lan2FGInQueuesH2PerformanceRDropPkts OBJECT-TYPE
   SYNTAX      Counter64
   MAX-ACCESS  read-only
   STATUS      current
   DESCRIPTION
      "Path: ethernet2.performance.ifInPriorityQueues.h2Performance.redDroppedPkts

       64 bit unsigned wrappable counter."
   ::= {pr1645v2Lan2FGInQueuesH2PerformanceEntry 201326592}

pr1645v2Lan2FGInQueuesH2PerformanceCirTxPkts OBJECT-TYPE
   SYNTAX      Counter64
   MAX-ACCESS  read-only
   STATUS      current
   DESCRIPTION
      "Path: ethernet2.performance.ifInPriorityQueues.h2Performance.cirTxPkts

       64 bit unsigned wrappable counter."
   ::= {pr1645v2Lan2FGInQueuesH2PerformanceEntry 83886080}

pr1645v2Lan2FGInQueuesH2PerformanceEirTxPkts OBJECT-TYPE
   SYNTAX      Counter64
   MAX-ACCESS  read-only
   STATUS      current
   DESCRIPTION
      "Path: ethernet2.performance.ifInPriorityQueues.h2Performance.eirTxPkts

       64 bit unsigned wrappable counter."
   ::= {pr1645v2Lan2FGInQueuesH2PerformanceEntry 100663296}

pr1645v2Lan2FGInQueuesH2PerformanceViolTxPkts OBJECT-TYPE
   SYNTAX      Counter64
   MAX-ACCESS  read-only
   STATUS      current
   DESCRIPTION
      "Path: ethernet2.performance.ifInPriorityQueues.h2Performance.violateTxPkts

       64 bit unsigned wrappable counter."
   ::= {pr1645v2Lan2FGInQueuesH2PerformanceEntry 301989888}

pr1645v2Lan2FGInQueuesH2PerformanceTotOcts OBJECT-TYPE
   SYNTAX      Counter64
   MAX-ACCESS  read-only
   STATUS      current
   DESCRIPTION
      "Path: ethernet2.performance.ifInPriorityQueues.h2Performance.totalOctets

       64 bit unsigned wrappable counter."
   ::= {pr1645v2Lan2FGInQueuesH2PerformanceEntry 251658240}

pr1645v2Lan2FGInQueuesH2PerformanceDirTxOcts OBJECT-TYPE
   SYNTAX      Counter64
   MAX-ACCESS  read-only
   STATUS      current
   DESCRIPTION
      "Path: ethernet2.performance.ifInPriorityQueues.h2Performance.directTxOctets

       64 bit unsigned wrappable counter."
   ::= {pr1645v2Lan2FGInQueuesH2PerformanceEntry 117440512}

pr1645v2Lan2FGInQueuesH2PerformanceQdOcts OBJECT-TYPE
   SYNTAX      Counter64
   MAX-ACCESS  read-only
   STATUS      current
   DESCRIPTION
      "Path: ethernet2.performance.ifInPriorityQueues.h2Performance.queuedOctets

       64 bit unsigned wrappable counter."
   ::= {pr1645v2Lan2FGInQueuesH2PerformanceEntry 134217728}

pr1645v2Lan2FGInQueuesH2PerformanceDropOcts OBJECT-TYPE
   SYNTAX      Counter64
   MAX-ACCESS  read-only
   STATUS      current
   DESCRIPTION
      "Path: ethernet2.performance.ifInPriorityQueues.h2Performance.droppedOctets

       64 bit unsigned wrappable counter."
   ::= {pr1645v2Lan2FGInQueuesH2PerformanceEntry 150994944}

pr1645v2Lan2FGInQueuesH2PerformanceRDropOcts OBJECT-TYPE
   SYNTAX      Counter64
   MAX-ACCESS  read-only
   STATUS      current
   DESCRIPTION
      "Path: ethernet2.performance.ifInPriorityQueues.h2Performance.redDroppedOctets

       64 bit unsigned wrappable counter."
   ::= {pr1645v2Lan2FGInQueuesH2PerformanceEntry 218103808}

pr1645v2Lan2FGInQueuesH2PerformanceCirTxOcts OBJECT-TYPE
   SYNTAX      Counter64
   MAX-ACCESS  read-only
   STATUS      current
   DESCRIPTION
      "Path: ethernet2.performance.ifInPriorityQueues.h2Performance.cirTxOctets

       64 bit unsigned wrappable counter."
   ::= {pr1645v2Lan2FGInQueuesH2PerformanceEntry 167772160}

pr1645v2Lan2FGInQueuesH2PerformanceEirTxOcts OBJECT-TYPE
   SYNTAX      Counter64
   MAX-ACCESS  read-only
   STATUS      current
   DESCRIPTION
      "Path: ethernet2.performance.ifInPriorityQueues.h2Performance.eirTxOctets

       64 bit unsigned wrappable counter."
   ::= {pr1645v2Lan2FGInQueuesH2PerformanceEntry 184549376}

pr1645v2Lan2FGInQueuesH2PerformanceViolTxOcts OBJECT-TYPE
   SYNTAX      Counter64
   MAX-ACCESS  read-only
   STATUS      current
   DESCRIPTION
      "Path: ethernet2.performance.ifInPriorityQueues.h2Performance.violateTxOctets

       64 bit unsigned wrappable counter."
   ::= {pr1645v2Lan2FGInQueuesH2PerformanceEntry 318767104}

pr1645v2Lan2FGInQueuesH2PerformanceBandwidth OBJECT-TYPE
   SYNTAX      Integer32
   MAX-ACCESS  read-only
   STATUS      current
   DESCRIPTION
      "Path: ethernet2.performance.ifInPriorityQueues.h2Performance.bandwidth

       unit name = bps
       formula = 8 * ; 8 /"
   ::= {pr1645v2Lan2FGInQueuesH2PerformanceEntry 268435456}

pr1645v2Lan2FGInQueuesH24Performance OBJECT-TYPE
   SYNTAX      SEQUENCE OF Pr1645v2Lan2FGInQueuesH24PerformanceEntry
   MAX-ACCESS  not-accessible
   STATUS      current
   DESCRIPTION
      ""
   ::= {pr1645v2Lan2FGInQueues 100663296}

pr1645v2Lan2FGInQueuesH24PerformanceEntry OBJECT-TYPE
   SYNTAX      Pr1645v2Lan2FGInQueuesH24PerformanceEntry
   MAX-ACCESS  not-accessible
   STATUS      current
   DESCRIPTION
      ""
   INDEX      { pr1645v2Lan2FGInQueuesTableIx,
                pr1645v2Lan2FGInQueuesH24PerformanceTableIx }
   ::= {pr1645v2Lan2FGInQueuesH24Performance 1}

Pr1645v2Lan2FGInQueuesH24PerformanceEntry ::=
   SEQUENCE
      {
      pr1645v2Lan2FGInQueuesH24PerformanceTableIx
         TableIndex,
      pr1645v2Lan2FGInQueuesH24PerformanceSysUpTime
         TimeTicks,
      pr1645v2Lan2FGInQueuesH24PerformanceTotPkts
         Counter64,
      pr1645v2Lan2FGInQueuesH24PerformanceDirTxPkts
         Counter64,
      pr1645v2Lan2FGInQueuesH24PerformanceQdPkts
         Counter64,
      pr1645v2Lan2FGInQueuesH24PerformanceDropPkts
         Counter64,
      pr1645v2Lan2FGInQueuesH24PerformanceRDropPkts
         Counter64,
      pr1645v2Lan2FGInQueuesH24PerformanceCirTxPkts
         Counter64,
      pr1645v2Lan2FGInQueuesH24PerformanceEirTxPkts
         Counter64,
      pr1645v2Lan2FGInQueuesH24PerformanceViolTxPkts
         Counter64,
      pr1645v2Lan2FGInQueuesH24PerformanceTotOcts
         Counter64,
      pr1645v2Lan2FGInQueuesH24PerformanceDirTxOcts
         Counter64,
      pr1645v2Lan2FGInQueuesH24PerformanceQdOcts
         Counter64,
      pr1645v2Lan2FGInQueuesH24PerformanceDropOcts
         Counter64,
      pr1645v2Lan2FGInQueuesH24PerformanceRDropOcts
         Counter64,
      pr1645v2Lan2FGInQueuesH24PerformanceCirTxOcts
         Counter64,
      pr1645v2Lan2FGInQueuesH24PerformanceEirTxOcts
         Counter64,
      pr1645v2Lan2FGInQueuesH24PerformanceViolTxOcts
         Counter64,
      pr1645v2Lan2FGInQueuesH24PerformanceBandwidth
         Integer32
      }

pr1645v2Lan2FGInQueuesH24PerformanceTableIx OBJECT-TYPE
   SYNTAX      TableIndex
   MAX-ACCESS  not-accessible
   STATUS      current
   DESCRIPTION
      ""
   ::= {pr1645v2Lan2FGInQueuesH24PerformanceEntry 11}

pr1645v2Lan2FGInQueuesH24PerformanceSysUpTime OBJECT-TYPE
   SYNTAX      TimeTicks
   MAX-ACCESS  read-only
   STATUS      current
   DESCRIPTION
      "Path: ethernet2.performance.ifInPriorityQueues.h24Performance.sysUpTime

       Time in centi-second."
   ::= {pr1645v2Lan2FGInQueuesH24PerformanceEntry 16777216}

pr1645v2Lan2FGInQueuesH24PerformanceTotPkts OBJECT-TYPE
   SYNTAX      Counter64
   MAX-ACCESS  read-only
   STATUS      current
   DESCRIPTION
      "Path: ethernet2.performance.ifInPriorityQueues.h24Performance.totalPkts

       64 bit unsigned wrappable counter."
   ::= {pr1645v2Lan2FGInQueuesH24PerformanceEntry 234881024}

pr1645v2Lan2FGInQueuesH24PerformanceDirTxPkts OBJECT-TYPE
   SYNTAX      Counter64
   MAX-ACCESS  read-only
   STATUS      current
   DESCRIPTION
      "Path: ethernet2.performance.ifInPriorityQueues.h24Performance.directTxPkts

       64 bit unsigned wrappable counter."
   ::= {pr1645v2Lan2FGInQueuesH24PerformanceEntry 33554432}

pr1645v2Lan2FGInQueuesH24PerformanceQdPkts OBJECT-TYPE
   SYNTAX      Counter64
   MAX-ACCESS  read-only
   STATUS      current
   DESCRIPTION
      "Path: ethernet2.performance.ifInPriorityQueues.h24Performance.queuedPkts

       64 bit unsigned wrappable counter."
   ::= {pr1645v2Lan2FGInQueuesH24PerformanceEntry 50331648}

pr1645v2Lan2FGInQueuesH24PerformanceDropPkts OBJECT-TYPE
   SYNTAX      Counter64
   MAX-ACCESS  read-only
   STATUS      current
   DESCRIPTION
      "Path: ethernet2.performance.ifInPriorityQueues.h24Performance.droppedPkts

       64 bit unsigned wrappable counter."
   ::= {pr1645v2Lan2FGInQueuesH24PerformanceEntry 67108864}

pr1645v2Lan2FGInQueuesH24PerformanceRDropPkts OBJECT-TYPE
   SYNTAX      Counter64
   MAX-ACCESS  read-only
   STATUS      current
   DESCRIPTION
      "Path: ethernet2.performance.ifInPriorityQueues.h24Performance.redDroppedPkts

       64 bit unsigned wrappable counter."
   ::= {pr1645v2Lan2FGInQueuesH24PerformanceEntry 201326592}

pr1645v2Lan2FGInQueuesH24PerformanceCirTxPkts OBJECT-TYPE
   SYNTAX      Counter64
   MAX-ACCESS  read-only
   STATUS      current
   DESCRIPTION
      "Path: ethernet2.performance.ifInPriorityQueues.h24Performance.cirTxPkts

       64 bit unsigned wrappable counter."
   ::= {pr1645v2Lan2FGInQueuesH24PerformanceEntry 83886080}

pr1645v2Lan2FGInQueuesH24PerformanceEirTxPkts OBJECT-TYPE
   SYNTAX      Counter64
   MAX-ACCESS  read-only
   STATUS      current
   DESCRIPTION
      "Path: ethernet2.performance.ifInPriorityQueues.h24Performance.eirTxPkts

       64 bit unsigned wrappable counter."
   ::= {pr1645v2Lan2FGInQueuesH24PerformanceEntry 100663296}

pr1645v2Lan2FGInQueuesH24PerformanceViolTxPkts OBJECT-TYPE
   SYNTAX      Counter64
   MAX-ACCESS  read-only
   STATUS      current
   DESCRIPTION
      "Path: ethernet2.performance.ifInPriorityQueues.h24Performance.violateTxPkts

       64 bit unsigned wrappable counter."
   ::= {pr1645v2Lan2FGInQueuesH24PerformanceEntry 301989888}

pr1645v2Lan2FGInQueuesH24PerformanceTotOcts OBJECT-TYPE
   SYNTAX      Counter64
   MAX-ACCESS  read-only
   STATUS      current
   DESCRIPTION
      "Path: ethernet2.performance.ifInPriorityQueues.h24Performance.totalOctets

       64 bit unsigned wrappable counter."
   ::= {pr1645v2Lan2FGInQueuesH24PerformanceEntry 251658240}

pr1645v2Lan2FGInQueuesH24PerformanceDirTxOcts OBJECT-TYPE
   SYNTAX      Counter64
   MAX-ACCESS  read-only
   STATUS      current
   DESCRIPTION
      "Path: ethernet2.performance.ifInPriorityQueues.h24Performance.directTxOctets

       64 bit unsigned wrappable counter."
   ::= {pr1645v2Lan2FGInQueuesH24PerformanceEntry 117440512}

pr1645v2Lan2FGInQueuesH24PerformanceQdOcts OBJECT-TYPE
   SYNTAX      Counter64
   MAX-ACCESS  read-only
   STATUS      current
   DESCRIPTION
      "Path: ethernet2.performance.ifInPriorityQueues.h24Performance.queuedOctets

       64 bit unsigned wrappable counter."
   ::= {pr1645v2Lan2FGInQueuesH24PerformanceEntry 134217728}

pr1645v2Lan2FGInQueuesH24PerformanceDropOcts OBJECT-TYPE
   SYNTAX      Counter64
   MAX-ACCESS  read-only
   STATUS      current
   DESCRIPTION
      "Path: ethernet2.performance.ifInPriorityQueues.h24Performance.droppedOctets

       64 bit unsigned wrappable counter."
   ::= {pr1645v2Lan2FGInQueuesH24PerformanceEntry 150994944}

pr1645v2Lan2FGInQueuesH24PerformanceRDropOcts OBJECT-TYPE
   SYNTAX      Counter64
   MAX-ACCESS  read-only
   STATUS      current
   DESCRIPTION
      "Path: ethernet2.performance.ifInPriorityQueues.h24Performance.redDroppedOctets

       64 bit unsigned wrappable counter."
   ::= {pr1645v2Lan2FGInQueuesH24PerformanceEntry 218103808}

pr1645v2Lan2FGInQueuesH24PerformanceCirTxOcts OBJECT-TYPE
   SYNTAX      Counter64
   MAX-ACCESS  read-only
   STATUS      current
   DESCRIPTION
      "Path: ethernet2.performance.ifInPriorityQueues.h24Performance.cirTxOctets

       64 bit unsigned wrappable counter."
   ::= {pr1645v2Lan2FGInQueuesH24PerformanceEntry 167772160}

pr1645v2Lan2FGInQueuesH24PerformanceEirTxOcts OBJECT-TYPE
   SYNTAX      Counter64
   MAX-ACCESS  read-only
   STATUS      current
   DESCRIPTION
      "Path: ethernet2.performance.ifInPriorityQueues.h24Performance.eirTxOctets

       64 bit unsigned wrappable counter."
   ::= {pr1645v2Lan2FGInQueuesH24PerformanceEntry 184549376}

pr1645v2Lan2FGInQueuesH24PerformanceViolTxOcts OBJECT-TYPE
   SYNTAX      Counter64
   MAX-ACCESS  read-only
   STATUS      current
   DESCRIPTION
      "Path: ethernet2.performance.ifInPriorityQueues.h24Performance.violateTxOctets

       64 bit unsigned wrappable counter."
   ::= {pr1645v2Lan2FGInQueuesH24PerformanceEntry 318767104}

pr1645v2Lan2FGInQueuesH24PerformanceBandwidth OBJECT-TYPE
   SYNTAX      Integer32
   MAX-ACCESS  read-only
   STATUS      current
   DESCRIPTION
      "Path: ethernet2.performance.ifInPriorityQueues.h24Performance.bandwidth

       unit name = bps
       formula = 8 * ; 8 /"
   ::= {pr1645v2Lan2FGInQueuesH24PerformanceEntry 268435456}

pr1645v2Lan2FGInQueuesD7Performance OBJECT-TYPE
   SYNTAX      SEQUENCE OF Pr1645v2Lan2FGInQueuesD7PerformanceEntry
   MAX-ACCESS  not-accessible
   STATUS      current
   DESCRIPTION
      ""
   ::= {pr1645v2Lan2FGInQueues 117440512}

pr1645v2Lan2FGInQueuesD7PerformanceEntry OBJECT-TYPE
   SYNTAX      Pr1645v2Lan2FGInQueuesD7PerformanceEntry
   MAX-ACCESS  not-accessible
   STATUS      current
   DESCRIPTION
      ""
   INDEX      { pr1645v2Lan2FGInQueuesTableIx,
                pr1645v2Lan2FGInQueuesD7PerformanceTableIx }
   ::= {pr1645v2Lan2FGInQueuesD7Performance 1}

Pr1645v2Lan2FGInQueuesD7PerformanceEntry ::=
   SEQUENCE
      {
      pr1645v2Lan2FGInQueuesD7PerformanceTableIx
         TableIndex,
      pr1645v2Lan2FGInQueuesD7PerformanceSysUpTime
         TimeTicks,
      pr1645v2Lan2FGInQueuesD7PerformanceTotPkts
         Counter64,
      pr1645v2Lan2FGInQueuesD7PerformanceDirTxPkts
         Counter64,
      pr1645v2Lan2FGInQueuesD7PerformanceQdPkts
         Counter64,
      pr1645v2Lan2FGInQueuesD7PerformanceDropPkts
         Counter64,
      pr1645v2Lan2FGInQueuesD7PerformanceRDropPkts
         Counter64,
      pr1645v2Lan2FGInQueuesD7PerformanceCirTxPkts
         Counter64,
      pr1645v2Lan2FGInQueuesD7PerformanceEirTxPkts
         Counter64,
      pr1645v2Lan2FGInQueuesD7PerformanceViolTxPkts
         Counter64,
      pr1645v2Lan2FGInQueuesD7PerformanceTotOcts
         Counter64,
      pr1645v2Lan2FGInQueuesD7PerformanceDirTxOcts
         Counter64,
      pr1645v2Lan2FGInQueuesD7PerformanceQdOcts
         Counter64,
      pr1645v2Lan2FGInQueuesD7PerformanceDropOcts
         Counter64,
      pr1645v2Lan2FGInQueuesD7PerformanceRDropOcts
         Counter64,
      pr1645v2Lan2FGInQueuesD7PerformanceCirTxOcts
         Counter64,
      pr1645v2Lan2FGInQueuesD7PerformanceEirTxOcts
         Counter64,
      pr1645v2Lan2FGInQueuesD7PerformanceViolTxOcts
         Counter64,
      pr1645v2Lan2FGInQueuesD7PerformanceBandwidth
         Integer32
      }

pr1645v2Lan2FGInQueuesD7PerformanceTableIx OBJECT-TYPE
   SYNTAX      TableIndex
   MAX-ACCESS  not-accessible
   STATUS      current
   DESCRIPTION
      ""
   ::= {pr1645v2Lan2FGInQueuesD7PerformanceEntry 11}

pr1645v2Lan2FGInQueuesD7PerformanceSysUpTime OBJECT-TYPE
   SYNTAX      TimeTicks
   MAX-ACCESS  read-only
   STATUS      current
   DESCRIPTION
      "Path: ethernet2.performance.ifInPriorityQueues.d7Performance.sysUpTime

       Time in centi-second."
   ::= {pr1645v2Lan2FGInQueuesD7PerformanceEntry 16777216}

pr1645v2Lan2FGInQueuesD7PerformanceTotPkts OBJECT-TYPE
   SYNTAX      Counter64
   MAX-ACCESS  read-only
   STATUS      current
   DESCRIPTION
      "Path: ethernet2.performance.ifInPriorityQueues.d7Performance.totalPkts

       64 bit unsigned wrappable counter."
   ::= {pr1645v2Lan2FGInQueuesD7PerformanceEntry 234881024}

pr1645v2Lan2FGInQueuesD7PerformanceDirTxPkts OBJECT-TYPE
   SYNTAX      Counter64
   MAX-ACCESS  read-only
   STATUS      current
   DESCRIPTION
      "Path: ethernet2.performance.ifInPriorityQueues.d7Performance.directTxPkts

       64 bit unsigned wrappable counter."
   ::= {pr1645v2Lan2FGInQueuesD7PerformanceEntry 33554432}

pr1645v2Lan2FGInQueuesD7PerformanceQdPkts OBJECT-TYPE
   SYNTAX      Counter64
   MAX-ACCESS  read-only
   STATUS      current
   DESCRIPTION
      "Path: ethernet2.performance.ifInPriorityQueues.d7Performance.queuedPkts

       64 bit unsigned wrappable counter."
   ::= {pr1645v2Lan2FGInQueuesD7PerformanceEntry 50331648}

pr1645v2Lan2FGInQueuesD7PerformanceDropPkts OBJECT-TYPE
   SYNTAX      Counter64
   MAX-ACCESS  read-only
   STATUS      current
   DESCRIPTION
      "Path: ethernet2.performance.ifInPriorityQueues.d7Performance.droppedPkts

       64 bit unsigned wrappable counter."
   ::= {pr1645v2Lan2FGInQueuesD7PerformanceEntry 67108864}

pr1645v2Lan2FGInQueuesD7PerformanceRDropPkts OBJECT-TYPE
   SYNTAX      Counter64
   MAX-ACCESS  read-only
   STATUS      current
   DESCRIPTION
      "Path: ethernet2.performance.ifInPriorityQueues.d7Performance.redDroppedPkts

       64 bit unsigned wrappable counter."
   ::= {pr1645v2Lan2FGInQueuesD7PerformanceEntry 201326592}

pr1645v2Lan2FGInQueuesD7PerformanceCirTxPkts OBJECT-TYPE
   SYNTAX      Counter64
   MAX-ACCESS  read-only
   STATUS      current
   DESCRIPTION
      "Path: ethernet2.performance.ifInPriorityQueues.d7Performance.cirTxPkts

       64 bit unsigned wrappable counter."
   ::= {pr1645v2Lan2FGInQueuesD7PerformanceEntry 83886080}

pr1645v2Lan2FGInQueuesD7PerformanceEirTxPkts OBJECT-TYPE
   SYNTAX      Counter64
   MAX-ACCESS  read-only
   STATUS      current
   DESCRIPTION
      "Path: ethernet2.performance.ifInPriorityQueues.d7Performance.eirTxPkts

       64 bit unsigned wrappable counter."
   ::= {pr1645v2Lan2FGInQueuesD7PerformanceEntry 100663296}

pr1645v2Lan2FGInQueuesD7PerformanceViolTxPkts OBJECT-TYPE
   SYNTAX      Counter64
   MAX-ACCESS  read-only
   STATUS      current
   DESCRIPTION
      "Path: ethernet2.performance.ifInPriorityQueues.d7Performance.violateTxPkts

       64 bit unsigned wrappable counter."
   ::= {pr1645v2Lan2FGInQueuesD7PerformanceEntry 301989888}

pr1645v2Lan2FGInQueuesD7PerformanceTotOcts OBJECT-TYPE
   SYNTAX      Counter64
   MAX-ACCESS  read-only
   STATUS      current
   DESCRIPTION
      "Path: ethernet2.performance.ifInPriorityQueues.d7Performance.totalOctets

       64 bit unsigned wrappable counter."
   ::= {pr1645v2Lan2FGInQueuesD7PerformanceEntry 251658240}

pr1645v2Lan2FGInQueuesD7PerformanceDirTxOcts OBJECT-TYPE
   SYNTAX      Counter64
   MAX-ACCESS  read-only
   STATUS      current
   DESCRIPTION
      "Path: ethernet2.performance.ifInPriorityQueues.d7Performance.directTxOctets

       64 bit unsigned wrappable counter."
   ::= {pr1645v2Lan2FGInQueuesD7PerformanceEntry 117440512}

pr1645v2Lan2FGInQueuesD7PerformanceQdOcts OBJECT-TYPE
   SYNTAX      Counter64
   MAX-ACCESS  read-only
   STATUS      current
   DESCRIPTION
      "Path: ethernet2.performance.ifInPriorityQueues.d7Performance.queuedOctets

       64 bit unsigned wrappable counter."
   ::= {pr1645v2Lan2FGInQueuesD7PerformanceEntry 134217728}

pr1645v2Lan2FGInQueuesD7PerformanceDropOcts OBJECT-TYPE
   SYNTAX      Counter64
   MAX-ACCESS  read-only
   STATUS      current
   DESCRIPTION
      "Path: ethernet2.performance.ifInPriorityQueues.d7Performance.droppedOctets

       64 bit unsigned wrappable counter."
   ::= {pr1645v2Lan2FGInQueuesD7PerformanceEntry 150994944}

pr1645v2Lan2FGInQueuesD7PerformanceRDropOcts OBJECT-TYPE
   SYNTAX      Counter64
   MAX-ACCESS  read-only
   STATUS      current
   DESCRIPTION
      "Path: ethernet2.performance.ifInPriorityQueues.d7Performance.redDroppedOctets

       64 bit unsigned wrappable counter."
   ::= {pr1645v2Lan2FGInQueuesD7PerformanceEntry 218103808}

pr1645v2Lan2FGInQueuesD7PerformanceCirTxOcts OBJECT-TYPE
   SYNTAX      Counter64
   MAX-ACCESS  read-only
   STATUS      current
   DESCRIPTION
      "Path: ethernet2.performance.ifInPriorityQueues.d7Performance.cirTxOctets

       64 bit unsigned wrappable counter."
   ::= {pr1645v2Lan2FGInQueuesD7PerformanceEntry 167772160}

pr1645v2Lan2FGInQueuesD7PerformanceEirTxOcts OBJECT-TYPE
   SYNTAX      Counter64
   MAX-ACCESS  read-only
   STATUS      current
   DESCRIPTION
      "Path: ethernet2.performance.ifInPriorityQueues.d7Performance.eirTxOctets

       64 bit unsigned wrappable counter."
   ::= {pr1645v2Lan2FGInQueuesD7PerformanceEntry 184549376}

pr1645v2Lan2FGInQueuesD7PerformanceViolTxOcts OBJECT-TYPE
   SYNTAX      Counter64
   MAX-ACCESS  read-only
   STATUS      current
   DESCRIPTION
      "Path: ethernet2.performance.ifInPriorityQueues.d7Performance.violateTxOctets

       64 bit unsigned wrappable counter."
   ::= {pr1645v2Lan2FGInQueuesD7PerformanceEntry 318767104}

pr1645v2Lan2FGInQueuesD7PerformanceBandwidth OBJECT-TYPE
   SYNTAX      Integer32
   MAX-ACCESS  read-only
   STATUS      current
   DESCRIPTION
      "Path: ethernet2.performance.ifInPriorityQueues.d7Performance.bandwidth

       unit name = bps
       formula = 8 * ; 8 /"
   ::= {pr1645v2Lan2FGInQueuesD7PerformanceEntry 268435456}


pr1645v2Lan2FGInBandwidth OBJECT IDENTIFIER ::= {pr1645v2Lan2FG 181}

pr1645v2Lan2FGInBandwidthSSC OBJECT IDENTIFIER ::= {pr1645v2Lan2FGInBandwidth 1}

pr1645v2Lan2FGInBandwidthEntry OBJECT IDENTIFIER ::= {pr1645v2Lan2FGInBandwidthSSC 1}

pr1645v2Lan2FGInBandwidth15sec OBJECT-TYPE
   SYNTAX      Integer32
   MAX-ACCESS  read-only
   STATUS      current
   DESCRIPTION
      "Path: ethernet2.performance.ifInBandwidth.15sec

       unit name = bps
       formula = 8 * ; 8 /"
   ::= {pr1645v2Lan2FGInBandwidthEntry 83886080}

pr1645v2Lan2FGInBandwidth30sec OBJECT-TYPE
   SYNTAX      Integer32
   MAX-ACCESS  read-only
   STATUS      current
   DESCRIPTION
      "Path: ethernet2.performance.ifInBandwidth.30sec

       unit name = bps
       formula = 8 * ; 8 /"
   ::= {pr1645v2Lan2FGInBandwidthEntry 167772160}

pr1645v2Lan2FGInBandwidth1min OBJECT-TYPE
   SYNTAX      Integer32
   MAX-ACCESS  read-only
   STATUS      current
   DESCRIPTION
      "Path: ethernet2.performance.ifInBandwidth.1min

       unit name = bps
       formula = 8 * ; 8 /"
   ::= {pr1645v2Lan2FGInBandwidthEntry 335544320}

pr1645v2Lan2FGInBandwidth2min OBJECT-TYPE
   SYNTAX      Integer32
   MAX-ACCESS  read-only
   STATUS      current
   DESCRIPTION
      "Path: ethernet2.performance.ifInBandwidth.2min

       unit name = bps
       formula = 8 * ; 8 /"
   ::= {pr1645v2Lan2FGInBandwidthEntry 671088640}

pr1645v2Lan2FGInBandwidth5min OBJECT-TYPE
   SYNTAX      Integer32
   MAX-ACCESS  read-only
   STATUS      current
   DESCRIPTION
      "Path: ethernet2.performance.ifInBandwidth.5min

       unit name = bps
       formula = 8 * ; 8 /"
   ::= {pr1645v2Lan2FGInBandwidthEntry 1677721600}


pr1645v2Lan2FGOutOctets OBJECT-TYPE
   SYNTAX      Counter64
   MAX-ACCESS  read-only
   STATUS      current
   DESCRIPTION
      "Path: ethernet2.performance.ifOutOctets
       Info: ifOutOctets

       64 bit unsigned wrappable counter."
   ::= {pr1645v2Lan2FG 115}


pr1645v2Lan2FGOutUcastPkts OBJECT-TYPE
   SYNTAX      Counter64
   MAX-ACCESS  read-only
   STATUS      current
   DESCRIPTION
      "Path: ethernet2.performance.ifOutUcastPkts
       Info: ifOutUcastPkts

       64 bit unsigned wrappable counter."
   ::= {pr1645v2Lan2FG 116}


pr1645v2Lan2FGOutNUcastPkts OBJECT-TYPE
   SYNTAX      Counter64
   MAX-ACCESS  read-only
   STATUS      current
   DESCRIPTION
      "Path: ethernet2.performance.ifOutNUcastPkts
       Info: ifOutNUcastPkts

       64 bit unsigned wrappable counter."
   ::= {pr1645v2Lan2FG 117}


pr1645v2Lan2FGOutBcastPkts OBJECT-TYPE
   SYNTAX      Counter64
   MAX-ACCESS  read-only
   STATUS      current
   DESCRIPTION
      "Path: ethernet2.performance.ifOutBcastPkts
       Info: ifOutBcastPkts

       64 bit unsigned wrappable counter."
   ::= {pr1645v2Lan2FG 217}


pr1645v2Lan2FGOutMcastPkts OBJECT-TYPE
   SYNTAX      Counter64
   MAX-ACCESS  read-only
   STATUS      current
   DESCRIPTION
      "Path: ethernet2.performance.ifOutMcastPkts
       Info: ifOutMcastPkts

       64 bit unsigned wrappable counter."
   ::= {pr1645v2Lan2FG 227}


pr1645v2Lan2FGOutDiscards OBJECT-TYPE
   SYNTAX      Counter64
   MAX-ACCESS  read-only
   STATUS      current
   DESCRIPTION
      "Path: ethernet2.performance.ifOutDiscards
       Info: ifOutDiscards

       64 bit unsigned wrappable counter."
   ::= {pr1645v2Lan2FG 118}


pr1645v2Lan2FGOutErrors OBJECT-TYPE
   SYNTAX      Counter64
   MAX-ACCESS  read-only
   STATUS      current
   DESCRIPTION
      "Path: ethernet2.performance.ifOutErrors
       Info: ifOutErrors

       64 bit unsigned wrappable counter."
   ::= {pr1645v2Lan2FG 119}


pr1645v2Lan2FGOutQLen OBJECT-TYPE
   SYNTAX      Gauge32
   MAX-ACCESS  read-only
   STATUS      current
   DESCRIPTION
      "Path: ethernet2.performance.ifOutQLen
       Info: ifOutQLen

       32 bit unsigned gauge value."
   ::= {pr1645v2Lan2FG 120}


pr1645v2Lan2FGOutDropEx OBJECT-TYPE
   SYNTAX      Counter64
   MAX-ACCESS  read-only
   STATUS      current
   DESCRIPTION
      "Path: ethernet2.performance.ifOutDropLevelExceeded
       Info: ifOutDiscards

       64 bit unsigned wrappable counter."
   ::= {pr1645v2Lan2FG 127}


pr1645v2Lan2FGOutDropNoArp OBJECT-TYPE
   SYNTAX      Counter64
   MAX-ACCESS  read-only
   STATUS      current
   DESCRIPTION
      "Path: ethernet2.performance.ifOutDiscardsNoArp
       Info: ifOutDiscards

       64 bit unsigned wrappable counter."
   ::= {pr1645v2Lan2FG 134}


pr1645v2Lan2FGOutDropFilter OBJECT-TYPE
   SYNTAX      Counter64
   MAX-ACCESS  read-only
   STATUS      current
   DESCRIPTION
      "Path: ethernet2.performance.ifOutDiscardsFilter
       Info: ifOutDiscards

       64 bit unsigned wrappable counter."
   ::= {pr1645v2Lan2FG 138}


pr1645v2Lan2FGOutQueues OBJECT IDENTIFIER ::= {pr1645v2Lan2FG 129}

pr1645v2Lan2FGOutQueuesSSCTable OBJECT-TYPE
   SYNTAX      SEQUENCE OF Pr1645v2Lan2FGOutQueuesEntry
   MAX-ACCESS  not-accessible
   STATUS      current
   DESCRIPTION
      "Queue Lengths"
   ::= {pr1645v2Lan2FGOutQueues 1}

pr1645v2Lan2FGOutQueuesEntry OBJECT-TYPE
   SYNTAX      Pr1645v2Lan2FGOutQueuesEntry
   MAX-ACCESS  not-accessible
   STATUS      current
   DESCRIPTION
      ""
   INDEX      { pr1645v2Lan2FGOutQueuesTableIx }
   ::= {pr1645v2Lan2FGOutQueuesSSCTable 1}

Pr1645v2Lan2FGOutQueuesEntry ::=
   SEQUENCE
      {
      pr1645v2Lan2FGOutQueuesTableIx
         TableIndex,
      pr1645v2Lan2FGOutQueuesName
         INTEGER,
      pr1645v2Lan2FGOutQueuesLength
         Integer32,
      pr1645v2Lan2FGOutQueuesOctetLength
         Integer32,
      pr1645v2Lan2FGOutQueuesRedLength
         Integer32,
      pr1645v2Lan2FGOutQueuesPacketsTotal
         Counter64,
      pr1645v2Lan2FGOutQueuesPacketsDirectTx
         Counter64,
      pr1645v2Lan2FGOutQueuesPacketsQueued
         Counter64,
      pr1645v2Lan2FGOutQueuesPacketsDropped
         Counter64,
      pr1645v2Lan2FGOutQueuesPacketsRedDropped
         Counter64,
      pr1645v2Lan2FGOutQueuesPacketsCirTx
         Counter64,
      pr1645v2Lan2FGOutQueuesPacketsEirTx
         Counter64,
      pr1645v2Lan2FGOutQueuesPacketsViolateTx
         Counter64,
      pr1645v2Lan2FGOutQueuesOctetsTotal
         Counter64,
      pr1645v2Lan2FGOutQueuesOctetsDirectTx
         Counter64,
      pr1645v2Lan2FGOutQueuesOctetsQueued
         Counter64,
      pr1645v2Lan2FGOutQueuesOctetsDropped
         Counter64,
      pr1645v2Lan2FGOutQueuesOctetsRedDropped
         Counter64,
      pr1645v2Lan2FGOutQueuesOctetsCirTx
         Counter64,
      pr1645v2Lan2FGOutQueuesOctetsEirTx
         Counter64,
      pr1645v2Lan2FGOutQueuesOctetsViolateTx
         Counter64,
      pr1645v2Lan2FGOutQueuesOctetsBandwidth15sec
         Integer32,
      pr1645v2Lan2FGOutQueuesOctetsBandwidth30sec
         Integer32,
      pr1645v2Lan2FGOutQueuesOctetsBandwidth1min
         Integer32,
      pr1645v2Lan2FGOutQueuesOctetsBandwidth2min
         Integer32,
      pr1645v2Lan2FGOutQueuesOctetsBandwidth5min
         Integer32
      }

pr1645v2Lan2FGOutQueuesTableIx OBJECT-TYPE
   SYNTAX      TableIndex
   MAX-ACCESS  not-accessible
   STATUS      current
   DESCRIPTION
      ""
   ::= {pr1645v2Lan2FGOutQueuesEntry 11}

pr1645v2Lan2FGOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGOutQueuesEntry 16777216}

pr1645v2Lan2FGOutQueuesLength OBJECT-TYPE
   SYNTAX      Integer32
   MAX-ACCESS  read-only
   STATUS      current
   DESCRIPTION
      "Path: ethernet2.performance.ifOutPriorityQueues.length"
   ::= {pr1645v2Lan2FGOutQueuesEntry 33554432}

pr1645v2Lan2FGOutQueuesOctetLength OBJECT-TYPE
   SYNTAX      Integer32
   MAX-ACCESS  read-only
   STATUS      current
   DESCRIPTION
      "Path: ethernet2.performance.ifOutPriorityQueues.octetLength"
   ::= {pr1645v2Lan2FGOutQueuesEntry 150994944}

pr1645v2Lan2FGOutQueuesRedLength OBJECT-TYPE
   SYNTAX      Integer32
   MAX-ACCESS  read-only
   STATUS      current
   DESCRIPTION
      "Path: ethernet2.performance.ifOutPriorityQueues.redLength"
   ::= {pr1645v2Lan2FGOutQueuesEntry 134217728}

pr1645v2Lan2FGOutQueuesPacketsTotal OBJECT-TYPE
   SYNTAX      Counter64
   MAX-ACCESS  read-only
   STATUS      current
   DESCRIPTION
      "Path: ethernet2.performance.ifOutPriorityQueues.packets.total

       64 bit unsigned wrappable counter."
   ::= {pr1645v2Lan2FGOutQueuesEntry 50790400}

pr1645v2Lan2FGOutQueuesPacketsDirectTx OBJECT-TYPE
   SYNTAX      Counter64
   MAX-ACCESS  read-only
   STATUS      current
   DESCRIPTION
      "Path: ethernet2.performance.ifOutPriorityQueues.packets.directTx

       64 bit unsigned wrappable counter."
   ::= {pr1645v2Lan2FGOutQueuesEntry 50397184}

pr1645v2Lan2FGOutQueuesPacketsQueued OBJECT-TYPE
   SYNTAX      Counter64
   MAX-ACCESS  read-only
   STATUS      current
   DESCRIPTION
      "Path: ethernet2.performance.ifOutPriorityQueues.packets.queued

       64 bit unsigned wrappable counter."
   ::= {pr1645v2Lan2FGOutQueuesEntry 50462720}

pr1645v2Lan2FGOutQueuesPacketsDropped OBJECT-TYPE
   SYNTAX      Counter64
   MAX-ACCESS  read-only
   STATUS      current
   DESCRIPTION
      "Path: ethernet2.performance.ifOutPriorityQueues.packets.dropped

       64 bit unsigned wrappable counter."
   ::= {pr1645v2Lan2FGOutQueuesEntry 50528256}

pr1645v2Lan2FGOutQueuesPacketsRedDropped OBJECT-TYPE
   SYNTAX      Counter64
   MAX-ACCESS  read-only
   STATUS      current
   DESCRIPTION
      "Path: ethernet2.performance.ifOutPriorityQueues.packets.redDropped

       64 bit unsigned wrappable counter."
   ::= {pr1645v2Lan2FGOutQueuesEntry 50724864}

pr1645v2Lan2FGOutQueuesPacketsCirTx OBJECT-TYPE
   SYNTAX      Counter64
   MAX-ACCESS  read-only
   STATUS      current
   DESCRIPTION
      "Path: ethernet2.performance.ifOutPriorityQueues.packets.cirTx

       64 bit unsigned wrappable counter."
   ::= {pr1645v2Lan2FGOutQueuesEntry 50593792}

pr1645v2Lan2FGOutQueuesPacketsEirTx OBJECT-TYPE
   SYNTAX      Counter64
   MAX-ACCESS  read-only
   STATUS      current
   DESCRIPTION
      "Path: ethernet2.performance.ifOutPriorityQueues.packets.eirTx

       64 bit unsigned wrappable counter."
   ::= {pr1645v2Lan2FGOutQueuesEntry 50659328}

pr1645v2Lan2FGOutQueuesPacketsViolateTx OBJECT-TYPE
   SYNTAX      Counter64
   MAX-ACCESS  read-only
   STATUS      current
   DESCRIPTION
      "Path: ethernet2.performance.ifOutPriorityQueues.packets.violateTx

       64 bit unsigned wrappable counter."
   ::= {pr1645v2Lan2FGOutQueuesEntry 50855936}

pr1645v2Lan2FGOutQueuesOctetsTotal OBJECT-TYPE
   SYNTAX      Counter64
   MAX-ACCESS  read-only
   STATUS      current
   DESCRIPTION
      "Path: ethernet2.performance.ifOutPriorityQueues.octets.total

       64 bit unsigned wrappable counter."
   ::= {pr1645v2Lan2FGOutQueuesEntry 67567616}

pr1645v2Lan2FGOutQueuesOctetsDirectTx OBJECT-TYPE
   SYNTAX      Counter64
   MAX-ACCESS  read-only
   STATUS      current
   DESCRIPTION
      "Path: ethernet2.performance.ifOutPriorityQueues.octets.directTx

       64 bit unsigned wrappable counter."
   ::= {pr1645v2Lan2FGOutQueuesEntry 67174400}

pr1645v2Lan2FGOutQueuesOctetsQueued OBJECT-TYPE
   SYNTAX      Counter64
   MAX-ACCESS  read-only
   STATUS      current
   DESCRIPTION
      "Path: ethernet2.performance.ifOutPriorityQueues.octets.queued

       64 bit unsigned wrappable counter."
   ::= {pr1645v2Lan2FGOutQueuesEntry 67239936}

pr1645v2Lan2FGOutQueuesOctetsDropped OBJECT-TYPE
   SYNTAX      Counter64
   MAX-ACCESS  read-only
   STATUS      current
   DESCRIPTION
      "Path: ethernet2.performance.ifOutPriorityQueues.octets.dropped

       64 bit unsigned wrappable counter."
   ::= {pr1645v2Lan2FGOutQueuesEntry 67305472}

pr1645v2Lan2FGOutQueuesOctetsRedDropped OBJECT-TYPE
   SYNTAX      Counter64
   MAX-ACCESS  read-only
   STATUS      current
   DESCRIPTION
      "Path: ethernet2.performance.ifOutPriorityQueues.octets.redDropped

       64 bit unsigned wrappable counter."
   ::= {pr1645v2Lan2FGOutQueuesEntry 67502080}

pr1645v2Lan2FGOutQueuesOctetsCirTx OBJECT-TYPE
   SYNTAX      Counter64
   MAX-ACCESS  read-only
   STATUS      current
   DESCRIPTION
      "Path: ethernet2.performance.ifOutPriorityQueues.octets.cirTx

       64 bit unsigned wrappable counter."
   ::= {pr1645v2Lan2FGOutQueuesEntry 67371008}

pr1645v2Lan2FGOutQueuesOctetsEirTx OBJECT-TYPE
   SYNTAX      Counter64
   MAX-ACCESS  read-only
   STATUS      current
   DESCRIPTION
      "Path: ethernet2.performance.ifOutPriorityQueues.octets.eirTx

       64 bit unsigned wrappable counter."
   ::= {pr1645v2Lan2FGOutQueuesEntry 67436544}

pr1645v2Lan2FGOutQueuesOctetsViolateTx OBJECT-TYPE
   SYNTAX      Counter64
   MAX-ACCESS  read-only
   STATUS      current
   DESCRIPTION
      "Path: ethernet2.performance.ifOutPriorityQueues.octets.violateTx

       64 bit unsigned wrappable counter."
   ::= {pr1645v2Lan2FGOutQueuesEntry 67633152}

pr1645v2Lan2FGOutQueuesOctetsBandwidth15sec OBJECT-TYPE
   SYNTAX      Integer32
   MAX-ACCESS  read-only
   STATUS      current
   DESCRIPTION
      "Path: ethernet2.performance.ifOutPriorityQueues.octets.bandwidth.15sec

       unit name = bps
       formula = 8 * ; 8 /"
   ::= {pr1645v2Lan2FGOutQueuesEntry 70386944}

pr1645v2Lan2FGOutQueuesOctetsBandwidth30sec OBJECT-TYPE
   SYNTAX      Integer32
   MAX-ACCESS  read-only
   STATUS      current
   DESCRIPTION
      "Path: ethernet2.performance.ifOutPriorityQueues.octets.bandwidth.30sec

       unit name = bps
       formula = 8 * ; 8 /"
   ::= {pr1645v2Lan2FGOutQueuesEntry 70388224}

pr1645v2Lan2FGOutQueuesOctetsBandwidth1min OBJECT-TYPE
   SYNTAX      Integer32
   MAX-ACCESS  read-only
   STATUS      current
   DESCRIPTION
      "Path: ethernet2.performance.ifOutPriorityQueues.octets.bandwidth.1min

       unit name = bps
       formula = 8 * ; 8 /"
   ::= {pr1645v2Lan2FGOutQueuesEntry 70390784}

pr1645v2Lan2FGOutQueuesOctetsBandwidth2min OBJECT-TYPE
   SYNTAX      Integer32
   MAX-ACCESS  read-only
   STATUS      current
   DESCRIPTION
      "Path: ethernet2.performance.ifOutPriorityQueues.octets.bandwidth.2min

       unit name = bps
       formula = 8 * ; 8 /"
   ::= {pr1645v2Lan2FGOutQueuesEntry 70395904}

pr1645v2Lan2FGOutQueuesOctetsBandwidth5min OBJECT-TYPE
   SYNTAX      Integer32
   MAX-ACCESS  read-only
   STATUS      current
   DESCRIPTION
      "Path: ethernet2.performance.ifOutPriorityQueues.octets.bandwidth.5min

       unit name = bps
       formula = 8 * ; 8 /"
   ::= {pr1645v2Lan2FGOutQueuesEntry 70411264}

pr1645v2Lan2FGOutQueuesH2Performance OBJECT-TYPE
   SYNTAX      SEQUENCE OF Pr1645v2Lan2FGOutQueuesH2PerformanceEntry
   MAX-ACCESS  not-accessible
   STATUS      current
   DESCRIPTION
      ""
   ::= {pr1645v2Lan2FGOutQueues 83886080}

pr1645v2Lan2FGOutQueuesH2PerformanceEntry OBJECT-TYPE
   SYNTAX      Pr1645v2Lan2FGOutQueuesH2PerformanceEntry
   MAX-ACCESS  not-accessible
   STATUS      current
   DESCRIPTION
      ""
   INDEX      { pr1645v2Lan2FGOutQueuesTableIx,
                pr1645v2Lan2FGOutQueuesH2PerformanceTableIx }
   ::= {pr1645v2Lan2FGOutQueuesH2Performance 1}

Pr1645v2Lan2FGOutQueuesH2PerformanceEntry ::=
   SEQUENCE
      {
      pr1645v2Lan2FGOutQueuesH2PerformanceTableIx
         TableIndex,
      pr1645v2Lan2FGOutQueuesH2PerformanceSysUpTime
         TimeTicks,
      pr1645v2Lan2FGOutQueuesH2PerformanceTotPkts
         Counter64,
      pr1645v2Lan2FGOutQueuesH2PerformanceDirTxPkts
         Counter64,
      pr1645v2Lan2FGOutQueuesH2PerformanceQdPkts
         Counter64,
      pr1645v2Lan2FGOutQueuesH2PerformanceDropPkts
         Counter64,
      pr1645v2Lan2FGOutQueuesH2PerformanceRDropPkts
         Counter64,
      pr1645v2Lan2FGOutQueuesH2PerformanceCirTxPkts
         Counter64,
      pr1645v2Lan2FGOutQueuesH2PerformanceEirTxPkts
         Counter64,
      pr1645v2Lan2FGOutQueuesH2PerformanceViolTxPkts
         Counter64,
      pr1645v2Lan2FGOutQueuesH2PerformanceTotOcts
         Counter64,
      pr1645v2Lan2FGOutQueuesH2PerformanceDirTxOcts
         Counter64,
      pr1645v2Lan2FGOutQueuesH2PerformanceQdOcts
         Counter64,
      pr1645v2Lan2FGOutQueuesH2PerformanceDropOcts
         Counter64,
      pr1645v2Lan2FGOutQueuesH2PerformanceRDropOcts
         Counter64,
      pr1645v2Lan2FGOutQueuesH2PerformanceCirTxOcts
         Counter64,
      pr1645v2Lan2FGOutQueuesH2PerformanceEirTxOcts
         Counter64,
      pr1645v2Lan2FGOutQueuesH2PerformanceViolTxOcts
         Counter64,
      pr1645v2Lan2FGOutQueuesH2PerformanceBandwidth
         Integer32
      }

pr1645v2Lan2FGOutQueuesH2PerformanceTableIx OBJECT-TYPE
   SYNTAX      TableIndex
   MAX-ACCESS  not-accessible
   STATUS      current
   DESCRIPTION
      ""
   ::= {pr1645v2Lan2FGOutQueuesH2PerformanceEntry 11}

pr1645v2Lan2FGOutQueuesH2PerformanceSysUpTime OBJECT-TYPE
   SYNTAX      TimeTicks
   MAX-ACCESS  read-only
   STATUS      current
   DESCRIPTION
      "Path: ethernet2.performance.ifOutPriorityQueues.h2Performance.sysUpTime

       Time in centi-second."
   ::= {pr1645v2Lan2FGOutQueuesH2PerformanceEntry 16777216}

pr1645v2Lan2FGOutQueuesH2PerformanceTotPkts OBJECT-TYPE
   SYNTAX      Counter64
   MAX-ACCESS  read-only
   STATUS      current
   DESCRIPTION
      "Path: ethernet2.performance.ifOutPriorityQueues.h2Performance.totalPkts

       64 bit unsigned wrappable counter."
   ::= {pr1645v2Lan2FGOutQueuesH2PerformanceEntry 234881024}

pr1645v2Lan2FGOutQueuesH2PerformanceDirTxPkts OBJECT-TYPE
   SYNTAX      Counter64
   MAX-ACCESS  read-only
   STATUS      current
   DESCRIPTION
      "Path: ethernet2.performance.ifOutPriorityQueues.h2Performance.directTxPkts

       64 bit unsigned wrappable counter."
   ::= {pr1645v2Lan2FGOutQueuesH2PerformanceEntry 33554432}

pr1645v2Lan2FGOutQueuesH2PerformanceQdPkts OBJECT-TYPE
   SYNTAX      Counter64
   MAX-ACCESS  read-only
   STATUS      current
   DESCRIPTION
      "Path: ethernet2.performance.ifOutPriorityQueues.h2Performance.queuedPkts

       64 bit unsigned wrappable counter."
   ::= {pr1645v2Lan2FGOutQueuesH2PerformanceEntry 50331648}

pr1645v2Lan2FGOutQueuesH2PerformanceDropPkts OBJECT-TYPE
   SYNTAX      Counter64
   MAX-ACCESS  read-only
   STATUS      current
   DESCRIPTION
      "Path: ethernet2.performance.ifOutPriorityQueues.h2Performance.droppedPkts

       64 bit unsigned wrappable counter."
   ::= {pr1645v2Lan2FGOutQueuesH2PerformanceEntry 67108864}

pr1645v2Lan2FGOutQueuesH2PerformanceRDropPkts OBJECT-TYPE
   SYNTAX      Counter64
   MAX-ACCESS  read-only
   STATUS      current
   DESCRIPTION
      "Path: ethernet2.performance.ifOutPriorityQueues.h2Performance.redDroppedPkts

       64 bit unsigned wrappable counter."
   ::= {pr1645v2Lan2FGOutQueuesH2PerformanceEntry 201326592}

pr1645v2Lan2FGOutQueuesH2PerformanceCirTxPkts OBJECT-TYPE
   SYNTAX      Counter64
   MAX-ACCESS  read-only
   STATUS      current
   DESCRIPTION
      "Path: ethernet2.performance.ifOutPriorityQueues.h2Performance.cirTxPkts

       64 bit unsigned wrappable counter."
   ::= {pr1645v2Lan2FGOutQueuesH2PerformanceEntry 83886080}

pr1645v2Lan2FGOutQueuesH2PerformanceEirTxPkts OBJECT-TYPE
   SYNTAX      Counter64
   MAX-ACCESS  read-only
   STATUS      current
   DESCRIPTION
      "Path: ethernet2.performance.ifOutPriorityQueues.h2Performance.eirTxPkts

       64 bit unsigned wrappable counter."
   ::= {pr1645v2Lan2FGOutQueuesH2PerformanceEntry 100663296}

pr1645v2Lan2FGOutQueuesH2PerformanceViolTxPkts OBJECT-TYPE
   SYNTAX      Counter64
   MAX-ACCESS  read-only
   STATUS      current
   DESCRIPTION
      "Path: ethernet2.performance.ifOutPriorityQueues.h2Performance.violateTxPkts

       64 bit unsigned wrappable counter."
   ::= {pr1645v2Lan2FGOutQueuesH2PerformanceEntry 301989888}

pr1645v2Lan2FGOutQueuesH2PerformanceTotOcts OBJECT-TYPE
   SYNTAX      Counter64
   MAX-ACCESS  read-only
   STATUS      current
   DESCRIPTION
      "Path: ethernet2.performance.ifOutPriorityQueues.h2Performance.totalOctets

       64 bit unsigned wrappable counter."
   ::= {pr1645v2Lan2FGOutQueuesH2PerformanceEntry 251658240}

pr1645v2Lan2FGOutQueuesH2PerformanceDirTxOcts OBJECT-TYPE
   SYNTAX      Counter64
   MAX-ACCESS  read-only
   STATUS      current
   DESCRIPTION
      "Path: ethernet2.performance.ifOutPriorityQueues.h2Performance.directTxOctets

       64 bit unsigned wrappable counter."
   ::= {pr1645v2Lan2FGOutQueuesH2PerformanceEntry 117440512}

pr1645v2Lan2FGOutQueuesH2PerformanceQdOcts OBJECT-TYPE
   SYNTAX      Counter64
   MAX-ACCESS  read-only
   STATUS      current
   DESCRIPTION
      "Path: ethernet2.performance.ifOutPriorityQueues.h2Performance.queuedOctets

       64 bit unsigned wrappable counter."
   ::= {pr1645v2Lan2FGOutQueuesH2PerformanceEntry 134217728}

pr1645v2Lan2FGOutQueuesH2PerformanceDropOcts OBJECT-TYPE
   SYNTAX      Counter64
   MAX-ACCESS  read-only
   STATUS      current
   DESCRIPTION
      "Path: ethernet2.performance.ifOutPriorityQueues.h2Performance.droppedOctets

       64 bit unsigned wrappable counter."
   ::= {pr1645v2Lan2FGOutQueuesH2PerformanceEntry 150994944}

pr1645v2Lan2FGOutQueuesH2PerformanceRDropOcts OBJECT-TYPE
   SYNTAX      Counter64
   MAX-ACCESS  read-only
   STATUS      current
   DESCRIPTION
      "Path: ethernet2.performance.ifOutPriorityQueues.h2Performance.redDroppedOctets

       64 bit unsigned wrappable counter."
   ::= {pr1645v2Lan2FGOutQueuesH2PerformanceEntry 218103808}

pr1645v2Lan2FGOutQueuesH2PerformanceCirTxOcts OBJECT-TYPE
   SYNTAX      Counter64
   MAX-ACCESS  read-only
   STATUS      current
   DESCRIPTION
      "Path: ethernet2.performance.ifOutPriorityQueues.h2Performance.cirTxOctets

       64 bit unsigned wrappable counter."
   ::= {pr1645v2Lan2FGOutQueuesH2PerformanceEntry 167772160}

pr1645v2Lan2FGOutQueuesH2PerformanceEirTxOcts OBJECT-TYPE
   SYNTAX      Counter64
   MAX-ACCESS  read-only
   STATUS      current
   DESCRIPTION
      "Path: ethernet2.performance.ifOutPriorityQueues.h2Performance.eirTxOctets

       64 bit unsigned wrappable counter."
   ::= {pr1645v2Lan2FGOutQueuesH2PerformanceEntry 184549376}

pr1645v2Lan2FGOutQueuesH2PerformanceViolTxOcts OBJECT-TYPE
   SYNTAX      Counter64
   MAX-ACCESS  read-only
   STATUS      current
   DESCRIPTION
      "Path: ethernet2.performance.ifOutPriorityQueues.h2Performance.violateTxOctets

       64 bit unsigned wrappable counter."
   ::= {pr1645v2Lan2FGOutQueuesH2PerformanceEntry 318767104}

pr1645v2Lan2FGOutQueuesH2PerformanceBandwidth OBJECT-TYPE
   SYNTAX      Integer32
   MAX-ACCESS  read-only
   STATUS      current
   DESCRIPTION
      "Path: ethernet2.performance.ifOutPriorityQueues.h2Performance.bandwidth

       unit name = bps
       formula = 8 * ; 8 /"
   ::= {pr1645v2Lan2FGOutQueuesH2PerformanceEntry 268435456}

pr1645v2Lan2FGOutQueuesH24Performance OBJECT-TYPE
   SYNTAX      SEQUENCE OF Pr1645v2Lan2FGOutQueuesH24PerformanceEntry
   MAX-ACCESS  not-accessible
   STATUS      current
   DESCRIPTION
      ""
   ::= {pr1645v2Lan2FGOutQueues 100663296}

pr1645v2Lan2FGOutQueuesH24PerformanceEntry OBJECT-TYPE
   SYNTAX      Pr1645v2Lan2FGOutQueuesH24PerformanceEntry
   MAX-ACCESS  not-accessible
   STATUS      current
   DESCRIPTION
      ""
   INDEX      { pr1645v2Lan2FGOutQueuesTableIx,
                pr1645v2Lan2FGOutQueuesH24PerformanceTableIx }
   ::= {pr1645v2Lan2FGOutQueuesH24Performance 1}

Pr1645v2Lan2FGOutQueuesH24PerformanceEntry ::=
   SEQUENCE
      {
      pr1645v2Lan2FGOutQueuesH24PerformanceTableIx
         TableIndex,
      pr1645v2Lan2FGOutQueuesH24PerformanceSysUpTime
         TimeTicks,
      pr1645v2Lan2FGOutQueuesH24PerformanceTotPkts
         Counter64,
      pr1645v2Lan2FGOutQueuesH24PerformanceDirTxPkts
         Counter64,
      pr1645v2Lan2FGOutQueuesH24PerformanceQdPkts
         Counter64,
      pr1645v2Lan2FGOutQueuesH24PerformanceDropPkts
         Counter64,
      pr1645v2Lan2FGOutQueuesH24PerformanceRDropPkts
         Counter64,
      pr1645v2Lan2FGOutQueuesH24PerformanceCirTxPkts
         Counter64,
      pr1645v2Lan2FGOutQueuesH24PerformanceEirTxPkts
         Counter64,
      pr1645v2Lan2FGOutQueuesH24PerformanceViolTxPkts
         Counter64,
      pr1645v2Lan2FGOutQueuesH24PerformanceTotOcts
         Counter64,
      pr1645v2Lan2FGOutQueuesH24PerformanceDirTxOcts
         Counter64,
      pr1645v2Lan2FGOutQueuesH24PerformanceQdOcts
         Counter64,
      pr1645v2Lan2FGOutQueuesH24PerformanceDropOcts
         Counter64,
      pr1645v2Lan2FGOutQueuesH24PerformanceRDropOcts
         Counter64,
      pr1645v2Lan2FGOutQueuesH24PerformanceCirTxOcts
         Counter64,
      pr1645v2Lan2FGOutQueuesH24PerformanceEirTxOcts
         Counter64,
      pr1645v2Lan2FGOutQueuesH24PerformanceViolTxOcts
         Counter64,
      pr1645v2Lan2FGOutQueuesH24PerformanceBandwidth
         Integer32
      }

pr1645v2Lan2FGOutQueuesH24PerformanceTableIx OBJECT-TYPE
   SYNTAX      TableIndex
   MAX-ACCESS  not-accessible
   STATUS      current
   DESCRIPTION
      ""
   ::= {pr1645v2Lan2FGOutQueuesH24PerformanceEntry 11}

pr1645v2Lan2FGOutQueuesH24PerformanceSysUpTime OBJECT-TYPE
   SYNTAX      TimeTicks
   MAX-ACCESS  read-only
   STATUS      current
   DESCRIPTION
      "Path: ethernet2.performance.ifOutPriorityQueues.h24Performance.sysUpTime

       Time in centi-second."
   ::= {pr1645v2Lan2FGOutQueuesH24PerformanceEntry 16777216}

pr1645v2Lan2FGOutQueuesH24PerformanceTotPkts OBJECT-TYPE
   SYNTAX      Counter64
   MAX-ACCESS  read-only
   STATUS      current
   DESCRIPTION
      "Path: ethernet2.performance.ifOutPriorityQueues.h24Performance.totalPkts

       64 bit unsigned wrappable counter."
   ::= {pr1645v2Lan2FGOutQueuesH24PerformanceEntry 234881024}

pr1645v2Lan2FGOutQueuesH24PerformanceDirTxPkts OBJECT-TYPE
   SYNTAX      Counter64
   MAX-ACCESS  read-only
   STATUS      current
   DESCRIPTION
      "Path: ethernet2.performance.ifOutPriorityQueues.h24Performance.directTxPkts

       64 bit unsigned wrappable counter."
   ::= {pr1645v2Lan2FGOutQueuesH24PerformanceEntry 33554432}

pr1645v2Lan2FGOutQueuesH24PerformanceQdPkts OBJECT-TYPE
   SYNTAX      Counter64
   MAX-ACCESS  read-only
   STATUS      current
   DESCRIPTION
      "Path: ethernet2.performance.ifOutPriorityQueues.h24Performance.queuedPkts

       64 bit unsigned wrappable counter."
   ::= {pr1645v2Lan2FGOutQueuesH24PerformanceEntry 50331648}

pr1645v2Lan2FGOutQueuesH24PerformanceDropPkts OBJECT-TYPE
   SYNTAX      Counter64
   MAX-ACCESS  read-only
   STATUS      current
   DESCRIPTION
      "Path: ethernet2.performance.ifOutPriorityQueues.h24Performance.droppedPkts

       64 bit unsigned wrappable counter."
   ::= {pr1645v2Lan2FGOutQueuesH24PerformanceEntry 67108864}

pr1645v2Lan2FGOutQueuesH24PerformanceRDropPkts OBJECT-TYPE
   SYNTAX      Counter64
   MAX-ACCESS  read-only
   STATUS      current
   DESCRIPTION
      "Path: ethernet2.performance.ifOutPriorityQueues.h24Performance.redDroppedPkts

       64 bit unsigned wrappable counter."
   ::= {pr1645v2Lan2FGOutQueuesH24PerformanceEntry 201326592}

pr1645v2Lan2FGOutQueuesH24PerformanceCirTxPkts OBJECT-TYPE
   SYNTAX      Counter64
   MAX-ACCESS  read-only
   STATUS      current
   DESCRIPTION
      "Path: ethernet2.performance.ifOutPriorityQueues.h24Performance.cirTxPkts

       64 bit unsigned wrappable counter."
   ::= {pr1645v2Lan2FGOutQueuesH24PerformanceEntry 83886080}

pr1645v2Lan2FGOutQueuesH24PerformanceEirTxPkts OBJECT-TYPE
   SYNTAX      Counter64
   MAX-ACCESS  read-only
   STATUS      current
   DESCRIPTION
      "Path: ethernet2.performance.ifOutPriorityQueues.h24Performance.eirTxPkts

       64 bit unsigned wrappable counter."
   ::= {pr1645v2Lan2FGOutQueuesH24PerformanceEntry 100663296}

pr1645v2Lan2FGOutQueuesH24PerformanceViolTxPkts OBJECT-TYPE
   SYNTAX      Counter64
   MAX-ACCESS  read-only
   STATUS      current
   DESCRIPTION
      "Path: ethernet2.performance.ifOutPriorityQueues.h24Performance.violateTxPkts

       64 bit unsigned wrappable counter."
   ::= {pr1645v2Lan2FGOutQueuesH24PerformanceEntry 301989888}

pr1645v2Lan2FGOutQueuesH24PerformanceTotOcts OBJECT-TYPE
   SYNTAX      Counter64
   MAX-ACCESS  read-only
   STATUS      current
   DESCRIPTION
      "Path: ethernet2.performance.ifOutPriorityQueues.h24Performance.totalOctets

       64 bit unsigned wrappable counter."
   ::= {pr1645v2Lan2FGOutQueuesH24PerformanceEntry 251658240}

pr1645v2Lan2FGOutQueuesH24PerformanceDirTxOcts OBJECT-TYPE
   SYNTAX      Counter64
   MAX-ACCESS  read-only
   STATUS      current
   DESCRIPTION
      "Path: ethernet2.performance.ifOutPriorityQueues.h24Performance.directTxOctets

       64 bit unsigned wrappable counter."
   ::= {pr1645v2Lan2FGOutQueuesH24PerformanceEntry 117440512}

pr1645v2Lan2FGOutQueuesH24PerformanceQdOcts OBJECT-TYPE
   SYNTAX      Counter64
   MAX-ACCESS  read-only
   STATUS      current
   DESCRIPTION
      "Path: ethernet2.performance.ifOutPriorityQueues.h24Performance.queuedOctets

       64 bit unsigned wrappable counter."
   ::= {pr1645v2Lan2FGOutQueuesH24PerformanceEntry 134217728}

pr1645v2Lan2FGOutQueuesH24PerformanceDropOcts OBJECT-TYPE
   SYNTAX      Counter64
   MAX-ACCESS  read-only
   STATUS      current
   DESCRIPTION
      "Path: ethernet2.performance.ifOutPriorityQueues.h24Performance.droppedOctets

       64 bit unsigned wrappable counter."
   ::= {pr1645v2Lan2FGOutQueuesH24PerformanceEntry 150994944}

pr1645v2Lan2FGOutQueuesH24PerformanceRDropOcts OBJECT-TYPE
   SYNTAX      Counter64
   MAX-ACCESS  read-only
   STATUS      current
   DESCRIPTION
      "Path: ethernet2.performance.ifOutPriorityQueues.h24Performance.redDroppedOctets

       64 bit unsigned wrappable counter."
   ::= {pr1645v2Lan2FGOutQueuesH24PerformanceEntry 218103808}

pr1645v2Lan2FGOutQueuesH24PerformanceCirTxOcts OBJECT-TYPE
   SYNTAX      Counter64
   MAX-ACCESS  read-only
   STATUS      current
   DESCRIPTION
      "Path: ethernet2.performance.ifOutPriorityQueues.h24Performance.cirTxOctets

       64 bit unsigned wrappable counter."
   ::= {pr1645v2Lan2FGOutQueuesH24PerformanceEntry 167772160}

pr1645v2Lan2FGOutQueuesH24PerformanceEirTxOcts OBJECT-TYPE
   SYNTAX      Counter64
   MAX-ACCESS  read-only
   STATUS      current
   DESCRIPTION
      "Path: ethernet2.performance.ifOutPriorityQueues.h24Performance.eirTxOctets

       64 bit unsigned wrappable counter."
   ::= {pr1645v2Lan2FGOutQueuesH24PerformanceEntry 184549376}

pr1645v2Lan2FGOutQueuesH24PerformanceViolTxOcts OBJECT-TYPE
   SYNTAX      Counter64
   MAX-ACCESS  read-only
   STATUS      current
   DESCRIPTION
      "Path: ethernet2.performance.ifOutPriorityQueues.h24Performance.violateTxOctets

       64 bit unsigned wrappable counter."
   ::= {pr1645v2Lan2FGOutQueuesH24PerformanceEntry 318767104}

pr1645v2Lan2FGOutQueuesH24PerformanceBandwidth OBJECT-TYPE
   SYNTAX      Integer32
   MAX-ACCESS  read-only
   STATUS      current
   DESCRIPTION
      "Path: ethernet2.performance.ifOutPriorityQueues.h24Performance.bandwidth

       unit name = bps
       formula = 8 * ; 8 /"
   ::= {pr1645v2Lan2FGOutQueuesH24PerformanceEntry 268435456}

pr1645v2Lan2FGOutQueuesD7Performance OBJECT-TYPE
   SYNTAX      SEQUENCE OF Pr1645v2Lan2FGOutQueuesD7PerformanceEntry
   MAX-ACCESS  not-accessible
   STATUS      current
   DESCRIPTION
      ""
   ::= {pr1645v2Lan2FGOutQueues 117440512}

pr1645v2Lan2FGOutQueuesD7PerformanceEntry OBJECT-TYPE
   SYNTAX      Pr1645v2Lan2FGOutQueuesD7PerformanceEntry
   MAX-ACCESS  not-accessible
   STATUS      current
   DESCRIPTION
      ""
   INDEX      { pr1645v2Lan2FGOutQueuesTableIx,
                pr1645v2Lan2FGOutQueuesD7PerformanceTableIx }
   ::= {pr1645v2Lan2FGOutQueuesD7Performance 1}

Pr1645v2Lan2FGOutQueuesD7PerformanceEntry ::=
   SEQUENCE
      {
      pr1645v2Lan2FGOutQueuesD7PerformanceTableIx
         TableIndex,
      pr1645v2Lan2FGOutQueuesD7PerformanceSysUpTime
         TimeTicks,
      pr1645v2Lan2FGOutQueuesD7PerformanceTotPkts
         Counter64,
      pr1645v2Lan2FGOutQueuesD7PerformanceDirTxPkts
         Counter64,
      pr1645v2Lan2FGOutQueuesD7PerformanceQdPkts
         Counter64,
      pr1645v2Lan2FGOutQueuesD7PerformanceDropPkts
         Counter64,
      pr1645v2Lan2FGOutQueuesD7PerformanceRDropPkts
         Counter64,
      pr1645v2Lan2FGOutQueuesD7PerformanceCirTxPkts
         Counter64,
      pr1645v2Lan2FGOutQueuesD7PerformanceEirTxPkts
         Counter64,
      pr1645v2Lan2FGOutQueuesD7PerformanceViolTxPkts
         Counter64,
      pr1645v2Lan2FGOutQueuesD7PerformanceTotOcts
         Counter64,
      pr1645v2Lan2FGOutQueuesD7PerformanceDirTxOcts
         Counter64,
      pr1645v2Lan2FGOutQueuesD7PerformanceQdOcts
         Counter64,
      pr1645v2Lan2FGOutQueuesD7PerformanceDropOcts
         Counter64,
      pr1645v2Lan2FGOutQueuesD7PerformanceRDropOcts
         Counter64,
      pr1645v2Lan2FGOutQueuesD7PerformanceCirTxOcts
         Counter64,
      pr1645v2Lan2FGOutQueuesD7PerformanceEirTxOcts
         Counter64,
      pr1645v2Lan2FGOutQueuesD7PerformanceViolTxOcts
         Counter64,
      pr1645v2Lan2FGOutQueuesD7PerformanceBandwidth
         Integer32
      }

pr1645v2Lan2FGOutQueuesD7PerformanceTableIx OBJECT-TYPE
   SYNTAX      TableIndex
   MAX-ACCESS  not-accessible
   STATUS      current
   DESCRIPTION
      ""
   ::= {pr1645v2Lan2FGOutQueuesD7PerformanceEntry 11}

pr1645v2Lan2FGOutQueuesD7PerformanceSysUpTime OBJECT-TYPE
   SYNTAX      TimeTicks
   MAX-ACCESS  read-only
   STATUS      current
   DESCRIPTION
      "Path: ethernet2.performance.ifOutPriorityQueues.d7Performance.sysUpTime

       Time in centi-second."
   ::= {pr1645v2Lan2FGOutQueuesD7PerformanceEntry 16777216}

pr1645v2Lan2FGOutQueuesD7PerformanceTotPkts OBJECT-TYPE
   SYNTAX      Counter64
   MAX-ACCESS  read-only
   STATUS      current
   DESCRIPTION
      "Path: ethernet2.performance.ifOutPriorityQueues.d7Performance.totalPkts

       64 bit unsigned wrappable counter."
   ::= {pr1645v2Lan2FGOutQueuesD7PerformanceEntry 234881024}

pr1645v2Lan2FGOutQueuesD7PerformanceDirTxPkts OBJECT-TYPE
   SYNTAX      Counter64
   MAX-ACCESS  read-only
   STATUS      current
   DESCRIPTION
      "Path: ethernet2.performance.ifOutPriorityQueues.d7Performance.directTxPkts

       64 bit unsigned wrappable counter."
   ::= {pr1645v2Lan2FGOutQueuesD7PerformanceEntry 33554432}

pr1645v2Lan2FGOutQueuesD7PerformanceQdPkts OBJECT-TYPE
   SYNTAX      Counter64
   MAX-ACCESS  read-only
   STATUS      current
   DESCRIPTION
      "Path: ethernet2.performance.ifOutPriorityQueues.d7Performance.queuedPkts

       64 bit unsigned wrappable counter."
   ::= {pr1645v2Lan2FGOutQueuesD7PerformanceEntry 50331648}

pr1645v2Lan2FGOutQueuesD7PerformanceDropPkts OBJECT-TYPE
   SYNTAX      Counter64
   MAX-ACCESS  read-only
   STATUS      current
   DESCRIPTION
      "Path: ethernet2.performance.ifOutPriorityQueues.d7Performance.droppedPkts

       64 bit unsigned wrappable counter."
   ::= {pr1645v2Lan2FGOutQueuesD7PerformanceEntry 67108864}

pr1645v2Lan2FGOutQueuesD7PerformanceRDropPkts OBJECT-TYPE
   SYNTAX      Counter64
   MAX-ACCESS  read-only
   STATUS      current
   DESCRIPTION
      "Path: ethernet2.performance.ifOutPriorityQueues.d7Performance.redDroppedPkts

       64 bit unsigned wrappable counter."
   ::= {pr1645v2Lan2FGOutQueuesD7PerformanceEntry 201326592}

pr1645v2Lan2FGOutQueuesD7PerformanceCirTxPkts OBJECT-TYPE
   SYNTAX      Counter64
   MAX-ACCESS  read-only
   STATUS      current
   DESCRIPTION
      "Path: ethernet2.performance.ifOutPriorityQueues.d7Performance.cirTxPkts

       64 bit unsigned wrappable counter."
   ::= {pr1645v2Lan2FGOutQueuesD7PerformanceEntry 83886080}

pr1645v2Lan2FGOutQueuesD7PerformanceEirTxPkts OBJECT-TYPE
   SYNTAX      Counter64
   MAX-ACCESS  read-only
   STATUS      current
   DESCRIPTION
      "Path: ethernet2.performance.ifOutPriorityQueues.d7Performance.eirTxPkts

       64 bit unsigned wrappable counter."
   ::= {pr1645v2Lan2FGOutQueuesD7PerformanceEntry 100663296}

pr1645v2Lan2FGOutQueuesD7PerformanceViolTxPkts OBJECT-TYPE
   SYNTAX      Counter64
   MAX-ACCESS  read-only
   STATUS      current
   DESCRIPTION
      "Path: ethernet2.performance.ifOutPriorityQueues.d7Performance.violateTxPkts

       64 bit unsigned wrappable counter."
   ::= {pr1645v2Lan2FGOutQueuesD7PerformanceEntry 301989888}

pr1645v2Lan2FGOutQueuesD7PerformanceTotOcts OBJECT-TYPE
   SYNTAX      Counter64
   MAX-ACCESS  read-only
   STATUS      current
   DESCRIPTION
      "Path: ethernet2.performance.ifOutPriorityQueues.d7Performance.totalOctets

       64 bit unsigned wrappable counter."
   ::= {pr1645v2Lan2FGOutQueuesD7PerformanceEntry 251658240}

pr1645v2Lan2FGOutQueuesD7PerformanceDirTxOcts OBJECT-TYPE
   SYNTAX      Counter64
   MAX-ACCESS  read-only
   STATUS      current
   DESCRIPTION
      "Path: ethernet2.performance.ifOutPriorityQueues.d7Performance.directTxOctets

       64 bit unsigned wrappable counter."
   ::= {pr1645v2Lan2FGOutQueuesD7PerformanceEntry 117440512}

pr1645v2Lan2FGOutQueuesD7PerformanceQdOcts OBJECT-TYPE
   SYNTAX      Counter64
   MAX-ACCESS  read-only
   STATUS      current
   DESCRIPTION
      "Path: ethernet2.performance.ifOutPriorityQueues.d7Performance.queuedOctets

       64 bit unsigned wrappable counter."
   ::= {pr1645v2Lan2FGOutQueuesD7PerformanceEntry 134217728}

pr1645v2Lan2FGOutQueuesD7PerformanceDropOcts OBJECT-TYPE
   SYNTAX      Counter64
   MAX-ACCESS  read-only
   STATUS      current
   DESCRIPTION
      "Path: ethernet2.performance.ifOutPriorityQueues.d7Performance.droppedOctets

       64 bit unsigned wrappable counter."
   ::= {pr1645v2Lan2FGOutQueuesD7PerformanceEntry 150994944}

pr1645v2Lan2FGOutQueuesD7PerformanceRDropOcts OBJECT-TYPE
   SYNTAX      Counter64
   MAX-ACCESS  read-only
   STATUS      current
   DESCRIPTION
      "Path: ethernet2.performance.ifOutPriorityQueues.d7Performance.redDroppedOctets

       64 bit unsigned wrappable counter."
   ::= {pr1645v2Lan2FGOutQueuesD7PerformanceEntry 218103808}

pr1645v2Lan2FGOutQueuesD7PerformanceCirTxOcts OBJECT-TYPE
   SYNTAX      Counter64
   MAX-ACCESS  read-only
   STATUS      current
   DESCRIPTION
      "Path: ethernet2.performance.ifOutPriorityQueues.d7Performance.cirTxOctets

       64 bit unsigned wrappable counter."
   ::= {pr1645v2Lan2FGOutQueuesD7PerformanceEntry 167772160}

pr1645v2Lan2FGOutQueuesD7PerformanceEirTxOcts OBJECT-TYPE
   SYNTAX      Counter64
   MAX-ACCESS  read-only
   STATUS      current
   DESCRIPTION
      "Path: ethernet2.performance.ifOutPriorityQueues.d7Performance.eirTxOctets

       64 bit unsigned wrappable counter."
   ::= {pr1645v2Lan2FGOutQueuesD7PerformanceEntry 184549376}

pr1645v2Lan2FGOutQueuesD7PerformanceViolTxOcts OBJECT-TYPE
   SYNTAX      Counter64
   MAX-ACCESS  read-only
   STATUS      current
   DESCRIPTION
      "Path: ethernet2.performance.ifOutPriorityQueues.d7Performance.violateTxOctets

       64 bit unsigned wrappable counter."
   ::= {pr1645v2Lan2FGOutQueuesD7PerformanceEntry 318767104}

pr1645v2Lan2FGOutQueuesD7PerformanceBandwidth OBJECT-TYPE
   SYNTAX      Integer32
   MAX-ACCESS  read-only
   STATUS      current
   DESCRIPTION
      "Path: ethernet2.performance.ifOutPriorityQueues.d7Performance.bandwidth

       unit name = bps
       formula = 8 * ; 8 /"
   ::= {pr1645v2Lan2FGOutQueuesD7PerformanceEntry 268435456}


pr1645v2Lan2FGOutBandwidth OBJECT IDENTIFIER ::= {pr1645v2Lan2FG 182}

pr1645v2Lan2FGOutBandwidthSSC OBJECT IDENTIFIER ::= {pr1645v2Lan2FGOutBandwidth 1}

pr1645v2Lan2FGOutBandwidthEntry OBJECT IDENTIFIER ::= {pr1645v2Lan2FGOutBandwidthSSC 1}

pr1645v2Lan2FGOutBandwidth15sec OBJECT-TYPE
   SYNTAX      Integer32
   MAX-ACCESS  read-only
   STATUS      current
   DESCRIPTION
      "Path: ethernet2.performance.ifOutBandwidth.15sec

       unit name = bps
       formula = 8 * ; 8 /"
   ::= {pr1645v2Lan2FGOutBandwidthEntry 83886080}

pr1645v2Lan2FGOutBandwidth30sec OBJECT-TYPE
   SYNTAX      Integer32
   MAX-ACCESS  read-only
   STATUS      current
   DESCRIPTION
      "Path: ethernet2.performance.ifOutBandwidth.30sec

       unit name = bps
       formula = 8 * ; 8 /"
   ::= {pr1645v2Lan2FGOutBandwidthEntry 167772160}

pr1645v2Lan2FGOutBandwidth1min OBJECT-TYPE
   SYNTAX      Integer32
   MAX-ACCESS  read-only
   STATUS      current
   DESCRIPTION
      "Path: ethernet2.performance.ifOutBandwidth.1min

       unit name = bps
       formula = 8 * ; 8 /"
   ::= {pr1645v2Lan2FGOutBandwidthEntry 335544320}

pr1645v2Lan2FGOutBandwidth2min OBJECT-TYPE
   SYNTAX      Integer32
   MAX-ACCESS  read-only
   STATUS      current
   DESCRIPTION
      "Path: ethernet2.performance.ifOutBandwidth.2min

       unit name = bps
       formula = 8 * ; 8 /"
   ::= {pr1645v2Lan2FGOutBandwidthEntry 671088640}

pr1645v2Lan2FGOutBandwidth5min OBJECT-TYPE
   SYNTAX      Integer32
   MAX-ACCESS  read-only
   STATUS      current
   DESCRIPTION
      "Path: ethernet2.performance.ifOutBandwidth.5min

       unit name = bps
       formula = 8 * ; 8 /"
   ::= {pr1645v2Lan2FGOutBandwidthEntry 1677721600}


pr1645v2Lan2FGInP OBJECT IDENTIFIER ::= {pr1645v2Lan2FG 307}

pr1645v2Lan2FGInPSSCTable OBJECT-TYPE
   SYNTAX      SEQUENCE OF Pr1645v2Lan2FGInPEntry
   MAX-ACCESS  not-accessible
   STATUS      current
   DESCRIPTION
      "h2IfInPerformance"
   ::= {pr1645v2Lan2FGInP 1}

pr1645v2Lan2FGInPEntry OBJECT-TYPE
   SYNTAX      Pr1645v2Lan2FGInPEntry
   MAX-ACCESS  not-accessible
   STATUS      current
   DESCRIPTION
      ""
   INDEX      { pr1645v2Lan2FGInPTableIx }
   ::= {pr1645v2Lan2FGInPSSCTable 1}

Pr1645v2Lan2FGInPEntry ::=
   SEQUENCE
      {
      pr1645v2Lan2FGInPTableIx
         TableIndex,
      pr1645v2Lan2FGInPSysUpTime
         TimeTicks,
      pr1645v2Lan2FGInPIfUpTime
         TimeTicks,
      pr1645v2Lan2FGInPIfStatChanges
         Counter32,
      pr1645v2Lan2FGInPIfInOctets
         Counter64,
      pr1645v2Lan2FGInPIfInUCPkts
         Counter64,
      pr1645v2Lan2FGInPIfInNUCPkts
         Counter64,
      pr1645v2Lan2FGInPIfInBCPkts
         Counter64,
      pr1645v2Lan2FGInPIfInMCPkts
         Counter64,
      pr1645v2Lan2FGInPIfInDiscards
         Counter64,
      pr1645v2Lan2FGInPIfInErrors
         Counter64,
      pr1645v2Lan2FGInPIfInUnkwn
         Counter64,
      pr1645v2Lan2FGInPInDropEx
         Counter64,
      pr1645v2Lan2FGInPInDropNoMac
         Counter64,
      pr1645v2Lan2FGInPInDropNUCast
         Counter64,
      pr1645v2Lan2FGInPInDropFilter
         Counter64,
      pr1645v2Lan2FGInPIfInBandwidth
         Integer32,
      pr1645v2Lan2FGInPIfOutOctets
         Counter64,
      pr1645v2Lan2FGInPIfOutUCPkts
         Counter64,
      pr1645v2Lan2FGInPIfOutNUCPkts
         Counter64,
      pr1645v2Lan2FGInPIfOutBCPkts
         Counter64,
      pr1645v2Lan2FGInPIfOutMCPkts
         Counter64,
      pr1645v2Lan2FGInPIfOutDiscards
         Counter64,
      pr1645v2Lan2FGInPIfOutErrors
         Counter64,
      pr1645v2Lan2FGInPOutDropEx
         Counter64,
      pr1645v2Lan2FGInPOutDropNoArp
         Counter64,
      pr1645v2Lan2FGInPOutDropFilter
         Counter64,
      pr1645v2Lan2FGInPIfOutBandwidth
         Integer32,
      pr1645v2Lan2FGInPIfErrSec
         Counter32
      }

pr1645v2Lan2FGInPTableIx OBJECT-TYPE
   SYNTAX      TableIndex
   MAX-ACCESS  not-accessible
   STATUS      current
   DESCRIPTION
      ""
   ::= {pr1645v2Lan2FGInPEntry 11}

pr1645v2Lan2FGInPSysUpTime OBJECT-TYPE
   SYNTAX      TimeTicks
   MAX-ACCESS  read-only
   STATUS      current
   DESCRIPTION
      "Path: ethernet2.performance.h2Performance.sysUpTime

       Time in centi-second."
   ::= {pr1645v2Lan2FGInPEntry 16777216}

pr1645v2Lan2FGInPIfUpTime OBJECT-TYPE
   SYNTAX      TimeTicks
   MAX-ACCESS  read-only
   STATUS      current
   DESCRIPTION
      "Path: ethernet2.performance.h2Performance.ifUpTime

       Time in centi-second."
   ::= {pr1645v2Lan2FGInPEntry 33554432}

pr1645v2Lan2FGInPIfStatChanges OBJECT-TYPE
   SYNTAX      Counter32
   MAX-ACCESS  read-only
   STATUS      current
   DESCRIPTION
      "Path: ethernet2.performance.h2Performance.ifStatusChanges

       32 bit unsigned wrappable counter."
   ::= {pr1645v2Lan2FGInPEntry 50331648}

pr1645v2Lan2FGInPIfInOctets OBJECT-TYPE
   SYNTAX      Counter64
   MAX-ACCESS  read-only
   STATUS      current
   DESCRIPTION
      "Path: ethernet2.performance.h2Performance.ifInOctets

       64 bit unsigned wrappable counter."
   ::= {pr1645v2Lan2FGInPEntry 67108864}

pr1645v2Lan2FGInPIfInUCPkts OBJECT-TYPE
   SYNTAX      Counter64
   MAX-ACCESS  read-only
   STATUS      current
   DESCRIPTION
      "Path: ethernet2.performance.h2Performance.ifInUcastPkts

       64 bit unsigned wrappable counter."
   ::= {pr1645v2Lan2FGInPEntry 83886080}

pr1645v2Lan2FGInPIfInNUCPkts OBJECT-TYPE
   SYNTAX      Counter64
   MAX-ACCESS  read-only
   STATUS      current
   DESCRIPTION
      "Path: ethernet2.performance.h2Performance.ifInNUcastPkts

       64 bit unsigned wrappable counter."
   ::= {pr1645v2Lan2FGInPEntry 100663296}

pr1645v2Lan2FGInPIfInBCPkts OBJECT-TYPE
   SYNTAX      Counter64
   MAX-ACCESS  read-only
   STATUS      current
   DESCRIPTION
      "Path: ethernet2.performance.h2Performance.ifInBcastPkts

       64 bit unsigned wrappable counter."
   ::= {pr1645v2Lan2FGInPEntry 419430400}

pr1645v2Lan2FGInPIfInMCPkts OBJECT-TYPE
   SYNTAX      Counter64
   MAX-ACCESS  read-only
   STATUS      current
   DESCRIPTION
      "Path: ethernet2.performance.h2Performance.ifInMcastPkts

       64 bit unsigned wrappable counter."
   ::= {pr1645v2Lan2FGInPEntry 436207616}

pr1645v2Lan2FGInPIfInDiscards OBJECT-TYPE
   SYNTAX      Counter64
   MAX-ACCESS  read-only
   STATUS      current
   DESCRIPTION
      "Path: ethernet2.performance.h2Performance.ifInDiscards

       64 bit unsigned wrappable counter."
   ::= {pr1645v2Lan2FGInPEntry 117440512}

pr1645v2Lan2FGInPIfInErrors OBJECT-TYPE
   SYNTAX      Counter64
   MAX-ACCESS  read-only
   STATUS      current
   DESCRIPTION
      "Path: ethernet2.performance.h2Performance.ifInErrors

       64 bit unsigned wrappable counter."
   ::= {pr1645v2Lan2FGInPEntry 134217728}

pr1645v2Lan2FGInPIfInUnkwn OBJECT-TYPE
   SYNTAX      Counter64
   MAX-ACCESS  read-only
   STATUS      current
   DESCRIPTION
      "Path: ethernet2.performance.h2Performance.ifInUnknownProtos

       64 bit unsigned wrappable counter."
   ::= {pr1645v2Lan2FGInPEntry 150994944}

pr1645v2Lan2FGInPInDropEx OBJECT-TYPE
   SYNTAX      Counter64
   MAX-ACCESS  read-only
   STATUS      current
   DESCRIPTION
      "Path: ethernet2.performance.h2Performance.ifInDropLevelExceeded

       64 bit unsigned wrappable counter."
   ::= {pr1645v2Lan2FGInPEntry 335544320}

pr1645v2Lan2FGInPInDropNoMac OBJECT-TYPE
   SYNTAX      Counter64
   MAX-ACCESS  read-only
   STATUS      current
   DESCRIPTION
      "Path: ethernet2.performance.h2Performance.fInDiscardsNoMacFit

       64 bit unsigned wrappable counter."
   ::= {pr1645v2Lan2FGInPEntry 301989888}

pr1645v2Lan2FGInPInDropNUCast OBJECT-TYPE
   SYNTAX      Counter64
   MAX-ACCESS  read-only
   STATUS      current
   DESCRIPTION
      "Path: ethernet2.performance.h2Performance.fInDiscardsNUCast

       64 bit unsigned wrappable counter."
   ::= {pr1645v2Lan2FGInPEntry 318767104}

pr1645v2Lan2FGInPInDropFilter OBJECT-TYPE
   SYNTAX      Counter64
   MAX-ACCESS  read-only
   STATUS      current
   DESCRIPTION
      "Path: ethernet2.performance.h2Performance.fInDiscardsFilter

       64 bit unsigned wrappable counter."
   ::= {pr1645v2Lan2FGInPEntry 385875968}

pr1645v2Lan2FGInPIfInBandwidth OBJECT-TYPE
   SYNTAX      Integer32
   MAX-ACCESS  read-only
   STATUS      current
   DESCRIPTION
      "Path: ethernet2.performance.h2Performance.ifInBandwidth

       unit name = bps
       formula = 8 * ; 8 /"
   ::= {pr1645v2Lan2FGInPEntry 268435456}

pr1645v2Lan2FGInPIfOutOctets OBJECT-TYPE
   SYNTAX      Counter64
   MAX-ACCESS  read-only
   STATUS      current
   DESCRIPTION
      "Path: ethernet2.performance.h2Performance.ifOutOctets

       64 bit unsigned wrappable counter."
   ::= {pr1645v2Lan2FGInPEntry 167772160}

pr1645v2Lan2FGInPIfOutUCPkts OBJECT-TYPE
   SYNTAX      Counter64
   MAX-ACCESS  read-only
   STATUS      current
   DESCRIPTION
      "Path: ethernet2.performance.h2Performance.ifOutUcastPkts

       64 bit unsigned wrappable counter."
   ::= {pr1645v2Lan2FGInPEntry 184549376}

pr1645v2Lan2FGInPIfOutNUCPkts OBJECT-TYPE
   SYNTAX      Counter64
   MAX-ACCESS  read-only
   STATUS      current
   DESCRIPTION
      "Path: ethernet2.performance.h2Performance.ifOutNUcastPkts

       64 bit unsigned wrappable counter."
   ::= {pr1645v2Lan2FGInPEntry 201326592}

pr1645v2Lan2FGInPIfOutBCPkts OBJECT-TYPE
   SYNTAX      Counter64
   MAX-ACCESS  read-only
   STATUS      current
   DESCRIPTION
      "Path: ethernet2.performance.h2Performance.ifOutBcastPkts

       64 bit unsigned wrappable counter."
   ::= {pr1645v2Lan2FGInPEntry 452984832}

pr1645v2Lan2FGInPIfOutMCPkts OBJECT-TYPE
   SYNTAX      Counter64
   MAX-ACCESS  read-only
   STATUS      current
   DESCRIPTION
      "Path: ethernet2.performance.h2Performance.ifOutMcastPkts

       64 bit unsigned wrappable counter."
   ::= {pr1645v2Lan2FGInPEntry 469762048}

pr1645v2Lan2FGInPIfOutDiscards OBJECT-TYPE
   SYNTAX      Counter64
   MAX-ACCESS  read-only
   STATUS      current
   DESCRIPTION
      "Path: ethernet2.performance.h2Performance.ifOutDiscards

       64 bit unsigned wrappable counter."
   ::= {pr1645v2Lan2FGInPEntry 218103808}

pr1645v2Lan2FGInPIfOutErrors OBJECT-TYPE
   SYNTAX      Counter64
   MAX-ACCESS  read-only
   STATUS      current
   DESCRIPTION
      "Path: ethernet2.performance.h2Performance.ifOutErrors

       64 bit unsigned wrappable counter."
   ::= {pr1645v2Lan2FGInPEntry 234881024}

pr1645v2Lan2FGInPOutDropEx OBJECT-TYPE
   SYNTAX      Counter64
   MAX-ACCESS  read-only
   STATUS      current
   DESCRIPTION
      "Path: ethernet2.performance.h2Performance.ifOutDropLevelExceeded

       64 bit unsigned wrappable counter."
   ::= {pr1645v2Lan2FGInPEntry 352321536}

pr1645v2Lan2FGInPOutDropNoArp OBJECT-TYPE
   SYNTAX      Counter64
   MAX-ACCESS  read-only
   STATUS      current
   DESCRIPTION
      "Path: ethernet2.performance.h2Performance.ifOutDiscardsNoArp

       64 bit unsigned wrappable counter."
   ::= {pr1645v2Lan2FGInPEntry 369098752}

pr1645v2Lan2FGInPOutDropFilter OBJECT-TYPE
   SYNTAX      Counter64
   MAX-ACCESS  read-only
   STATUS      current
   DESCRIPTION
      "Path: ethernet2.performance.h2Performance.ifOutDiscardsFilter

       64 bit unsigned wrappable counter."
   ::= {pr1645v2Lan2FGInPEntry 402653184}

pr1645v2Lan2FGInPIfOutBandwidth OBJECT-TYPE
   SYNTAX      Integer32
   MAX-ACCESS  read-only
   STATUS      current
   DESCRIPTION
      "Path: ethernet2.performance.h2Performance.ifOutBandwidth

       unit name = bps
       formula = 8 * ; 8 /"
   ::= {pr1645v2Lan2FGInPEntry 285212672}

pr1645v2Lan2FGInPIfErrSec OBJECT-TYPE
   SYNTAX      Counter32
   MAX-ACCESS  read-only
   STATUS      current
   DESCRIPTION
      "Path: ethernet2.performance.h2Performance.ifErrSec

       32 bit unsigned wrappable counter."
   ::= {pr1645v2Lan2FGInPEntry 251658240}


pr1645v2Lan2FGH24InP OBJECT IDENTIFIER ::= {pr1645v2Lan2FG 308}

pr1645v2Lan2FGH24InPSSCTable OBJECT-TYPE
   SYNTAX      SEQUENCE OF Pr1645v2Lan2FGH24InPEntry
   MAX-ACCESS  not-accessible
   STATUS      current
   DESCRIPTION
      "h24IfInPerformance"
   ::= {pr1645v2Lan2FGH24InP 1}

pr1645v2Lan2FGH24InPEntry OBJECT-TYPE
   SYNTAX      Pr1645v2Lan2FGH24InPEntry
   MAX-ACCESS  not-accessible
   STATUS      current
   DESCRIPTION
      ""
   INDEX      { pr1645v2Lan2FGH24InPTableIx }
   ::= {pr1645v2Lan2FGH24InPSSCTable 1}

Pr1645v2Lan2FGH24InPEntry ::=
   SEQUENCE
      {
      pr1645v2Lan2FGH24InPTableIx
         TableIndex,
      pr1645v2Lan2FGH24InPSysUpTime
         TimeTicks,
      pr1645v2Lan2FGH24InPIfUpTime
         TimeTicks,
      pr1645v2Lan2FGH24InPIfStatChanges
         Counter32,
      pr1645v2Lan2FGH24InPIfInOctets
         Counter64,
      pr1645v2Lan2FGH24InPIfInUCPkts
         Counter64,
      pr1645v2Lan2FGH24InPIfInNUCPkts
         Counter64,
      pr1645v2Lan2FGH24InPIfInBCPkts
         Counter64,
      pr1645v2Lan2FGH24InPIfInMCPkts
         Counter64,
      pr1645v2Lan2FGH24InPIfInDiscards
         Counter64,
      pr1645v2Lan2FGH24InPIfInErrors
         Counter64,
      pr1645v2Lan2FGH24InPIfInUnkwn
         Counter64,
      pr1645v2Lan2FGH24InPInDropEx
         Counter64,
      pr1645v2Lan2FGH24InPInDropNoMac
         Counter64,
      pr1645v2Lan2FGH24InPInDropNUCast
         Counter64,
      pr1645v2Lan2FGH24InPInDropFilter
         Counter64,
      pr1645v2Lan2FGH24InPIfInBandwidth
         Integer32,
      pr1645v2Lan2FGH24InPIfOutOctets
         Counter64,
      pr1645v2Lan2FGH24InPIfOutUCPkts
         Counter64,
      pr1645v2Lan2FGH24InPIfOutNUCPkts
         Counter64,
      pr1645v2Lan2FGH24InPIfOutBCPkts
         Counter64,
      pr1645v2Lan2FGH24InPIfOutMCPkts
         Counter64,
      pr1645v2Lan2FGH24InPIfOutDiscards
         Counter64,
      pr1645v2Lan2FGH24InPIfOutErrors
         Counter64,
      pr1645v2Lan2FGH24InPOutDropEx
         Counter64,
      pr1645v2Lan2FGH24InPOutDropNoArp
         Counter64,
      pr1645v2Lan2FGH24InPOutDropFilter
         Counter64,
      pr1645v2Lan2FGH24InPIfOutBandwidth
         Integer32,
      pr1645v2Lan2FGH24InPIfErrSec
         Counter32
      }

pr1645v2Lan2FGH24InPTableIx OBJECT-TYPE
   SYNTAX      TableIndex
   MAX-ACCESS  not-accessible
   STATUS      current
   DESCRIPTION
      ""
   ::= {pr1645v2Lan2FGH24InPEntry 11}

pr1645v2Lan2FGH24InPSysUpTime OBJECT-TYPE
   SYNTAX      TimeTicks
   MAX-ACCESS  read-only
   STATUS      current
   DESCRIPTION
      "Path: ethernet2.performance.h24Performance.sysUpTime

       Time in centi-second."
   ::= {pr1645v2Lan2FGH24InPEntry 16777216}

pr1645v2Lan2FGH24InPIfUpTime OBJECT-TYPE
   SYNTAX      TimeTicks
   MAX-ACCESS  read-only
   STATUS      current
   DESCRIPTION
      "Path: ethernet2.performance.h24Performance.ifUpTime

       Time in centi-second."
   ::= {pr1645v2Lan2FGH24InPEntry 33554432}

pr1645v2Lan2FGH24InPIfStatChanges OBJECT-TYPE
   SYNTAX      Counter32
   MAX-ACCESS  read-only
   STATUS      current
   DESCRIPTION
      "Path: ethernet2.performance.h24Performance.ifStatusChanges

       32 bit unsigned wrappable counter."
   ::= {pr1645v2Lan2FGH24InPEntry 50331648}

pr1645v2Lan2FGH24InPIfInOctets OBJECT-TYPE
   SYNTAX      Counter64
   MAX-ACCESS  read-only
   STATUS      current
   DESCRIPTION
      "Path: ethernet2.performance.h24Performance.ifInOctets

       64 bit unsigned wrappable counter."
   ::= {pr1645v2Lan2FGH24InPEntry 67108864}

pr1645v2Lan2FGH24InPIfInUCPkts OBJECT-TYPE
   SYNTAX      Counter64
   MAX-ACCESS  read-only
   STATUS      current
   DESCRIPTION
      "Path: ethernet2.performance.h24Performance.ifInUcastPkts

       64 bit unsigned wrappable counter."
   ::= {pr1645v2Lan2FGH24InPEntry 83886080}

pr1645v2Lan2FGH24InPIfInNUCPkts OBJECT-TYPE
   SYNTAX      Counter64
   MAX-ACCESS  read-only
   STATUS      current
   DESCRIPTION
      "Path: ethernet2.performance.h24Performance.ifInNUcastPkts

       64 bit unsigned wrappable counter."
   ::= {pr1645v2Lan2FGH24InPEntry 100663296}

pr1645v2Lan2FGH24InPIfInBCPkts OBJECT-TYPE
   SYNTAX      Counter64
   MAX-ACCESS  read-only
   STATUS      current
   DESCRIPTION
      "Path: ethernet2.performance.h24Performance.ifInBcastPkts

       64 bit unsigned wrappable counter."
   ::= {pr1645v2Lan2FGH24InPEntry 419430400}

pr1645v2Lan2FGH24InPIfInMCPkts OBJECT-TYPE
   SYNTAX      Counter64
   MAX-ACCESS  read-only
   STATUS      current
   DESCRIPTION
      "Path: ethernet2.performance.h24Performance.ifInMcastPkts

       64 bit unsigned wrappable counter."
   ::= {pr1645v2Lan2FGH24InPEntry 436207616}

pr1645v2Lan2FGH24InPIfInDiscards OBJECT-TYPE
   SYNTAX      Counter64
   MAX-ACCESS  read-only
   STATUS      current
   DESCRIPTION
      "Path: ethernet2.performance.h24Performance.ifInDiscards

       64 bit unsigned wrappable counter."
   ::= {pr1645v2Lan2FGH24InPEntry 117440512}

pr1645v2Lan2FGH24InPIfInErrors OBJECT-TYPE
   SYNTAX      Counter64
   MAX-ACCESS  read-only
   STATUS      current
   DESCRIPTION
      "Path: ethernet2.performance.h24Performance.ifInErrors

       64 bit unsigned wrappable counter."
   ::= {pr1645v2Lan2FGH24InPEntry 134217728}

pr1645v2Lan2FGH24InPIfInUnkwn OBJECT-TYPE
   SYNTAX      Counter64
   MAX-ACCESS  read-only
   STATUS      current
   DESCRIPTION
      "Path: ethernet2.performance.h24Performance.ifInUnknownProtos

       64 bit unsigned wrappable counter."
   ::= {pr1645v2Lan2FGH24InPEntry 150994944}

pr1645v2Lan2FGH24InPInDropEx OBJECT-TYPE
   SYNTAX      Counter64
   MAX-ACCESS  read-only
   STATUS      current
   DESCRIPTION
      "Path: ethernet2.performance.h24Performance.ifInDropLevelExceeded

       64 bit unsigned wrappable counter."
   ::= {pr1645v2Lan2FGH24InPEntry 335544320}

pr1645v2Lan2FGH24InPInDropNoMac OBJECT-TYPE
   SYNTAX      Counter64
   MAX-ACCESS  read-only
   STATUS      current
   DESCRIPTION
      "Path: ethernet2.performance.h24Performance.fInDiscardsNoMacFit

       64 bit unsigned wrappable counter."
   ::= {pr1645v2Lan2FGH24InPEntry 301989888}

pr1645v2Lan2FGH24InPInDropNUCast OBJECT-TYPE
   SYNTAX      Counter64
   MAX-ACCESS  read-only
   STATUS      current
   DESCRIPTION
      "Path: ethernet2.performance.h24Performance.fInDiscardsNUCast

       64 bit unsigned wrappable counter."
   ::= {pr1645v2Lan2FGH24InPEntry 318767104}

pr1645v2Lan2FGH24InPInDropFilter OBJECT-TYPE
   SYNTAX      Counter64
   MAX-ACCESS  read-only
   STATUS      current
   DESCRIPTION
      "Path: ethernet2.performance.h24Performance.fInDiscardsFilter

       64 bit unsigned wrappable counter."
   ::= {pr1645v2Lan2FGH24InPEntry 385875968}

pr1645v2Lan2FGH24InPIfInBandwidth OBJECT-TYPE
   SYNTAX      Integer32
   MAX-ACCESS  read-only
   STATUS      current
   DESCRIPTION
      "Path: ethernet2.performance.h24Performance.ifInBandwidth

       unit name = bps
       formula = 8 * ; 8 /"
   ::= {pr1645v2Lan2FGH24InPEntry 268435456}

pr1645v2Lan2FGH24InPIfOutOctets OBJECT-TYPE
   SYNTAX      Counter64
   MAX-ACCESS  read-only
   STATUS      current
   DESCRIPTION
      "Path: ethernet2.performance.h24Performance.ifOutOctets

       64 bit unsigned wrappable counter."
   ::= {pr1645v2Lan2FGH24InPEntry 167772160}

pr1645v2Lan2FGH24InPIfOutUCPkts OBJECT-TYPE
   SYNTAX      Counter64
   MAX-ACCESS  read-only
   STATUS      current
   DESCRIPTION
      "Path: ethernet2.performance.h24Performance.ifOutUcastPkts

       64 bit unsigned wrappable counter."
   ::= {pr1645v2Lan2FGH24InPEntry 184549376}

pr1645v2Lan2FGH24InPIfOutNUCPkts OBJECT-TYPE
   SYNTAX      Counter64
   MAX-ACCESS  read-only
   STATUS      current
   DESCRIPTION
      "Path: ethernet2.performance.h24Performance.ifOutNUcastPkts

       64 bit unsigned wrappable counter."
   ::= {pr1645v2Lan2FGH24InPEntry 201326592}

pr1645v2Lan2FGH24InPIfOutBCPkts OBJECT-TYPE
   SYNTAX      Counter64
   MAX-ACCESS  read-only
   STATUS      current
   DESCRIPTION
      "Path: ethernet2.performance.h24Performance.ifOutBcastPkts

       64 bit unsigned wrappable counter."
   ::= {pr1645v2Lan2FGH24InPEntry 452984832}

pr1645v2Lan2FGH24InPIfOutMCPkts OBJECT-TYPE
   SYNTAX      Counter64
   MAX-ACCESS  read-only
   STATUS      current
   DESCRIPTION
      "Path: ethernet2.performance.h24Performance.ifOutMcastPkts

       64 bit unsigned wrappable counter."
   ::= {pr1645v2Lan2FGH24InPEntry 469762048}

pr1645v2Lan2FGH24InPIfOutDiscards OBJECT-TYPE
   SYNTAX      Counter64
   MAX-ACCESS  read-only
   STATUS      current
   DESCRIPTION
      "Path: ethernet2.performance.h24Performance.ifOutDiscards

       64 bit unsigned wrappable counter."
   ::= {pr1645v2Lan2FGH24InPEntry 218103808}

pr1645v2Lan2FGH24InPIfOutErrors OBJECT-TYPE
   SYNTAX      Counter64
   MAX-ACCESS  read-only
   STATUS      current
   DESCRIPTION
      "Path: ethernet2.performance.h24Performance.ifOutErrors

       64 bit unsigned wrappable counter."
   ::= {pr1645v2Lan2FGH24InPEntry 234881024}

pr1645v2Lan2FGH24InPOutDropEx OBJECT-TYPE
   SYNTAX      Counter64
   MAX-ACCESS  read-only
   STATUS      current
   DESCRIPTION
      "Path: ethernet2.performance.h24Performance.ifOutDropLevelExceeded

       64 bit unsigned wrappable counter."
   ::= {pr1645v2Lan2FGH24InPEntry 352321536}

pr1645v2Lan2FGH24InPOutDropNoArp OBJECT-TYPE
   SYNTAX      Counter64
   MAX-ACCESS  read-only
   STATUS      current
   DESCRIPTION
      "Path: ethernet2.performance.h24Performance.ifOutDiscardsNoArp

       64 bit unsigned wrappable counter."
   ::= {pr1645v2Lan2FGH24InPEntry 369098752}

pr1645v2Lan2FGH24InPOutDropFilter OBJECT-TYPE
   SYNTAX      Counter64
   MAX-ACCESS  read-only
   STATUS      current
   DESCRIPTION
      "Path: ethernet2.performance.h24Performance.ifOutDiscardsFilter

       64 bit unsigned wrappable counter."
   ::= {pr1645v2Lan2FGH24InPEntry 402653184}

pr1645v2Lan2FGH24InPIfOutBandwidth OBJECT-TYPE
   SYNTAX      Integer32
   MAX-ACCESS  read-only
   STATUS      current
   DESCRIPTION
      "Path: ethernet2.performance.h24Performance.ifOutBandwidth

       unit name = bps
       formula = 8 * ; 8 /"
   ::= {pr1645v2Lan2FGH24InPEntry 285212672}

pr1645v2Lan2FGH24InPIfErrSec OBJECT-TYPE
   SYNTAX      Counter32
   MAX-ACCESS  read-only
   STATUS      current
   DESCRIPTION
      "Path: ethernet2.performance.h24Performance.ifErrSec

       32 bit unsigned wrappable counter."
   ::= {pr1645v2Lan2FGH24InPEntry 251658240}


pr1645v2Lan2FGD7InP OBJECT IDENTIFIER ::= {pr1645v2Lan2FG 309}

pr1645v2Lan2FGD7InPSSCTable OBJECT-TYPE
   SYNTAX      SEQUENCE OF Pr1645v2Lan2FGD7InPEntry
   MAX-ACCESS  not-accessible
   STATUS      current
   DESCRIPTION
      "d7IfInPerformance"
   ::= {pr1645v2Lan2FGD7InP 1}

pr1645v2Lan2FGD7InPEntry OBJECT-TYPE
   SYNTAX      Pr1645v2Lan2FGD7InPEntry
   MAX-ACCESS  not-accessible
   STATUS      current
   DESCRIPTION
      ""
   INDEX      { pr1645v2Lan2FGD7InPTableIx }
   ::= {pr1645v2Lan2FGD7InPSSCTable 1}

Pr1645v2Lan2FGD7InPEntry ::=
   SEQUENCE
      {
      pr1645v2Lan2FGD7InPTableIx
         TableIndex,
      pr1645v2Lan2FGD7InPSysUpTime
         TimeTicks,
      pr1645v2Lan2FGD7InPIfUpTime
         TimeTicks,
      pr1645v2Lan2FGD7InPIfStatChanges
         Counter32,
      pr1645v2Lan2FGD7InPIfInOctets
         Counter64,
      pr1645v2Lan2FGD7InPIfInUCPkts
         Counter64,
      pr1645v2Lan2FGD7InPIfInNUCPkts
         Counter64,
      pr1645v2Lan2FGD7InPIfInBCPkts
         Counter64,
      pr1645v2Lan2FGD7InPIfInMCPkts
         Counter64,
      pr1645v2Lan2FGD7InPIfInDiscards
         Counter64,
      pr1645v2Lan2FGD7InPIfInErrors
         Counter64,
      pr1645v2Lan2FGD7InPIfInUnkwn
         Counter64,
      pr1645v2Lan2FGD7InPInDropEx
         Counter64,
      pr1645v2Lan2FGD7InPInDropNoMac
         Counter64,
      pr1645v2Lan2FGD7InPInDropNUCast
         Counter64,
      pr1645v2Lan2FGD7InPInDropFilter
         Counter64,
      pr1645v2Lan2FGD7InPIfInBandwidth
         Integer32,
      pr1645v2Lan2FGD7InPIfOutOctets
         Counter64,
      pr1645v2Lan2FGD7InPIfOutUCPkts
         Counter64,
      pr1645v2Lan2FGD7InPIfOutNUCPkts
         Counter64,
      pr1645v2Lan2FGD7InPIfOutBCPkts
         Counter64,
      pr1645v2Lan2FGD7InPIfOutMCPkts
         Counter64,
      pr1645v2Lan2FGD7InPIfOutDiscards
         Counter64,
      pr1645v2Lan2FGD7InPIfOutErrors
         Counter64,
      pr1645v2Lan2FGD7InPOutDropEx
         Counter64,
      pr1645v2Lan2FGD7InPOutDropNoArp
         Counter64,
      pr1645v2Lan2FGD7InPOutDropFilter
         Counter64,
      pr1645v2Lan2FGD7InPIfOutBandwidth
         Integer32,
      pr1645v2Lan2FGD7InPIfErrSec
         Counter32
      }

pr1645v2Lan2FGD7InPTableIx OBJECT-TYPE
   SYNTAX      TableIndex
   MAX-ACCESS  not-accessible
   STATUS      current
   DESCRIPTION
      ""
   ::= {pr1645v2Lan2FGD7InPEntry 11}

pr1645v2Lan2FGD7InPSysUpTime OBJECT-TYPE
   SYNTAX      TimeTicks
   MAX-ACCESS  read-only
   STATUS      current
   DESCRIPTION
      "Path: ethernet2.performance.d7Performance.sysUpTime

       Time in centi-second."
   ::= {pr1645v2Lan2FGD7InPEntry 16777216}

pr1645v2Lan2FGD7InPIfUpTime OBJECT-TYPE
   SYNTAX      TimeTicks
   MAX-ACCESS  read-only
   STATUS      current
   DESCRIPTION
      "Path: ethernet2.performance.d7Performance.ifUpTime

       Time in centi-second."
   ::= {pr1645v2Lan2FGD7InPEntry 33554432}

pr1645v2Lan2FGD7InPIfStatChanges OBJECT-TYPE
   SYNTAX      Counter32
   MAX-ACCESS  read-only
   STATUS      current
   DESCRIPTION
      "Path: ethernet2.performance.d7Performance.ifStatusChanges

       32 bit unsigned wrappable counter."
   ::= {pr1645v2Lan2FGD7InPEntry 50331648}

pr1645v2Lan2FGD7InPIfInOctets OBJECT-TYPE
   SYNTAX      Counter64
   MAX-ACCESS  read-only
   STATUS      current
   DESCRIPTION
      "Path: ethernet2.performance.d7Performance.ifInOctets

       64 bit unsigned wrappable counter."
   ::= {pr1645v2Lan2FGD7InPEntry 67108864}

pr1645v2Lan2FGD7InPIfInUCPkts OBJECT-TYPE
   SYNTAX      Counter64
   MAX-ACCESS  read-only
   STATUS      current
   DESCRIPTION
      "Path: ethernet2.performance.d7Performance.ifInUcastPkts

       64 bit unsigned wrappable counter."
   ::= {pr1645v2Lan2FGD7InPEntry 83886080}

pr1645v2Lan2FGD7InPIfInNUCPkts OBJECT-TYPE
   SYNTAX      Counter64
   MAX-ACCESS  read-only
   STATUS      current
   DESCRIPTION
      "Path: ethernet2.performance.d7Performance.ifInNUcastPkts

       64 bit unsigned wrappable counter."
   ::= {pr1645v2Lan2FGD7InPEntry 100663296}

pr1645v2Lan2FGD7InPIfInBCPkts OBJECT-TYPE
   SYNTAX      Counter64
   MAX-ACCESS  read-only
   STATUS      current
   DESCRIPTION
      "Path: ethernet2.performance.d7Performance.ifInBcastPkts

       64 bit unsigned wrappable counter."
   ::= {pr1645v2Lan2FGD7InPEntry 419430400}

pr1645v2Lan2FGD7InPIfInMCPkts OBJECT-TYPE
   SYNTAX      Counter64
   MAX-ACCESS  read-only
   STATUS      current
   DESCRIPTION
      "Path: ethernet2.performance.d7Performance.ifInMcastPkts

       64 bit unsigned wrappable counter."
   ::= {pr1645v2Lan2FGD7InPEntry 436207616}

pr1645v2Lan2FGD7InPIfInDiscards OBJECT-TYPE
   SYNTAX      Counter64
   MAX-ACCESS  read-only
   STATUS      current
   DESCRIPTION
      "Path: ethernet2.performance.d7Performance.ifInDiscards

       64 bit unsigned wrappable counter."
   ::= {pr1645v2Lan2FGD7InPEntry 117440512}

pr1645v2Lan2FGD7InPIfInErrors OBJECT-TYPE
   SYNTAX      Counter64
   MAX-ACCESS  read-only
   STATUS      current
   DESCRIPTION
      "Path: ethernet2.performance.d7Performance.ifInErrors

       64 bit unsigned wrappable counter."
   ::= {pr1645v2Lan2FGD7InPEntry 134217728}

pr1645v2Lan2FGD7InPIfInUnkwn OBJECT-TYPE
   SYNTAX      Counter64
   MAX-ACCESS  read-only
   STATUS      current
   DESCRIPTION
      "Path: ethernet2.performance.d7Performance.ifInUnknownProtos

       64 bit unsigned wrappable counter."
   ::= {pr1645v2Lan2FGD7InPEntry 150994944}

pr1645v2Lan2FGD7InPInDropEx OBJECT-TYPE
   SYNTAX      Counter64
   MAX-ACCESS  read-only
   STATUS      current
   DESCRIPTION
      "Path: ethernet2.performance.d7Performance.ifInDropLevelExceeded

       64 bit unsigned wrappable counter."
   ::= {pr1645v2Lan2FGD7InPEntry 335544320}

pr1645v2Lan2FGD7InPInDropNoMac OBJECT-TYPE
   SYNTAX      Counter64
   MAX-ACCESS  read-only
   STATUS      current
   DESCRIPTION
      "Path: ethernet2.performance.d7Performance.fInDiscardsNoMacFit

       64 bit unsigned wrappable counter."
   ::= {pr1645v2Lan2FGD7InPEntry 301989888}

pr1645v2Lan2FGD7InPInDropNUCast OBJECT-TYPE
   SYNTAX      Counter64
   MAX-ACCESS  read-only
   STATUS      current
   DESCRIPTION
      "Path: ethernet2.performance.d7Performance.fInDiscardsNUCast

       64 bit unsigned wrappable counter."
   ::= {pr1645v2Lan2FGD7InPEntry 318767104}

pr1645v2Lan2FGD7InPInDropFilter OBJECT-TYPE
   SYNTAX      Counter64
   MAX-ACCESS  read-only
   STATUS      current
   DESCRIPTION
      "Path: ethernet2.performance.d7Performance.fInDiscardsFilter

       64 bit unsigned wrappable counter."
   ::= {pr1645v2Lan2FGD7InPEntry 385875968}

pr1645v2Lan2FGD7InPIfInBandwidth OBJECT-TYPE
   SYNTAX      Integer32
   MAX-ACCESS  read-only
   STATUS      current
   DESCRIPTION
      "Path: ethernet2.performance.d7Performance.ifInBandwidth

       unit name = bps
       formula = 8 * ; 8 /"
   ::= {pr1645v2Lan2FGD7InPEntry 268435456}

pr1645v2Lan2FGD7InPIfOutOctets OBJECT-TYPE
   SYNTAX      Counter64
   MAX-ACCESS  read-only
   STATUS      current
   DESCRIPTION
      "Path: ethernet2.performance.d7Performance.ifOutOctets

       64 bit unsigned wrappable counter."
   ::= {pr1645v2Lan2FGD7InPEntry 167772160}

pr1645v2Lan2FGD7InPIfOutUCPkts OBJECT-TYPE
   SYNTAX      Counter64
   MAX-ACCESS  read-only
   STATUS      current
   DESCRIPTION
      "Path: ethernet2.performance.d7Performance.ifOutUcastPkts

       64 bit unsigned wrappable counter."
   ::= {pr1645v2Lan2FGD7InPEntry 184549376}

pr1645v2Lan2FGD7InPIfOutNUCPkts OBJECT-TYPE
   SYNTAX      Counter64
   MAX-ACCESS  read-only
   STATUS      current
   DESCRIPTION
      "Path: ethernet2.performance.d7Performance.ifOutNUcastPkts

       64 bit unsigned wrappable counter."
   ::= {pr1645v2Lan2FGD7InPEntry 201326592}

pr1645v2Lan2FGD7InPIfOutBCPkts OBJECT-TYPE
   SYNTAX      Counter64
   MAX-ACCESS  read-only
   STATUS      current
   DESCRIPTION
      "Path: ethernet2.performance.d7Performance.ifOutBcastPkts

       64 bit unsigned wrappable counter."
   ::= {pr1645v2Lan2FGD7InPEntry 452984832}

pr1645v2Lan2FGD7InPIfOutMCPkts OBJECT-TYPE
   SYNTAX      Counter64
   MAX-ACCESS  read-only
   STATUS      current
   DESCRIPTION
      "Path: ethernet2.performance.d7Performance.ifOutMcastPkts

       64 bit unsigned wrappable counter."
   ::= {pr1645v2Lan2FGD7InPEntry 469762048}

pr1645v2Lan2FGD7InPIfOutDiscards OBJECT-TYPE
   SYNTAX      Counter64
   MAX-ACCESS  read-only
   STATUS      current
   DESCRIPTION
      "Path: ethernet2.performance.d7Performance.ifOutDiscards

       64 bit unsigned wrappable counter."
   ::= {pr1645v2Lan2FGD7InPEntry 218103808}

pr1645v2Lan2FGD7InPIfOutErrors OBJECT-TYPE
   SYNTAX      Counter64
   MAX-ACCESS  read-only
   STATUS      current
   DESCRIPTION
      "Path: ethernet2.performance.d7Performance.ifOutErrors

       64 bit unsigned wrappable counter."
   ::= {pr1645v2Lan2FGD7InPEntry 234881024}

pr1645v2Lan2FGD7InPOutDropEx OBJECT-TYPE
   SYNTAX      Counter64
   MAX-ACCESS  read-only
   STATUS      current
   DESCRIPTION
      "Path: ethernet2.performance.d7Performance.ifOutDropLevelExceeded

       64 bit unsigned wrappable counter."
   ::= {pr1645v2Lan2FGD7InPEntry 352321536}

pr1645v2Lan2FGD7InPOutDropNoArp OBJECT-TYPE
   SYNTAX      Counter64
   MAX-ACCESS  read-only
   STATUS      current
   DESCRIPTION
      "Path: ethernet2.performance.d7Performance.ifOutDiscardsNoArp

       64 bit unsigned wrappable counter."
   ::= {pr1645v2Lan2FGD7InPEntry 369098752}

pr1645v2Lan2FGD7InPOutDropFilter OBJECT-TYPE
   SYNTAX      Counter64
   MAX-ACCESS  read-only
   STATUS      current
   DESCRIPTION
      "Path: ethernet2.performance.d7Performance.ifOutDiscardsFilter

       64 bit unsigned wrappable counter."
   ::= {pr1645v2Lan2FGD7InPEntry 402653184}

pr1645v2Lan2FGD7InPIfOutBandwidth OBJECT-TYPE
   SYNTAX      Integer32
   MAX-ACCESS  read-only
   STATUS      current
   DESCRIPTION
      "Path: ethernet2.performance.d7Performance.ifOutBandwidth

       unit name = bps
       formula = 8 * ; 8 /"
   ::= {pr1645v2Lan2FGD7InPEntry 285212672}

pr1645v2Lan2FGD7InPIfErrSec OBJECT-TYPE
   SYNTAX      Counter32
   MAX-ACCESS  read-only
   STATUS      current
   DESCRIPTION
      "Path: ethernet2.performance.d7Performance.ifErrSec

       32 bit unsigned wrappable counter."
   ::= {pr1645v2Lan2FGD7InPEntry 251658240}


pr1645v2Lan2FGOam OBJECT IDENTIFIER ::= {pr1645v2Lan2FG 910}

pr1645v2Lan2FGOamSSC OBJECT IDENTIFIER ::= {pr1645v2Lan2FGOam 1}

pr1645v2Lan2FGOamEntry OBJECT IDENTIFIER ::= {pr1645v2Lan2FGOamSSC 1}

pr1645v2Lan2FGOamInformationTx OBJECT-TYPE
   SYNTAX      Counter32
   MAX-ACCESS  read-only
   STATUS      current
   DESCRIPTION
      "Path: ethernet2.performance.oam.informationTx

       32 bit unsigned wrappable counter."
   ::= {pr1645v2Lan2FGOamEntry 16777216}

pr1645v2Lan2FGOamInformationRx OBJECT-TYPE
   SYNTAX      Counter32
   MAX-ACCESS  read-only
   STATUS      current
   DESCRIPTION
      "Path: ethernet2.performance.oam.informationRx

       32 bit unsigned wrappable counter."
   ::= {pr1645v2Lan2FGOamEntry 33554432}

pr1645v2Lan2FGOamUniqueEventNotifTx OBJECT-TYPE
   SYNTAX      Counter32
   MAX-ACCESS  read-only
   STATUS      current
   DESCRIPTION
      "Path: ethernet2.performance.oam.uniqueEventNotifTx

       32 bit unsigned wrappable counter."
   ::= {pr1645v2Lan2FGOamEntry 50331648}

pr1645v2Lan2FGOamUniqueEventNotifRx OBJECT-TYPE
   SYNTAX      Counter32
   MAX-ACCESS  read-only
   STATUS      current
   DESCRIPTION
      "Path: ethernet2.performance.oam.uniqueEventNotifRx

       32 bit unsigned wrappable counter."
   ::= {pr1645v2Lan2FGOamEntry 67108864}

pr1645v2Lan2FGOamLoopbackCtrlTx OBJECT-TYPE
   SYNTAX      Counter32
   MAX-ACCESS  read-only
   STATUS      current
   DESCRIPTION
      "Path: ethernet2.performance.oam.loopbackCtrlTx

       32 bit unsigned wrappable counter."
   ::= {pr1645v2Lan2FGOamEntry 117440512}

pr1645v2Lan2FGOamLoopbackCtrlRx OBJECT-TYPE
   SYNTAX      Counter32
   MAX-ACCESS  read-only
   STATUS      current
   DESCRIPTION
      "Path: ethernet2.performance.oam.loopbackCtrlRx

       32 bit unsigned wrappable counter."
   ::= {pr1645v2Lan2FGOamEntry 134217728}

pr1645v2Lan2FGOamVarReqTx OBJECT-TYPE
   SYNTAX      Counter32
   MAX-ACCESS  read-only
   STATUS      current
   DESCRIPTION
      "Path: ethernet2.performance.oam.varReqTx

       32 bit unsigned wrappable counter."
   ::= {pr1645v2Lan2FGOamEntry 150994944}

pr1645v2Lan2FGOamVarReqRx OBJECT-TYPE
   SYNTAX      Counter32
   MAX-ACCESS  read-only
   STATUS      current
   DESCRIPTION
      "Path: ethernet2.performance.oam.varReqRx

       32 bit unsigned wrappable counter."
   ::= {pr1645v2Lan2FGOamEntry 167772160}

pr1645v2Lan2FGOamVarRespTx OBJECT-TYPE
   SYNTAX      Counter32
   MAX-ACCESS  read-only
   STATUS      current
   DESCRIPTION
      "Path: ethernet2.performance.oam.varRespTx

       32 bit unsigned wrappable counter."
   ::= {pr1645v2Lan2FGOamEntry 184549376}

pr1645v2Lan2FGOamVarRespRx OBJECT-TYPE
   SYNTAX      Counter32
   MAX-ACCESS  read-only
   STATUS      current
   DESCRIPTION
      "Path: ethernet2.performance.oam.varRespRx

       32 bit unsigned wrappable counter."
   ::= {pr1645v2Lan2FGOamEntry 201326592}

pr1645v2Lan2FGOamOrgSpecificTx OBJECT-TYPE
   SYNTAX      Counter32
   MAX-ACCESS  read-only
   STATUS      current
   DESCRIPTION
      "Path: ethernet2.performance.oam.orgSpecificTx

       32 bit unsigned wrappable counter."
   ::= {pr1645v2Lan2FGOamEntry 218103808}

pr1645v2Lan2FGOamOrgSpecificRx OBJECT-TYPE
   SYNTAX      Counter32
   MAX-ACCESS  read-only
   STATUS      current
   DESCRIPTION
      "Path: ethernet2.performance.oam.orgSpecificRx

       32 bit unsigned wrappable counter."
   ::= {pr1645v2Lan2FGOamEntry 234881024}

pr1645v2Lan2FGOamUnsupportedCodesTx OBJECT-TYPE
   SYNTAX      Counter32
   MAX-ACCESS  read-only
   STATUS      current
   DESCRIPTION
      "Path: ethernet2.performance.oam.unsupportedCodesTx

       32 bit unsigned wrappable counter."
   ::= {pr1645v2Lan2FGOamEntry 251658240}

pr1645v2Lan2FGOamUnsupportedCodesRx OBJECT-TYPE
   SYNTAX      Counter32
   MAX-ACCESS  read-only
   STATUS      current
   DESCRIPTION
      "Path: ethernet2.performance.oam.unsupportedCodesRx

       32 bit unsigned wrappable counter."
   ::= {pr1645v2Lan2FGOamEntry 268435456}

pr1645v2Lan2FGOamPduDiscardRx OBJECT-TYPE
   SYNTAX      Counter32
   MAX-ACCESS  read-only
   STATUS      current
   DESCRIPTION
      "Path: ethernet2.performance.oam.pduDiscardRx

       32 bit unsigned wrappable counter."
   ::= {pr1645v2Lan2FGOamEntry 1694498816}

pr1645v2Lan2FGOamDataDiscardTx OBJECT-TYPE
   SYNTAX      Counter32
   MAX-ACCESS  read-only
   STATUS      current
   DESCRIPTION
      "Path: ethernet2.performance.oam.dataDiscardTx

       32 bit unsigned wrappable counter."
   ::= {pr1645v2Lan2FGOamEntry 1711276032}

pr1645v2Lan2FGOamDataDiscardRx OBJECT-TYPE
   SYNTAX      Counter32
   MAX-ACCESS  read-only
   STATUS      current
   DESCRIPTION
      "Path: ethernet2.performance.oam.dataDiscardRx

       32 bit unsigned wrappable counter."
   ::= {pr1645v2Lan2FGOamEntry 1728053248}


pr1645v2Lan2FGVlan OBJECT IDENTIFIER ::= {pr1645v2Lan2FG 310}

pr1645v2Lan2FGVlanSSCTable OBJECT-TYPE
   SYNTAX      SEQUENCE OF Pr1645v2Lan2FGVlanEntry
   MAX-ACCESS  not-accessible
   STATUS      current
   DESCRIPTION
      ""
   ::= {pr1645v2Lan2FGVlan 1}

pr1645v2Lan2FGVlanEntry OBJECT-TYPE
   SYNTAX      Pr1645v2Lan2FGVlanEntry
   MAX-ACCESS  not-accessible
   STATUS      current
   DESCRIPTION
      ""
   INDEX      { pr1645v2Lan2FGVlanTableIx }
   ::= {pr1645v2Lan2FGVlanSSCTable 1}

Pr1645v2Lan2FGVlanEntry ::=
   SEQUENCE
      {
      pr1645v2Lan2FGVlanTableIx
         TableIndex,
      pr1645v2Lan2FGVlanName
         DisplayString,
      pr1645v2Lan2FGVlanMCInOctets
         Counter64,
      pr1645v2Lan2FGVlanMCInUcast
         Counter64,
      pr1645v2Lan2FGVlanMCInNUcastPkts
         Counter64,
      pr1645v2Lan2FGVlanMCInBcastPkts
         Counter64,
      pr1645v2Lan2FGVlanMCInMcastPkts
         Counter64,
      pr1645v2Lan2FGVlanMCInDiscards
         Counter64,
      pr1645v2Lan2FGVlanMCInErrors
         Counter64,
      pr1645v2Lan2FGVlanMCInUnknownProtos
         Counter64,
      pr1645v2Lan2FGVlanMCInDropEx
         Counter64,
      pr1645v2Lan2FGVlanMCInDropNoMac
         Counter64,
      pr1645v2Lan2FGVlanMCInDropNUCast
         Counter64,
      pr1645v2Lan2FGVlanMCInDropFilter
         Counter64,
      pr1645v2Lan2FGVlanMCInBandwidth15sec
         Integer32,
      pr1645v2Lan2FGVlanMCInBandwidth30sec
         Integer32,
      pr1645v2Lan2FGVlanMCInBandwidth1min
         Integer32,
      pr1645v2Lan2FGVlanMCInBandwidth2min
         Integer32,
      pr1645v2Lan2FGVlanMCInBandwidth5min
         Integer32,
      pr1645v2Lan2FGVlanMCOutOctets
         Counter64,
      pr1645v2Lan2FGVlanMCOutUcastPkts
         Counter64,
      pr1645v2Lan2FGVlanMCOutNUcastPkts
         Counter64,
      pr1645v2Lan2FGVlanMCOutBcastPkts
         Counter64,
      pr1645v2Lan2FGVlanMCOutMcastPkts
         Counter64,
      pr1645v2Lan2FGVlanMCOutDiscards
         Counter64,
      pr1645v2Lan2FGVlanMCOutErrors
         Counter64,
      pr1645v2Lan2FGVlanMCOutQLen
         Counter32,
      pr1645v2Lan2FGVlanMCOutDropEx
         Counter64,
      pr1645v2Lan2FGVlanMCOutDropNoArp
         Counter64,
      pr1645v2Lan2FGVlanMCOutDropFilter
         Counter64,
      pr1645v2Lan2FGVlanMCOutBandwidth15sec
         Integer32,
      pr1645v2Lan2FGVlanMCOutBandwidth30sec
         Integer32,
      pr1645v2Lan2FGVlanMCOutBandwidth1min
         Integer32,
      pr1645v2Lan2FGVlanMCOutBandwidth2min
         Integer32,
      pr1645v2Lan2FGVlanMCOutBandwidth5min
         Integer32,
      pr1645v2Lan2FGVlanVlanVid
         Integer32,
      pr1645v2Lan2FGVlanPppLinkMonitoringRequestsSent
         Gauge32,
      pr1645v2Lan2FGVlanPppLinkMonitoringRepliesRcvd
         Gauge32,
      pr1645v2Lan2FGVlanPppLinkMonitoringRequestsRcvd
         Gauge32,
      pr1645v2Lan2FGVlanPppLinkMonitoringRepliesSent
         Gauge32
      }

pr1645v2Lan2FGVlanTableIx OBJECT-TYPE
   SYNTAX      TableIndex
   MAX-ACCESS  not-accessible
   STATUS      current
   DESCRIPTION
      ""
   ::= {pr1645v2Lan2FGVlanEntry 11}

pr1645v2Lan2FGVlanName OBJECT-TYPE
   SYNTAX      DisplayString
   MAX-ACCESS  read-only
   STATUS      current
   DESCRIPTION
      "Path: ethernet2.performance.vlan.name"
   ::= {pr1645v2Lan2FGVlanEntry 16777216}

pr1645v2Lan2FGVlanMCInOctets OBJECT-TYPE
   SYNTAX      Counter64
   MAX-ACCESS  read-only
   STATUS      current
   DESCRIPTION
      "Path: ethernet2.performance.vlan.mibCounters.ifInOctets

       64 bit unsigned wrappable counter."
   ::= {pr1645v2Lan2FGVlanEntry 40697856}

pr1645v2Lan2FGVlanMCInUcast OBJECT-TYPE
   SYNTAX      Counter64
   MAX-ACCESS  read-only
   STATUS      current
   DESCRIPTION
      "Path: ethernet2.performance.vlan.mibCounters.ifInUcastPkts

       64 bit unsigned wrappable counter."
   ::= {pr1645v2Lan2FGVlanEntry 40763392}

pr1645v2Lan2FGVlanMCInNUcastPkts OBJECT-TYPE
   SYNTAX      Counter64
   MAX-ACCESS  read-only
   STATUS      current
   DESCRIPTION
      "Path: ethernet2.performance.vlan.mibCounters.ifInNUcastPkts

       64 bit unsigned wrappable counter."
   ::= {pr1645v2Lan2FGVlanEntry 40828928}

pr1645v2Lan2FGVlanMCInBcastPkts OBJECT-TYPE
   SYNTAX      Counter64
   MAX-ACCESS  read-only
   STATUS      current
   DESCRIPTION
      "Path: ethernet2.performance.vlan.mibCounters.ifInBcastPkts

       64 bit unsigned wrappable counter."
   ::= {pr1645v2Lan2FGVlanEntry 47382528}

pr1645v2Lan2FGVlanMCInMcastPkts OBJECT-TYPE
   SYNTAX      Counter64
   MAX-ACCESS  read-only
   STATUS      current
   DESCRIPTION
      "Path: ethernet2.performance.vlan.mibCounters.ifInMcastPkts

       64 bit unsigned wrappable counter."
   ::= {pr1645v2Lan2FGVlanEntry 48037888}

pr1645v2Lan2FGVlanMCInDiscards OBJECT-TYPE
   SYNTAX      Counter64
   MAX-ACCESS  read-only
   STATUS      current
   DESCRIPTION
      "Path: ethernet2.performance.vlan.mibCounters.ifInDiscards

       64 bit unsigned wrappable counter."
   ::= {pr1645v2Lan2FGVlanEntry 40894464}

pr1645v2Lan2FGVlanMCInErrors OBJECT-TYPE
   SYNTAX      Counter64
   MAX-ACCESS  read-only
   STATUS      current
   DESCRIPTION
      "Path: ethernet2.performance.vlan.mibCounters.ifInErrors

       64 bit unsigned wrappable counter."
   ::= {pr1645v2Lan2FGVlanEntry 40960000}

pr1645v2Lan2FGVlanMCInUnknownProtos OBJECT-TYPE
   SYNTAX      Counter64
   MAX-ACCESS  read-only
   STATUS      current
   DESCRIPTION
      "Path: ethernet2.performance.vlan.mibCounters.ifInUnknownProtos

       64 bit unsigned wrappable counter."
   ::= {pr1645v2Lan2FGVlanEntry 41025536}

pr1645v2Lan2FGVlanMCInDropEx OBJECT-TYPE
   SYNTAX      Counter64
   MAX-ACCESS  read-only
   STATUS      current
   DESCRIPTION
      "Path: ethernet2.performance.vlan.mibCounters.ifInDropLevelExceeded

       64 bit unsigned wrappable counter."
   ::= {pr1645v2Lan2FGVlanEntry 42074112}

pr1645v2Lan2FGVlanMCInDropNoMac OBJECT-TYPE
   SYNTAX      Counter64
   MAX-ACCESS  read-only
   STATUS      current
   DESCRIPTION
      "Path: ethernet2.performance.vlan.mibCounters.ifInDiscardsNoMacFit

       64 bit unsigned wrappable counter."
   ::= {pr1645v2Lan2FGVlanEntry 42270720}

pr1645v2Lan2FGVlanMCInDropNUCast OBJECT-TYPE
   SYNTAX      Counter64
   MAX-ACCESS  read-only
   STATUS      current
   DESCRIPTION
      "Path: ethernet2.performance.vlan.mibCounters.ifInDiscardsNUCast

       64 bit unsigned wrappable counter."
   ::= {pr1645v2Lan2FGVlanEntry 42467328}

pr1645v2Lan2FGVlanMCInDropFilter OBJECT-TYPE
   SYNTAX      Counter64
   MAX-ACCESS  read-only
   STATUS      current
   DESCRIPTION
      "Path: ethernet2.performance.vlan.mibCounters.ifInDiscardsFilter

       64 bit unsigned wrappable counter."
   ::= {pr1645v2Lan2FGVlanEntry 42532864}

pr1645v2Lan2FGVlanMCInBandwidth15sec OBJECT-TYPE
   SYNTAX      Integer32
   MAX-ACCESS  read-only
   STATUS      current
   DESCRIPTION
      "Path: ethernet2.performance.vlan.mibCounters.ifInBandwidth.15sec

       unit name = bps
       formula = 8 * ; 8 /"
   ::= {pr1645v2Lan2FGVlanEntry 45417728}

pr1645v2Lan2FGVlanMCInBandwidth30sec OBJECT-TYPE
   SYNTAX      Integer32
   MAX-ACCESS  read-only
   STATUS      current
   DESCRIPTION
      "Path: ethernet2.performance.vlan.mibCounters.ifInBandwidth.30sec

       unit name = bps
       formula = 8 * ; 8 /"
   ::= {pr1645v2Lan2FGVlanEntry 45419008}

pr1645v2Lan2FGVlanMCInBandwidth1min OBJECT-TYPE
   SYNTAX      Integer32
   MAX-ACCESS  read-only
   STATUS      current
   DESCRIPTION
      "Path: ethernet2.performance.vlan.mibCounters.ifInBandwidth.1min

       unit name = bps
       formula = 8 * ; 8 /"
   ::= {pr1645v2Lan2FGVlanEntry 45421568}

pr1645v2Lan2FGVlanMCInBandwidth2min OBJECT-TYPE
   SYNTAX      Integer32
   MAX-ACCESS  read-only
   STATUS      current
   DESCRIPTION
      "Path: ethernet2.performance.vlan.mibCounters.ifInBandwidth.2min

       unit name = bps
       formula = 8 * ; 8 /"
   ::= {pr1645v2Lan2FGVlanEntry 45426688}

pr1645v2Lan2FGVlanMCInBandwidth5min OBJECT-TYPE
   SYNTAX      Integer32
   MAX-ACCESS  read-only
   STATUS      current
   DESCRIPTION
      "Path: ethernet2.performance.vlan.mibCounters.ifInBandwidth.5min

       unit name = bps
       formula = 8 * ; 8 /"
   ::= {pr1645v2Lan2FGVlanEntry 45442048}

pr1645v2Lan2FGVlanMCOutOctets OBJECT-TYPE
   SYNTAX      Counter64
   MAX-ACCESS  read-only
   STATUS      current
   DESCRIPTION
      "Path: ethernet2.performance.vlan.mibCounters.ifOutOctets

       64 bit unsigned wrappable counter."
   ::= {pr1645v2Lan2FGVlanEntry 41091072}

pr1645v2Lan2FGVlanMCOutUcastPkts OBJECT-TYPE
   SYNTAX      Counter64
   MAX-ACCESS  read-only
   STATUS      current
   DESCRIPTION
      "Path: ethernet2.performance.vlan.mibCounters.ifOutUcastPkts

       64 bit unsigned wrappable counter."
   ::= {pr1645v2Lan2FGVlanEntry 41156608}

pr1645v2Lan2FGVlanMCOutNUcastPkts OBJECT-TYPE
   SYNTAX      Counter64
   MAX-ACCESS  read-only
   STATUS      current
   DESCRIPTION
      "Path: ethernet2.performance.vlan.mibCounters.ifOutNUcastPkts

       64 bit unsigned wrappable counter."
   ::= {pr1645v2Lan2FGVlanEntry 41222144}

pr1645v2Lan2FGVlanMCOutBcastPkts OBJECT-TYPE
   SYNTAX      Counter64
   MAX-ACCESS  read-only
   STATUS      current
   DESCRIPTION
      "Path: ethernet2.performance.vlan.mibCounters.ifOutBcastPkts

       64 bit unsigned wrappable counter."
   ::= {pr1645v2Lan2FGVlanEntry 47775744}

pr1645v2Lan2FGVlanMCOutMcastPkts OBJECT-TYPE
   SYNTAX      Counter64
   MAX-ACCESS  read-only
   STATUS      current
   DESCRIPTION
      "Path: ethernet2.performance.vlan.mibCounters.ifOutMcastPkts

       64 bit unsigned wrappable counter."
   ::= {pr1645v2Lan2FGVlanEntry 48431104}

pr1645v2Lan2FGVlanMCOutDiscards OBJECT-TYPE
   SYNTAX      Counter64
   MAX-ACCESS  read-only
   STATUS      current
   DESCRIPTION
      "Path: ethernet2.performance.vlan.mibCounters.ifOutDiscards

       64 bit unsigned wrappable counter."
   ::= {pr1645v2Lan2FGVlanEntry 41287680}

pr1645v2Lan2FGVlanMCOutErrors OBJECT-TYPE
   SYNTAX      Counter64
   MAX-ACCESS  read-only
   STATUS      current
   DESCRIPTION
      "Path: ethernet2.performance.vlan.mibCounters.ifOutErrors

       64 bit unsigned wrappable counter."
   ::= {pr1645v2Lan2FGVlanEntry 41353216}

pr1645v2Lan2FGVlanMCOutQLen OBJECT-TYPE
   SYNTAX      Counter32
   MAX-ACCESS  read-only
   STATUS      current
   DESCRIPTION
      "Path: ethernet2.performance.vlan.mibCounters.ifOutQLen

       32 bit unsigned wrappable counter."
   ::= {pr1645v2Lan2FGVlanEntry 41418752}

pr1645v2Lan2FGVlanMCOutDropEx OBJECT-TYPE
   SYNTAX      Counter64
   MAX-ACCESS  read-only
   STATUS      current
   DESCRIPTION
      "Path: ethernet2.performance.vlan.mibCounters.ifOutDropLevelExceeded

       64 bit unsigned wrappable counter."
   ::= {pr1645v2Lan2FGVlanEntry 41484288}

pr1645v2Lan2FGVlanMCOutDropNoArp OBJECT-TYPE
   SYNTAX      Counter64
   MAX-ACCESS  read-only
   STATUS      current
   DESCRIPTION
      "Path: ethernet2.performance.vlan.mibCounters.ifOutDiscardsNoArp

       64 bit unsigned wrappable counter."
   ::= {pr1645v2Lan2FGVlanEntry 42336256}

pr1645v2Lan2FGVlanMCOutDropFilter OBJECT-TYPE
   SYNTAX      Counter64
   MAX-ACCESS  read-only
   STATUS      current
   DESCRIPTION
      "Path: ethernet2.performance.vlan.mibCounters.ifOutDiscardsFilter

       64 bit unsigned wrappable counter."
   ::= {pr1645v2Lan2FGVlanEntry 42598400}

pr1645v2Lan2FGVlanMCOutBandwidth15sec OBJECT-TYPE
   SYNTAX      Integer32
   MAX-ACCESS  read-only
   STATUS      current
   DESCRIPTION
      "Path: ethernet2.performance.vlan.mibCounters.ifOutBandwidth.15sec

       unit name = bps
       formula = 8 * ; 8 /"
   ::= {pr1645v2Lan2FGVlanEntry 45483264}

pr1645v2Lan2FGVlanMCOutBandwidth30sec OBJECT-TYPE
   SYNTAX      Integer32
   MAX-ACCESS  read-only
   STATUS      current
   DESCRIPTION
      "Path: ethernet2.performance.vlan.mibCounters.ifOutBandwidth.30sec

       unit name = bps
       formula = 8 * ; 8 /"
   ::= {pr1645v2Lan2FGVlanEntry 45484544}

pr1645v2Lan2FGVlanMCOutBandwidth1min OBJECT-TYPE
   SYNTAX      Integer32
   MAX-ACCESS  read-only
   STATUS      current
   DESCRIPTION
      "Path: ethernet2.performance.vlan.mibCounters.ifOutBandwidth.1min

       unit name = bps
       formula = 8 * ; 8 /"
   ::= {pr1645v2Lan2FGVlanEntry 45487104}

pr1645v2Lan2FGVlanMCOutBandwidth2min OBJECT-TYPE
   SYNTAX      Integer32
   MAX-ACCESS  read-only
   STATUS      current
   DESCRIPTION
      "Path: ethernet2.performance.vlan.mibCounters.ifOutBandwidth.2min

       unit name = bps
       formula = 8 * ; 8 /"
   ::= {pr1645v2Lan2FGVlanEntry 45492224}

pr1645v2Lan2FGVlanMCOutBandwidth5min OBJECT-TYPE
   SYNTAX      Integer32
   MAX-ACCESS  read-only
   STATUS      current
   DESCRIPTION
      "Path: ethernet2.performance.vlan.mibCounters.ifOutBandwidth.5min

       unit name = bps
       formula = 8 * ; 8 /"
   ::= {pr1645v2Lan2FGVlanEntry 45507584}

pr1645v2Lan2FGVlanVlanVid OBJECT-TYPE
   SYNTAX      Integer32
   MAX-ACCESS  read-only
   STATUS      current
   DESCRIPTION
      "Path: ethernet2.performance.vlan.vlan.vid"
   ::= {pr1645v2Lan2FGVlanEntry 234946560}

pr1645v2Lan2FGVlanPppLinkMonitoringRequestsSent OBJECT-TYPE
   SYNTAX      Gauge32
   MAX-ACCESS  read-only
   STATUS      current
   DESCRIPTION
      "Path: ethernet2.performance.vlan.ppp.linkMonitoring.requestsSent

       32 bit unsigned gauge value."
   ::= {pr1645v2Lan2FGVlanEntry 50397440}

pr1645v2Lan2FGVlanPppLinkMonitoringRepliesRcvd OBJECT-TYPE
   SYNTAX      Gauge32
   MAX-ACCESS  read-only
   STATUS      current
   DESCRIPTION
      "Path: ethernet2.performance.vlan.ppp.linkMonitoring.repliesRcvd

       32 bit unsigned gauge value."
   ::= {pr1645v2Lan2FGVlanEntry 50397696}

pr1645v2Lan2FGVlanPppLinkMonitoringRequestsRcvd OBJECT-TYPE
   SYNTAX      Gauge32
   MAX-ACCESS  read-only
   STATUS      current
   DESCRIPTION
      "Path: ethernet2.performance.vlan.ppp.linkMonitoring.requestsRcvd

       32 bit unsigned gauge value."
   ::= {pr1645v2Lan2FGVlanEntry 50397952}

pr1645v2Lan2FGVlanPppLinkMonitoringRepliesSent OBJECT-TYPE
   SYNTAX      Gauge32
   MAX-ACCESS  read-only
   STATUS      current
   DESCRIPTION
      "Path: ethernet2.performance.vlan.ppp.linkMonitoring.repliesSent

       32 bit unsigned gauge value."
   ::= {pr1645v2Lan2FGVlanEntry 50398208}

pr1645v2Lan2FGVlanMCH2P OBJECT-TYPE
   SYNTAX      SEQUENCE OF Pr1645v2Lan2FGVlanMCH2PEntry
   MAX-ACCESS  not-accessible
   STATUS      current
   DESCRIPTION
      ""
   ::= {pr1645v2Lan2FGVlan 41549824}

pr1645v2Lan2FGVlanMCH2PEntry OBJECT-TYPE
   SYNTAX      Pr1645v2Lan2FGVlanMCH2PEntry
   MAX-ACCESS  not-accessible
   STATUS      current
   DESCRIPTION
      ""
   INDEX      { pr1645v2Lan2FGVlanTableIx,
                pr1645v2Lan2FGVlanMCH2PTableIx }
   ::= {pr1645v2Lan2FGVlanMCH2P 1}

Pr1645v2Lan2FGVlanMCH2PEntry ::=
   SEQUENCE
      {
      pr1645v2Lan2FGVlanMCH2PTableIx
         TableIndex,
      pr1645v2Lan2FGVlanMCH2PSysUpTime
         TimeTicks,
      pr1645v2Lan2FGVlanMCH2PIfUpTime
         TimeTicks,
      pr1645v2Lan2FGVlanMCH2PIfStatChanges
         Counter32,
      pr1645v2Lan2FGVlanMCH2PIfInOctets
         Counter64,
      pr1645v2Lan2FGVlanMCH2PIfInUCPkts
         Counter64,
      pr1645v2Lan2FGVlanMCH2PIfInNUCPkts
         Counter64,
      pr1645v2Lan2FGVlanMCH2PIfInBCPkts
         Counter64,
      pr1645v2Lan2FGVlanMCH2PIfInMCPkts
         Counter64,
      pr1645v2Lan2FGVlanMCH2PIfInDiscards
         Counter64,
      pr1645v2Lan2FGVlanMCH2PIfInErrors
         Counter64,
      pr1645v2Lan2FGVlanMCH2PIfInUnkwn
         Counter64,
      pr1645v2Lan2FGVlanMCH2PInDropEx
         Counter64,
      pr1645v2Lan2FGVlanMCH2PInDropNoMac
         Counter64,
      pr1645v2Lan2FGVlanMCH2PInDropNUCast
         Counter64,
      pr1645v2Lan2FGVlanMCH2PInDropFilter
         Counter64,
      pr1645v2Lan2FGVlanMCH2PIfInBandwidth
         Integer32,
      pr1645v2Lan2FGVlanMCH2PIfOutOctets
         Counter64,
      pr1645v2Lan2FGVlanMCH2PIfOutUCPkts
         Counter64,
      pr1645v2Lan2FGVlanMCH2PIfOutNUCPkts
         Counter64,
      pr1645v2Lan2FGVlanMCH2PIfOutBCPkts
         Counter64,
      pr1645v2Lan2FGVlanMCH2PIfOutMCPkts
         Counter64,
      pr1645v2Lan2FGVlanMCH2PIfOutDiscards
         Counter64,
      pr1645v2Lan2FGVlanMCH2PIfOutErrors
         Counter64,
      pr1645v2Lan2FGVlanMCH2POutDropEx
         Counter64,
      pr1645v2Lan2FGVlanMCH2POutDropNoArp
         Counter64,
      pr1645v2Lan2FGVlanMCH2POutDropFilter
         Counter64,
      pr1645v2Lan2FGVlanMCH2PIfOutBandwidth
         Integer32,
      pr1645v2Lan2FGVlanMCH2PIfErrSec
         Counter32
      }

pr1645v2Lan2FGVlanMCH2PTableIx OBJECT-TYPE
   SYNTAX      TableIndex
   MAX-ACCESS  not-accessible
   STATUS      current
   DESCRIPTION
      ""
   ::= {pr1645v2Lan2FGVlanMCH2PEntry 11}

pr1645v2Lan2FGVlanMCH2PSysUpTime OBJECT-TYPE
   SYNTAX      TimeTicks
   MAX-ACCESS  read-only
   STATUS      current
   DESCRIPTION
      "Path: ethernet2.performance.vlan.mibCounters.h2Performance.sysUpTime

       Time in centi-second."
   ::= {pr1645v2Lan2FGVlanMCH2PEntry 16777216}

pr1645v2Lan2FGVlanMCH2PIfUpTime OBJECT-TYPE
   SYNTAX      TimeTicks
   MAX-ACCESS  read-only
   STATUS      current
   DESCRIPTION
      "Path: ethernet2.performance.vlan.mibCounters.h2Performance.ifUpTime

       Time in centi-second."
   ::= {pr1645v2Lan2FGVlanMCH2PEntry 33554432}

pr1645v2Lan2FGVlanMCH2PIfStatChanges OBJECT-TYPE
   SYNTAX      Counter32
   MAX-ACCESS  read-only
   STATUS      current
   DESCRIPTION
      "Path: ethernet2.performance.vlan.mibCounters.h2Performance.ifStatusChanges

       32 bit unsigned wrappable counter."
   ::= {pr1645v2Lan2FGVlanMCH2PEntry 50331648}

pr1645v2Lan2FGVlanMCH2PIfInOctets OBJECT-TYPE
   SYNTAX      Counter64
   MAX-ACCESS  read-only
   STATUS      current
   DESCRIPTION
      "Path: ethernet2.performance.vlan.mibCounters.h2Performance.ifInOctets

       64 bit unsigned wrappable counter."
   ::= {pr1645v2Lan2FGVlanMCH2PEntry 67108864}

pr1645v2Lan2FGVlanMCH2PIfInUCPkts OBJECT-TYPE
   SYNTAX      Counter64
   MAX-ACCESS  read-only
   STATUS      current
   DESCRIPTION
      "Path: ethernet2.performance.vlan.mibCounters.h2Performance.ifInUcastPkts

       64 bit unsigned wrappable counter."
   ::= {pr1645v2Lan2FGVlanMCH2PEntry 83886080}

pr1645v2Lan2FGVlanMCH2PIfInNUCPkts OBJECT-TYPE
   SYNTAX      Counter64
   MAX-ACCESS  read-only
   STATUS      current
   DESCRIPTION
      "Path: ethernet2.performance.vlan.mibCounters.h2Performance.ifInNUcastPkts

       64 bit unsigned wrappable counter."
   ::= {pr1645v2Lan2FGVlanMCH2PEntry 100663296}

pr1645v2Lan2FGVlanMCH2PIfInBCPkts OBJECT-TYPE
   SYNTAX      Counter64
   MAX-ACCESS  read-only
   STATUS      current
   DESCRIPTION
      "Path: ethernet2.performance.vlan.mibCounters.h2Performance.ifInBcastPkts

       64 bit unsigned wrappable counter."
   ::= {pr1645v2Lan2FGVlanMCH2PEntry 419430400}

pr1645v2Lan2FGVlanMCH2PIfInMCPkts OBJECT-TYPE
   SYNTAX      Counter64
   MAX-ACCESS  read-only
   STATUS      current
   DESCRIPTION
      "Path: ethernet2.performance.vlan.mibCounters.h2Performance.ifInMcastPkts

       64 bit unsigned wrappable counter."
   ::= {pr1645v2Lan2FGVlanMCH2PEntry 436207616}

pr1645v2Lan2FGVlanMCH2PIfInDiscards OBJECT-TYPE
   SYNTAX      Counter64
   MAX-ACCESS  read-only
   STATUS      current
   DESCRIPTION
      "Path: ethernet2.performance.vlan.mibCounters.h2Performance.ifInDiscards

       64 bit unsigned wrappable counter."
   ::= {pr1645v2Lan2FGVlanMCH2PEntry 117440512}

pr1645v2Lan2FGVlanMCH2PIfInErrors OBJECT-TYPE
   SYNTAX      Counter64
   MAX-ACCESS  read-only
   STATUS      current
   DESCRIPTION
      "Path: ethernet2.performance.vlan.mibCounters.h2Performance.ifInErrors

       64 bit unsigned wrappable counter."
   ::= {pr1645v2Lan2FGVlanMCH2PEntry 134217728}

pr1645v2Lan2FGVlanMCH2PIfInUnkwn OBJECT-TYPE
   SYNTAX      Counter64
   MAX-ACCESS  read-only
   STATUS      current
   DESCRIPTION
      "Path: ethernet2.performance.vlan.mibCounters.h2Performance.ifInUnknownProtos

       64 bit unsigned wrappable counter."
   ::= {pr1645v2Lan2FGVlanMCH2PEntry 150994944}

pr1645v2Lan2FGVlanMCH2PInDropEx OBJECT-TYPE
   SYNTAX      Counter64
   MAX-ACCESS  read-only
   STATUS      current
   DESCRIPTION
      "Path: ethernet2.performance.vlan.mibCounters.h2Performance.ifInDropLevelExceeded

       64 bit unsigned wrappable counter."
   ::= {pr1645v2Lan2FGVlanMCH2PEntry 335544320}

pr1645v2Lan2FGVlanMCH2PInDropNoMac OBJECT-TYPE
   SYNTAX      Counter64
   MAX-ACCESS  read-only
   STATUS      current
   DESCRIPTION
      "Path: ethernet2.performance.vlan.mibCounters.h2Performance.fInDiscardsNoMacFit

       64 bit unsigned wrappable counter."
   ::= {pr1645v2Lan2FGVlanMCH2PEntry 301989888}

pr1645v2Lan2FGVlanMCH2PInDropNUCast OBJECT-TYPE
   SYNTAX      Counter64
   MAX-ACCESS  read-only
   STATUS      current
   DESCRIPTION
      "Path: ethernet2.performance.vlan.mibCounters.h2Performance.fInDiscardsNUCast

       64 bit unsigned wrappable counter."
   ::= {pr1645v2Lan2FGVlanMCH2PEntry 318767104}

pr1645v2Lan2FGVlanMCH2PInDropFilter OBJECT-TYPE
   SYNTAX      Counter64
   MAX-ACCESS  read-only
   STATUS      current
   DESCRIPTION
      "Path: ethernet2.performance.vlan.mibCounters.h2Performance.fInDiscardsFilter

       64 bit unsigned wrappable counter."
   ::= {pr1645v2Lan2FGVlanMCH2PEntry 385875968}

pr1645v2Lan2FGVlanMCH2PIfInBandwidth OBJECT-TYPE
   SYNTAX      Integer32
   MAX-ACCESS  read-only
   STATUS      current
   DESCRIPTION
      "Path: ethernet2.performance.vlan.mibCounters.h2Performance.ifInBandwidth

       unit name = bps
       formula = 8 * ; 8 /"
   ::= {pr1645v2Lan2FGVlanMCH2PEntry 268435456}

pr1645v2Lan2FGVlanMCH2PIfOutOctets OBJECT-TYPE
   SYNTAX      Counter64
   MAX-ACCESS  read-only
   STATUS      current
   DESCRIPTION
      "Path: ethernet2.performance.vlan.mibCounters.h2Performance.ifOutOctets

       64 bit unsigned wrappable counter."
   ::= {pr1645v2Lan2FGVlanMCH2PEntry 167772160}

pr1645v2Lan2FGVlanMCH2PIfOutUCPkts OBJECT-TYPE
   SYNTAX      Counter64
   MAX-ACCESS  read-only
   STATUS      current
   DESCRIPTION
      "Path: ethernet2.performance.vlan.mibCounters.h2Performance.ifOutUcastPkts

       64 bit unsigned wrappable counter."
   ::= {pr1645v2Lan2FGVlanMCH2PEntry 184549376}

pr1645v2Lan2FGVlanMCH2PIfOutNUCPkts OBJECT-TYPE
   SYNTAX      Counter64
   MAX-ACCESS  read-only
   STATUS      current
   DESCRIPTION
      "Path: ethernet2.performance.vlan.mibCounters.h2Performance.ifOutNUcastPkts

       64 bit unsigned wrappable counter."
   ::= {pr1645v2Lan2FGVlanMCH2PEntry 201326592}

pr1645v2Lan2FGVlanMCH2PIfOutBCPkts OBJECT-TYPE
   SYNTAX      Counter64
   MAX-ACCESS  read-only
   STATUS      current
   DESCRIPTION
      "Path: ethernet2.performance.vlan.mibCounters.h2Performance.ifOutBcastPkts

       64 bit unsigned wrappable counter."
   ::= {pr1645v2Lan2FGVlanMCH2PEntry 452984832}

pr1645v2Lan2FGVlanMCH2PIfOutMCPkts OBJECT-TYPE
   SYNTAX      Counter64
   MAX-ACCESS  read-only
   STATUS      current
   DESCRIPTION
      "Path: ethernet2.performance.vlan.mibCounters.h2Performance.ifOutMcastPkts

       64 bit unsigned wrappable counter."
   ::= {pr1645v2Lan2FGVlanMCH2PEntry 469762048}

pr1645v2Lan2FGVlanMCH2PIfOutDiscards OBJECT-TYPE
   SYNTAX      Counter64
   MAX-ACCESS  read-only
   STATUS      current
   DESCRIPTION
      "Path: ethernet2.performance.vlan.mibCounters.h2Performance.ifOutDiscards

       64 bit unsigned wrappable counter."
   ::= {pr1645v2Lan2FGVlanMCH2PEntry 218103808}

pr1645v2Lan2FGVlanMCH2PIfOutErrors OBJECT-TYPE
   SYNTAX      Counter64
   MAX-ACCESS  read-only
   STATUS      current
   DESCRIPTION
      "Path: ethernet2.performance.vlan.mibCounters.h2Performance.ifOutErrors

       64 bit unsigned wrappable counter."
   ::= {pr1645v2Lan2FGVlanMCH2PEntry 234881024}

pr1645v2Lan2FGVlanMCH2POutDropEx OBJECT-TYPE
   SYNTAX      Counter64
   MAX-ACCESS  read-only
   STATUS      current
   DESCRIPTION
      "Path: ethernet2.performance.vlan.mibCounters.h2Performance.ifOutDropLevelExceeded

       64 bit unsigned wrappable counter."
   ::= {pr1645v2Lan2FGVlanMCH2PEntry 352321536}

pr1645v2Lan2FGVlanMCH2POutDropNoArp OBJECT-TYPE
   SYNTAX      Counter64
   MAX-ACCESS  read-only
   STATUS      current
   DESCRIPTION
      "Path: ethernet2.performance.vlan.mibCounters.h2Performance.ifOutDiscardsNoArp

       64 bit unsigned wrappable counter."
   ::= {pr1645v2Lan2FGVlanMCH2PEntry 369098752}

pr1645v2Lan2FGVlanMCH2POutDropFilter OBJECT-TYPE
   SYNTAX      Counter64
   MAX-ACCESS  read-only
   STATUS      current
   DESCRIPTION
      "Path: ethernet2.performance.vlan.mibCounters.h2Performance.ifOutDiscardsFilter

       64 bit unsigned wrappable counter."
   ::= {pr1645v2Lan2FGVlanMCH2PEntry 402653184}

pr1645v2Lan2FGVlanMCH2PIfOutBandwidth OBJECT-TYPE
   SYNTAX      Integer32
   MAX-ACCESS  read-only
   STATUS      current
   DESCRIPTION
      "Path: ethernet2.performance.vlan.mibCounters.h2Performance.ifOutBandwidth

       unit name = bps
       formula = 8 * ; 8 /"
   ::= {pr1645v2Lan2FGVlanMCH2PEntry 285212672}

pr1645v2Lan2FGVlanMCH2PIfErrSec OBJECT-TYPE
   SYNTAX      Counter32
   MAX-ACCESS  read-only
   STATUS      current
   DESCRIPTION
      "Path: ethernet2.performance.vlan.mibCounters.h2Performance.ifErrSec

       32 bit unsigned wrappable counter."
   ::= {pr1645v2Lan2FGVlanMCH2PEntry 251658240}

pr1645v2Lan2FGVlanMCH24P OBJECT-TYPE
   SYNTAX      SEQUENCE OF Pr1645v2Lan2FGVlanMCH24PEntry
   MAX-ACCESS  not-accessible
   STATUS      current
   DESCRIPTION
      ""
   ::= {pr1645v2Lan2FGVlan 41615360}

pr1645v2Lan2FGVlanMCH24PEntry OBJECT-TYPE
   SYNTAX      Pr1645v2Lan2FGVlanMCH24PEntry
   MAX-ACCESS  not-accessible
   STATUS      current
   DESCRIPTION
      ""
   INDEX      { pr1645v2Lan2FGVlanTableIx,
                pr1645v2Lan2FGVlanMCH24PTableIx }
   ::= {pr1645v2Lan2FGVlanMCH24P 1}

Pr1645v2Lan2FGVlanMCH24PEntry ::=
   SEQUENCE
      {
      pr1645v2Lan2FGVlanMCH24PTableIx
         TableIndex,
      pr1645v2Lan2FGVlanMCH24PSysUpTime
         TimeTicks,
      pr1645v2Lan2FGVlanMCH24PIfUpTime
         TimeTicks,
      pr1645v2Lan2FGVlanMCH24PIfStatChanges
         Counter32,
      pr1645v2Lan2FGVlanMCH24PIfInOctets
         Counter64,
      pr1645v2Lan2FGVlanMCH24PIfInUCPkts
         Counter64,
      pr1645v2Lan2FGVlanMCH24PIfInNUCPkts
         Counter64,
      pr1645v2Lan2FGVlanMCH24PIfInBCPkts
         Counter64,
      pr1645v2Lan2FGVlanMCH24PIfInMCPkts
         Counter64,
      pr1645v2Lan2FGVlanMCH24PIfInDiscards
         Counter64,
      pr1645v2Lan2FGVlanMCH24PIfInErrors
         Counter64,
      pr1645v2Lan2FGVlanMCH24PIfInUnkwn
         Counter64,
      pr1645v2Lan2FGVlanMCH24PInDropEx
         Counter64,
      pr1645v2Lan2FGVlanMCH24PInDropNoMac
         Counter64,
      pr1645v2Lan2FGVlanMCH24PInDropNUCast
         Counter64,
      pr1645v2Lan2FGVlanMCH24PInDropFilter
         Counter64,
      pr1645v2Lan2FGVlanMCH24PIfInBandwidth
         Integer32,
      pr1645v2Lan2FGVlanMCH24PIfOutOctets
         Counter64,
      pr1645v2Lan2FGVlanMCH24PIfOutUCPkts
         Counter64,
      pr1645v2Lan2FGVlanMCH24PIfOutNUCPkts
         Counter64,
      pr1645v2Lan2FGVlanMCH24PIfOutBCPkts
         Counter64,
      pr1645v2Lan2FGVlanMCH24PIfOutMCPkts
         Counter64,
      pr1645v2Lan2FGVlanMCH24PIfOutDiscards
         Counter64,
      pr1645v2Lan2FGVlanMCH24PIfOutErrors
         Counter64,
      pr1645v2Lan2FGVlanMCH24POutDropEx
         Counter64,
      pr1645v2Lan2FGVlanMCH24POutDropNoArp
         Counter64,
      pr1645v2Lan2FGVlanMCH24POutDropFilter
         Counter64,
      pr1645v2Lan2FGVlanMCH24PIfOutBandwidth
         Integer32,
      pr1645v2Lan2FGVlanMCH24PIfErrSec
         Counter32
      }

pr1645v2Lan2FGVlanMCH24PTableIx OBJECT-TYPE
   SYNTAX      TableIndex
   MAX-ACCESS  not-accessible
   STATUS      current
   DESCRIPTION
      ""
   ::= {pr1645v2Lan2FGVlanMCH24PEntry 11}

pr1645v2Lan2FGVlanMCH24PSysUpTime OBJECT-TYPE
   SYNTAX      TimeTicks
   MAX-ACCESS  read-only
   STATUS      current
   DESCRIPTION
      "Path: ethernet2.performance.vlan.mibCounters.h24Performance.sysUpTime

       Time in centi-second."
   ::= {pr1645v2Lan2FGVlanMCH24PEntry 16777216}

pr1645v2Lan2FGVlanMCH24PIfUpTime OBJECT-TYPE
   SYNTAX      TimeTicks
   MAX-ACCESS  read-only
   STATUS      current
   DESCRIPTION
      "Path: ethernet2.performance.vlan.mibCounters.h24Performance.ifUpTime

       Time in centi-second."
   ::= {pr1645v2Lan2FGVlanMCH24PEntry 33554432}

pr1645v2Lan2FGVlanMCH24PIfStatChanges OBJECT-TYPE
   SYNTAX      Counter32
   MAX-ACCESS  read-only
   STATUS      current
   DESCRIPTION
      "Path: ethernet2.performance.vlan.mibCounters.h24Performance.ifStatusChanges

       32 bit unsigned wrappable counter."
   ::= {pr1645v2Lan2FGVlanMCH24PEntry 50331648}

pr1645v2Lan2FGVlanMCH24PIfInOctets OBJECT-TYPE
   SYNTAX      Counter64
   MAX-ACCESS  read-only
   STATUS      current
   DESCRIPTION
      "Path: ethernet2.performance.vlan.mibCounters.h24Performance.ifInOctets

       64 bit unsigned wrappable counter."
   ::= {pr1645v2Lan2FGVlanMCH24PEntry 67108864}

pr1645v2Lan2FGVlanMCH24PIfInUCPkts OBJECT-TYPE
   SYNTAX      Counter64
   MAX-ACCESS  read-only
   STATUS      current
   DESCRIPTION
      "Path: ethernet2.performance.vlan.mibCounters.h24Performance.ifInUcastPkts

       64 bit unsigned wrappable counter."
   ::= {pr1645v2Lan2FGVlanMCH24PEntry 83886080}

pr1645v2Lan2FGVlanMCH24PIfInNUCPkts OBJECT-TYPE
   SYNTAX      Counter64
   MAX-ACCESS  read-only
   STATUS      current
   DESCRIPTION
      "Path: ethernet2.performance.vlan.mibCounters.h24Performance.ifInNUcastPkts

       64 bit unsigned wrappable counter."
   ::= {pr1645v2Lan2FGVlanMCH24PEntry 100663296}

pr1645v2Lan2FGVlanMCH24PIfInBCPkts OBJECT-TYPE
   SYNTAX      Counter64
   MAX-ACCESS  read-only
   STATUS      current
   DESCRIPTION
      "Path: ethernet2.performance.vlan.mibCounters.h24Performance.ifInBcastPkts

       64 bit unsigned wrappable counter."
   ::= {pr1645v2Lan2FGVlanMCH24PEntry 419430400}

pr1645v2Lan2FGVlanMCH24PIfInMCPkts OBJECT-TYPE
   SYNTAX      Counter64
   MAX-ACCESS  read-only
   STATUS      current
   DESCRIPTION
      "Path: ethernet2.performance.vlan.mibCounters.h24Performance.ifInMcastPkts

       64 bit unsigned wrappable counter."
   ::= {pr1645v2Lan2FGVlanMCH24PEntry 436207616}

pr1645v2Lan2FGVlanMCH24PIfInDiscards OBJECT-TYPE
   SYNTAX      Counter64
   MAX-ACCESS  read-only
   STATUS      current
   DESCRIPTION
      "Path: ethernet2.performance.vlan.mibCounters.h24Performance.ifInDiscards

       64 bit unsigned wrappable counter."
   ::= {pr1645v2Lan2FGVlanMCH24PEntry 117440512}

pr1645v2Lan2FGVlanMCH24PIfInErrors OBJECT-TYPE
   SYNTAX      Counter64
   MAX-ACCESS  read-only
   STATUS      current
   DESCRIPTION
      "Path: ethernet2.performance.vlan.mibCounters.h24Performance.ifInErrors

       64 bit unsigned wrappable counter."
   ::= {pr1645v2Lan2FGVlanMCH24PEntry 134217728}

pr1645v2Lan2FGVlanMCH24PIfInUnkwn OBJECT-TYPE
   SYNTAX      Counter64
   MAX-ACCESS  read-only
   STATUS      current
   DESCRIPTION
      "Path: ethernet2.performance.vlan.mibCounters.h24Performance.ifInUnknownProtos

       64 bit unsigned wrappable counter."
   ::= {pr1645v2Lan2FGVlanMCH24PEntry 150994944}

pr1645v2Lan2FGVlanMCH24PInDropEx OBJECT-TYPE
   SYNTAX      Counter64
   MAX-ACCESS  read-only
   STATUS      current
   DESCRIPTION
      "Path: ethernet2.performance.vlan.mibCounters.h24Performance.ifInDropLevelExceeded

       64 bit unsigned wrappable counter."
   ::= {pr1645v2Lan2FGVlanMCH24PEntry 335544320}

pr1645v2Lan2FGVlanMCH24PInDropNoMac OBJECT-TYPE
   SYNTAX      Counter64
   MAX-ACCESS  read-only
   STATUS      current
   DESCRIPTION
      "Path: ethernet2.performance.vlan.mibCounters.h24Performance.fInDiscardsNoMacFit

       64 bit unsigned wrappable counter."
   ::= {pr1645v2Lan2FGVlanMCH24PEntry 301989888}

pr1645v2Lan2FGVlanMCH24PInDropNUCast OBJECT-TYPE
   SYNTAX      Counter64
   MAX-ACCESS  read-only
   STATUS      current
   DESCRIPTION
      "Path: ethernet2.performance.vlan.mibCounters.h24Performance.fInDiscardsNUCast

       64 bit unsigned wrappable counter."
   ::= {pr1645v2Lan2FGVlanMCH24PEntry 318767104}

pr1645v2Lan2FGVlanMCH24PInDropFilter OBJECT-TYPE
   SYNTAX      Counter64
   MAX-ACCESS  read-only
   STATUS      current
   DESCRIPTION
      "Path: ethernet2.performance.vlan.mibCounters.h24Performance.fInDiscardsFilter

       64 bit unsigned wrappable counter."
   ::= {pr1645v2Lan2FGVlanMCH24PEntry 385875968}

pr1645v2Lan2FGVlanMCH24PIfInBandwidth OBJECT-TYPE
   SYNTAX      Integer32
   MAX-ACCESS  read-only
   STATUS      current
   DESCRIPTION
      "Path: ethernet2.performance.vlan.mibCounters.h24Performance.ifInBandwidth

       unit name = bps
       formula = 8 * ; 8 /"
   ::= {pr1645v2Lan2FGVlanMCH24PEntry 268435456}

pr1645v2Lan2FGVlanMCH24PIfOutOctets OBJECT-TYPE
   SYNTAX      Counter64
   MAX-ACCESS  read-only
   STATUS      current
   DESCRIPTION
      "Path: ethernet2.performance.vlan.mibCounters.h24Performance.ifOutOctets

       64 bit unsigned wrappable counter."
   ::= {pr1645v2Lan2FGVlanMCH24PEntry 167772160}

pr1645v2Lan2FGVlanMCH24PIfOutUCPkts OBJECT-TYPE
   SYNTAX      Counter64
   MAX-ACCESS  read-only
   STATUS      current
   DESCRIPTION
      "Path: ethernet2.performance.vlan.mibCounters.h24Performance.ifOutUcastPkts

       64 bit unsigned wrappable counter."
   ::= {pr1645v2Lan2FGVlanMCH24PEntry 184549376}

pr1645v2Lan2FGVlanMCH24PIfOutNUCPkts OBJECT-TYPE
   SYNTAX      Counter64
   MAX-ACCESS  read-only
   STATUS      current
   DESCRIPTION
      "Path: ethernet2.performance.vlan.mibCounters.h24Performance.ifOutNUcastPkts

       64 bit unsigned wrappable counter."
   ::= {pr1645v2Lan2FGVlanMCH24PEntry 201326592}

pr1645v2Lan2FGVlanMCH24PIfOutBCPkts OBJECT-TYPE
   SYNTAX      Counter64
   MAX-ACCESS  read-only
   STATUS      current
   DESCRIPTION
      "Path: ethernet2.performance.vlan.mibCounters.h24Performance.ifOutBcastPkts

       64 bit unsigned wrappable counter."
   ::= {pr1645v2Lan2FGVlanMCH24PEntry 452984832}

pr1645v2Lan2FGVlanMCH24PIfOutMCPkts OBJECT-TYPE
   SYNTAX      Counter64
   MAX-ACCESS  read-only
   STATUS      current
   DESCRIPTION
      "Path: ethernet2.performance.vlan.mibCounters.h24Performance.ifOutMcastPkts

       64 bit unsigned wrappable counter."
   ::= {pr1645v2Lan2FGVlanMCH24PEntry 469762048}

pr1645v2Lan2FGVlanMCH24PIfOutDiscards OBJECT-TYPE
   SYNTAX      Counter64
   MAX-ACCESS  read-only
   STATUS      current
   DESCRIPTION
      "Path: ethernet2.performance.vlan.mibCounters.h24Performance.ifOutDiscards

       64 bit unsigned wrappable counter."
   ::= {pr1645v2Lan2FGVlanMCH24PEntry 218103808}

pr1645v2Lan2FGVlanMCH24PIfOutErrors OBJECT-TYPE
   SYNTAX      Counter64
   MAX-ACCESS  read-only
   STATUS      current
   DESCRIPTION
      "Path: ethernet2.performance.vlan.mibCounters.h24Performance.ifOutErrors

       64 bit unsigned wrappable counter."
   ::= {pr1645v2Lan2FGVlanMCH24PEntry 234881024}

pr1645v2Lan2FGVlanMCH24POutDropEx OBJECT-TYPE
   SYNTAX      Counter64
   MAX-ACCESS  read-only
   STATUS      current
   DESCRIPTION
      "Path: ethernet2.performance.vlan.mibCounters.h24Performance.ifOutDropLevelExceeded

       64 bit unsigned wrappable counter."
   ::= {pr1645v2Lan2FGVlanMCH24PEntry 352321536}

pr1645v2Lan2FGVlanMCH24POutDropNoArp OBJECT-TYPE
   SYNTAX      Counter64
   MAX-ACCESS  read-only
   STATUS      current
   DESCRIPTION
      "Path: ethernet2.performance.vlan.mibCounters.h24Performance.ifOutDiscardsNoArp

       64 bit unsigned wrappable counter."
   ::= {pr1645v2Lan2FGVlanMCH24PEntry 369098752}

pr1645v2Lan2FGVlanMCH24POutDropFilter OBJECT-TYPE
   SYNTAX      Counter64
   MAX-ACCESS  read-only
   STATUS      current
   DESCRIPTION
      "Path: ethernet2.performance.vlan.mibCounters.h24Performance.ifOutDiscardsFilter

       64 bit unsigned wrappable counter."
   ::= {pr1645v2Lan2FGVlanMCH24PEntry 402653184}

pr1645v2Lan2FGVlanMCH24PIfOutBandwidth OBJECT-TYPE
   SYNTAX      Integer32
   MAX-ACCESS  read-only
   STATUS      current
   DESCRIPTION
      "Path: ethernet2.performance.vlan.mibCounters.h24Performance.ifOutBandwidth

       unit name = bps
       formula = 8 * ; 8 /"
   ::= {pr1645v2Lan2FGVlanMCH24PEntry 285212672}

pr1645v2Lan2FGVlanMCH24PIfErrSec OBJECT-TYPE
   SYNTAX      Counter32
   MAX-ACCESS  read-only
   STATUS      current
   DESCRIPTION
      "Path: ethernet2.performance.vlan.mibCounters.h24Performance.ifErrSec

       32 bit unsigned wrappable counter."
   ::= {pr1645v2Lan2FGVlanMCH24PEntry 251658240}

pr1645v2Lan2FGVlanMCD7P OBJECT-TYPE
   SYNTAX      SEQUENCE OF Pr1645v2Lan2FGVlanMCD7PEntry
   MAX-ACCESS  not-accessible
   STATUS      current
   DESCRIPTION
      ""
   ::= {pr1645v2Lan2FGVlan 41680896}

pr1645v2Lan2FGVlanMCD7PEntry OBJECT-TYPE
   SYNTAX      Pr1645v2Lan2FGVlanMCD7PEntry
   MAX-ACCESS  not-accessible
   STATUS      current
   DESCRIPTION
      ""
   INDEX      { pr1645v2Lan2FGVlanTableIx,
                pr1645v2Lan2FGVlanMCD7PTableIx }
   ::= {pr1645v2Lan2FGVlanMCD7P 1}

Pr1645v2Lan2FGVlanMCD7PEntry ::=
   SEQUENCE
      {
      pr1645v2Lan2FGVlanMCD7PTableIx
         TableIndex,
      pr1645v2Lan2FGVlanMCD7PSysUpTime
         TimeTicks,
      pr1645v2Lan2FGVlanMCD7PIfUpTime
         TimeTicks,
      pr1645v2Lan2FGVlanMCD7PIfStatChanges
         Counter32,
      pr1645v2Lan2FGVlanMCD7PIfInOctets
         Counter64,
      pr1645v2Lan2FGVlanMCD7PIfInUCPkts
         Counter64,
      pr1645v2Lan2FGVlanMCD7PIfInNUCPkts
         Counter64,
      pr1645v2Lan2FGVlanMCD7PIfInBCPkts
         Counter64,
      pr1645v2Lan2FGVlanMCD7PIfInMCPkts
         Counter64,
      pr1645v2Lan2FGVlanMCD7PIfInDiscards
         Counter64,
      pr1645v2Lan2FGVlanMCD7PIfInErrors
         Counter64,
      pr1645v2Lan2FGVlanMCD7PIfInUnkwn
         Counter64,
      pr1645v2Lan2FGVlanMCD7PInDropEx
         Counter64,
      pr1645v2Lan2FGVlanMCD7PInDropNoMac
         Counter64,
      pr1645v2Lan2FGVlanMCD7PInDropNUCast
         Counter64,
      pr1645v2Lan2FGVlanMCD7PInDropFilter
         Counter64,
      pr1645v2Lan2FGVlanMCD7PIfInBandwidth
         Integer32,
      pr1645v2Lan2FGVlanMCD7PIfOutOctets
         Counter64,
      pr1645v2Lan2FGVlanMCD7PIfOutUCPkts
         Counter64,
      pr1645v2Lan2FGVlanMCD7PIfOutNUCPkts
         Counter64,
      pr1645v2Lan2FGVlanMCD7PIfOutBCPkts
         Counter64,
      pr1645v2Lan2FGVlanMCD7PIfOutMCPkts
         Counter64,
      pr1645v2Lan2FGVlanMCD7PIfOutDiscards
         Counter64,
      pr1645v2Lan2FGVlanMCD7PIfOutErrors
         Counter64,
      pr1645v2Lan2FGVlanMCD7POutDropEx
         Counter64,
      pr1645v2Lan2FGVlanMCD7POutDropNoArp
         Counter64,
      pr1645v2Lan2FGVlanMCD7POutDropFilter
         Counter64,
      pr1645v2Lan2FGVlanMCD7PIfOutBandwidth
         Integer32,
      pr1645v2Lan2FGVlanMCD7PIfErrSec
         Counter32
      }

pr1645v2Lan2FGVlanMCD7PTableIx OBJECT-TYPE
   SYNTAX      TableIndex
   MAX-ACCESS  not-accessible
   STATUS      current
   DESCRIPTION
      ""
   ::= {pr1645v2Lan2FGVlanMCD7PEntry 11}

pr1645v2Lan2FGVlanMCD7PSysUpTime OBJECT-TYPE
   SYNTAX      TimeTicks
   MAX-ACCESS  read-only
   STATUS      current
   DESCRIPTION
      "Path: ethernet2.performance.vlan.mibCounters.d7Performance.sysUpTime

       Time in centi-second."
   ::= {pr1645v2Lan2FGVlanMCD7PEntry 16777216}

pr1645v2Lan2FGVlanMCD7PIfUpTime OBJECT-TYPE
   SYNTAX      TimeTicks
   MAX-ACCESS  read-only
   STATUS      current
   DESCRIPTION
      "Path: ethernet2.performance.vlan.mibCounters.d7Performance.ifUpTime

       Time in centi-second."
   ::= {pr1645v2Lan2FGVlanMCD7PEntry 33554432}

pr1645v2Lan2FGVlanMCD7PIfStatChanges OBJECT-TYPE
   SYNTAX      Counter32
   MAX-ACCESS  read-only
   STATUS      current
   DESCRIPTION
      "Path: ethernet2.performance.vlan.mibCounters.d7Performance.ifStatusChanges

       32 bit unsigned wrappable counter."
   ::= {pr1645v2Lan2FGVlanMCD7PEntry 50331648}

pr1645v2Lan2FGVlanMCD7PIfInOctets OBJECT-TYPE
   SYNTAX      Counter64
   MAX-ACCESS  read-only
   STATUS      current
   DESCRIPTION
      "Path: ethernet2.performance.vlan.mibCounters.d7Performance.ifInOctets

       64 bit unsigned wrappable counter."
   ::= {pr1645v2Lan2FGVlanMCD7PEntry 67108864}

pr1645v2Lan2FGVlanMCD7PIfInUCPkts OBJECT-TYPE
   SYNTAX      Counter64
   MAX-ACCESS  read-only
   STATUS      current
   DESCRIPTION
      "Path: ethernet2.performance.vlan.mibCounters.d7Performance.ifInUcastPkts

       64 bit unsigned wrappable counter."
   ::= {pr1645v2Lan2FGVlanMCD7PEntry 83886080}

pr1645v2Lan2FGVlanMCD7PIfInNUCPkts OBJECT-TYPE
   SYNTAX      Counter64
   MAX-ACCESS  read-only
   STATUS      current
   DESCRIPTION
      "Path: ethernet2.performance.vlan.mibCounters.d7Performance.ifInNUcastPkts

       64 bit unsigned wrappable counter."
   ::= {pr1645v2Lan2FGVlanMCD7PEntry 100663296}

pr1645v2Lan2FGVlanMCD7PIfInBCPkts OBJECT-TYPE
   SYNTAX      Counter64
   MAX-ACCESS  read-only
   STATUS      current
   DESCRIPTION
      "Path: ethernet2.performance.vlan.mibCounters.d7Performance.ifInBcastPkts

       64 bit unsigned wrappable counter."
   ::= {pr1645v2Lan2FGVlanMCD7PEntry 419430400}

pr1645v2Lan2FGVlanMCD7PIfInMCPkts OBJECT-TYPE
   SYNTAX      Counter64
   MAX-ACCESS  read-only
   STATUS      current
   DESCRIPTION
      "Path: ethernet2.performance.vlan.mibCounters.d7Performance.ifInMcastPkts

       64 bit unsigned wrappable counter."
   ::= {pr1645v2Lan2FGVlanMCD7PEntry 436207616}

pr1645v2Lan2FGVlanMCD7PIfInDiscards OBJECT-TYPE
   SYNTAX      Counter64
   MAX-ACCESS  read-only
   STATUS      current
   DESCRIPTION
      "Path: ethernet2.performance.vlan.mibCounters.d7Performance.ifInDiscards

       64 bit unsigned wrappable counter."
   ::= {pr1645v2Lan2FGVlanMCD7PEntry 117440512}

pr1645v2Lan2FGVlanMCD7PIfInErrors OBJECT-TYPE
   SYNTAX      Counter64
   MAX-ACCESS  read-only
   STATUS      current
   DESCRIPTION
      "Path: ethernet2.performance.vlan.mibCounters.d7Performance.ifInErrors

       64 bit unsigned wrappable counter."
   ::= {pr1645v2Lan2FGVlanMCD7PEntry 134217728}

pr1645v2Lan2FGVlanMCD7PIfInUnkwn OBJECT-TYPE
   SYNTAX      Counter64
   MAX-ACCESS  read-only
   STATUS      current
   DESCRIPTION
      "Path: ethernet2.performance.vlan.mibCounters.d7Performance.ifInUnknownProtos

       64 bit unsigned wrappable counter."
   ::= {pr1645v2Lan2FGVlanMCD7PEntry 150994944}

pr1645v2Lan2FGVlanMCD7PInDropEx OBJECT-TYPE
   SYNTAX      Counter64
   MAX-ACCESS  read-only
   STATUS      current
   DESCRIPTION
      "Path: ethernet2.performance.vlan.mibCounters.d7Performance.ifInDropLevelExceeded

       64 bit unsigned wrappable counter."
   ::= {pr1645v2Lan2FGVlanMCD7PEntry 335544320}

pr1645v2Lan2FGVlanMCD7PInDropNoMac OBJECT-TYPE
   SYNTAX      Counter64
   MAX-ACCESS  read-only
   STATUS      current
   DESCRIPTION
      "Path: ethernet2.performance.vlan.mibCounters.d7Performance.fInDiscardsNoMacFit

       64 bit unsigned wrappable counter."
   ::= {pr1645v2Lan2FGVlanMCD7PEntry 301989888}

pr1645v2Lan2FGVlanMCD7PInDropNUCast OBJECT-TYPE
   SYNTAX      Counter64
   MAX-ACCESS  read-only
   STATUS      current
   DESCRIPTION
      "Path: ethernet2.performance.vlan.mibCounters.d7Performance.fInDiscardsNUCast

       64 bit unsigned wrappable counter."
   ::= {pr1645v2Lan2FGVlanMCD7PEntry 318767104}

pr1645v2Lan2FGVlanMCD7PInDropFilter OBJECT-TYPE
   SYNTAX      Counter64
   MAX-ACCESS  read-only
   STATUS      current
   DESCRIPTION
      "Path: ethernet2.performance.vlan.mibCounters.d7Performance.fInDiscardsFilter

       64 bit unsigned wrappable counter."
   ::= {pr1645v2Lan2FGVlanMCD7PEntry 385875968}

pr1645v2Lan2FGVlanMCD7PIfInBandwidth OBJECT-TYPE
   SYNTAX      Integer32
   MAX-ACCESS  read-only
   STATUS      current
   DESCRIPTION
      "Path: ethernet2.performance.vlan.mibCounters.d7Performance.ifInBandwidth

       unit name = bps
       formula = 8 * ; 8 /"
   ::= {pr1645v2Lan2FGVlanMCD7PEntry 268435456}

pr1645v2Lan2FGVlanMCD7PIfOutOctets OBJECT-TYPE
   SYNTAX      Counter64
   MAX-ACCESS  read-only
   STATUS      current
   DESCRIPTION
      "Path: ethernet2.performance.vlan.mibCounters.d7Performance.ifOutOctets

       64 bit unsigned wrappable counter."
   ::= {pr1645v2Lan2FGVlanMCD7PEntry 167772160}

pr1645v2Lan2FGVlanMCD7PIfOutUCPkts OBJECT-TYPE
   SYNTAX      Counter64
   MAX-ACCESS  read-only
   STATUS      current
   DESCRIPTION
      "Path: ethernet2.performance.vlan.mibCounters.d7Performance.ifOutUcastPkts

       64 bit unsigned wrappable counter."
   ::= {pr1645v2Lan2FGVlanMCD7PEntry 184549376}

pr1645v2Lan2FGVlanMCD7PIfOutNUCPkts OBJECT-TYPE
   SYNTAX      Counter64
   MAX-ACCESS  read-only
   STATUS      current
   DESCRIPTION
      "Path: ethernet2.performance.vlan.mibCounters.d7Performance.ifOutNUcastPkts

       64 bit unsigned wrappable counter."
   ::= {pr1645v2Lan2FGVlanMCD7PEntry 201326592}

pr1645v2Lan2FGVlanMCD7PIfOutBCPkts OBJECT-TYPE
   SYNTAX      Counter64
   MAX-ACCESS  read-only
   STATUS      current
   DESCRIPTION
      "Path: ethernet2.performance.vlan.mibCounters.d7Performance.ifOutBcastPkts

       64 bit unsigned wrappable counter."
   ::= {pr1645v2Lan2FGVlanMCD7PEntry 452984832}

pr1645v2Lan2FGVlanMCD7PIfOutMCPkts OBJECT-TYPE
   SYNTAX      Counter64
   MAX-ACCESS  read-only
   STATUS      current
   DESCRIPTION
      "Path: ethernet2.performance.vlan.mibCounters.d7Performance.ifOutMcastPkts

       64 bit unsigned wrappable counter."
   ::= {pr1645v2Lan2FGVlanMCD7PEntry 469762048}

pr1645v2Lan2FGVlanMCD7PIfOutDiscards OBJECT-TYPE
   SYNTAX      Counter64
   MAX-ACCESS  read-only
   STATUS      current
   DESCRIPTION
      "Path: ethernet2.performance.vlan.mibCounters.d7Performance.ifOutDiscards

       64 bit unsigned wrappable counter."
   ::= {pr1645v2Lan2FGVlanMCD7PEntry 218103808}

pr1645v2Lan2FGVlanMCD7PIfOutErrors OBJECT-TYPE
   SYNTAX      Counter64
   MAX-ACCESS  read-only
   STATUS      current
   DESCRIPTION
      "Path: ethernet2.performance.vlan.mibCounters.d7Performance.ifOutErrors

       64 bit unsigned wrappable counter."
   ::= {pr1645v2Lan2FGVlanMCD7PEntry 234881024}

pr1645v2Lan2FGVlanMCD7POutDropEx OBJECT-TYPE
   SYNTAX      Counter64
   MAX-ACCESS  read-only
   STATUS      current
   DESCRIPTION
      "Path: ethernet2.performance.vlan.mibCounters.d7Performance.ifOutDropLevelExceeded

       64 bit unsigned wrappable counter."
   ::= {pr1645v2Lan2FGVlanMCD7PEntry 352321536}

pr1645v2Lan2FGVlanMCD7POutDropNoArp OBJECT-TYPE
   SYNTAX      Counter64
   MAX-ACCESS  read-only
   STATUS      current
   DESCRIPTION
      "Path: ethernet2.performance.vlan.mibCounters.d7Performance.ifOutDiscardsNoArp

       64 bit unsigned wrappable counter."
   ::= {pr1645v2Lan2FGVlanMCD7PEntry 369098752}

pr1645v2Lan2FGVlanMCD7POutDropFilter OBJECT-TYPE
   SYNTAX      Counter64
   MAX-ACCESS  read-only
   STATUS      current
   DESCRIPTION
      "Path: ethernet2.performance.vlan.mibCounters.d7Performance.ifOutDiscardsFilter

       64 bit unsigned wrappable counter."
   ::= {pr1645v2Lan2FGVlanMCD7PEntry 402653184}

pr1645v2Lan2FGVlanMCD7PIfOutBandwidth OBJECT-TYPE
   SYNTAX      Integer32
   MAX-ACCESS  read-only
   STATUS      current
   DESCRIPTION
      "Path: ethernet2.performance.vlan.mibCounters.d7Performance.ifOutBandwidth

       unit name = bps
       formula = 8 * ; 8 /"
   ::= {pr1645v2Lan2FGVlanMCD7PEntry 285212672}

pr1645v2Lan2FGVlanMCD7PIfErrSec OBJECT-TYPE
   SYNTAX      Counter32
   MAX-ACCESS  read-only
   STATUS      current
   DESCRIPTION
      "Path: ethernet2.performance.vlan.mibCounters.d7Performance.ifErrSec

       32 bit unsigned wrappable counter."
   ::= {pr1645v2Lan2FGVlanMCD7PEntry 251658240}

pr1645v2Lan2FGVlanInPQs OBJECT-TYPE
   SYNTAX      SEQUENCE OF Pr1645v2Lan2FGVlanInPQsEntry
   MAX-ACCESS  not-accessible
   STATUS      current
   DESCRIPTION
      ""
   ::= {pr1645v2Lan2FGVlan 100663296}

pr1645v2Lan2FGVlanInPQsEntry OBJECT-TYPE
   SYNTAX      Pr1645v2Lan2FGVlanInPQsEntry
   MAX-ACCESS  not-accessible
   STATUS      current
   DESCRIPTION
      ""
   INDEX      { pr1645v2Lan2FGVlanTableIx,
                pr1645v2Lan2FGVlanInPQsTableIx }
   ::= {pr1645v2Lan2FGVlanInPQs 1}

Pr1645v2Lan2FGVlanInPQsEntry ::=
   SEQUENCE
      {
      pr1645v2Lan2FGVlanInPQsTableIx
         TableIndex,
      pr1645v2Lan2FGVlanInPQsName
         INTEGER,
      pr1645v2Lan2FGVlanInPQsLength
         Integer32,
      pr1645v2Lan2FGVlanInPQsOctetLength
         Integer32,
      pr1645v2Lan2FGVlanInPQsRedLength
         Integer32,
      pr1645v2Lan2FGVlanInPQsPacketsTotal
         Counter64,
      pr1645v2Lan2FGVlanInPQsPacketsDirectTx
         Counter64,
      pr1645v2Lan2FGVlanInPQsPacketsQueued
         Counter64,
      pr1645v2Lan2FGVlanInPQsPacketsDropped
         Counter64,
      pr1645v2Lan2FGVlanInPQsPacketsRedDropped
         Counter64,
      pr1645v2Lan2FGVlanInPQsPacketsCirTx
         Counter64,
      pr1645v2Lan2FGVlanInPQsPacketsEirTx
         Counter64,
      pr1645v2Lan2FGVlanInPQsPacketsViolateTx
         Counter64,
      pr1645v2Lan2FGVlanInPQsOctetsTotal
         Counter64,
      pr1645v2Lan2FGVlanInPQsOctetsDirectTx
         Counter64,
      pr1645v2Lan2FGVlanInPQsOctetsQueued
         Counter64,
      pr1645v2Lan2FGVlanInPQsOctetsDropped
         Counter64,
      pr1645v2Lan2FGVlanInPQsOctetsRedDropped
         Counter64,
      pr1645v2Lan2FGVlanInPQsOctetsCirTx
         Counter64,
      pr1645v2Lan2FGVlanInPQsOctetsEirTx
         Counter64,
      pr1645v2Lan2FGVlanInPQsOctetsViolateTx
         Counter64,
      pr1645v2Lan2FGVlanInPQsOctetsBandwidth15sec
         Integer32,
      pr1645v2Lan2FGVlanInPQsOctetsBandwidth30sec
         Integer32,
      pr1645v2Lan2FGVlanInPQsOctetsBandwidth1min
         Integer32,
      pr1645v2Lan2FGVlanInPQsOctetsBandwidth2min
         Integer32,
      pr1645v2Lan2FGVlanInPQsOctetsBandwidth5min
         Integer32
      }

pr1645v2Lan2FGVlanInPQsTableIx OBJECT-TYPE
   SYNTAX      TableIndex
   MAX-ACCESS  not-accessible
   STATUS      current
   DESCRIPTION
      ""
   ::= {pr1645v2Lan2FGVlanInPQsEntry 11}

pr1645v2Lan2FGVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGVlanInPQsEntry 16777216}

pr1645v2Lan2FGVlanInPQsLength OBJECT-TYPE
   SYNTAX      Integer32
   MAX-ACCESS  read-only
   STATUS      current
   DESCRIPTION
      "Path: ethernet2.performance.vlan.inPriorityQueues.length"
   ::= {pr1645v2Lan2FGVlanInPQsEntry 33554432}

pr1645v2Lan2FGVlanInPQsOctetLength OBJECT-TYPE
   SYNTAX      Integer32
   MAX-ACCESS  read-only
   STATUS      current
   DESCRIPTION
      "Path: ethernet2.performance.vlan.inPriorityQueues.octetLength"
   ::= {pr1645v2Lan2FGVlanInPQsEntry 150994944}

pr1645v2Lan2FGVlanInPQsRedLength OBJECT-TYPE
   SYNTAX      Integer32
   MAX-ACCESS  read-only
   STATUS      current
   DESCRIPTION
      "Path: ethernet2.performance.vlan.inPriorityQueues.redLength"
   ::= {pr1645v2Lan2FGVlanInPQsEntry 134217728}

pr1645v2Lan2FGVlanInPQsPacketsTotal OBJECT-TYPE
   SYNTAX      Counter64
   MAX-ACCESS  read-only
   STATUS      current
   DESCRIPTION
      "Path: ethernet2.performance.vlan.inPriorityQueues.packets.total

       64 bit unsigned wrappable counter."
   ::= {pr1645v2Lan2FGVlanInPQsEntry 50790400}

pr1645v2Lan2FGVlanInPQsPacketsDirectTx OBJECT-TYPE
   SYNTAX      Counter64
   MAX-ACCESS  read-only
   STATUS      current
   DESCRIPTION
      "Path: ethernet2.performance.vlan.inPriorityQueues.packets.directTx

       64 bit unsigned wrappable counter."
   ::= {pr1645v2Lan2FGVlanInPQsEntry 50397184}

pr1645v2Lan2FGVlanInPQsPacketsQueued OBJECT-TYPE
   SYNTAX      Counter64
   MAX-ACCESS  read-only
   STATUS      current
   DESCRIPTION
      "Path: ethernet2.performance.vlan.inPriorityQueues.packets.queued

       64 bit unsigned wrappable counter."
   ::= {pr1645v2Lan2FGVlanInPQsEntry 50462720}

pr1645v2Lan2FGVlanInPQsPacketsDropped OBJECT-TYPE
   SYNTAX      Counter64
   MAX-ACCESS  read-only
   STATUS      current
   DESCRIPTION
      "Path: ethernet2.performance.vlan.inPriorityQueues.packets.dropped

       64 bit unsigned wrappable counter."
   ::= {pr1645v2Lan2FGVlanInPQsEntry 50528256}

pr1645v2Lan2FGVlanInPQsPacketsRedDropped OBJECT-TYPE
   SYNTAX      Counter64
   MAX-ACCESS  read-only
   STATUS      current
   DESCRIPTION
      "Path: ethernet2.performance.vlan.inPriorityQueues.packets.redDropped

       64 bit unsigned wrappable counter."
   ::= {pr1645v2Lan2FGVlanInPQsEntry 50724864}

pr1645v2Lan2FGVlanInPQsPacketsCirTx OBJECT-TYPE
   SYNTAX      Counter64
   MAX-ACCESS  read-only
   STATUS      current
   DESCRIPTION
      "Path: ethernet2.performance.vlan.inPriorityQueues.packets.cirTx

       64 bit unsigned wrappable counter."
   ::= {pr1645v2Lan2FGVlanInPQsEntry 50593792}

pr1645v2Lan2FGVlanInPQsPacketsEirTx OBJECT-TYPE
   SYNTAX      Counter64
   MAX-ACCESS  read-only
   STATUS      current
   DESCRIPTION
      "Path: ethernet2.performance.vlan.inPriorityQueues.packets.eirTx

       64 bit unsigned wrappable counter."
   ::= {pr1645v2Lan2FGVlanInPQsEntry 50659328}

pr1645v2Lan2FGVlanInPQsPacketsViolateTx OBJECT-TYPE
   SYNTAX      Counter64
   MAX-ACCESS  read-only
   STATUS      current
   DESCRIPTION
      "Path: ethernet2.performance.vlan.inPriorityQueues.packets.violateTx

       64 bit unsigned wrappable counter."
   ::= {pr1645v2Lan2FGVlanInPQsEntry 50855936}

pr1645v2Lan2FGVlanInPQsOctetsTotal OBJECT-TYPE
   SYNTAX      Counter64
   MAX-ACCESS  read-only
   STATUS      current
   DESCRIPTION
      "Path: ethernet2.performance.vlan.inPriorityQueues.octets.total

       64 bit unsigned wrappable counter."
   ::= {pr1645v2Lan2FGVlanInPQsEntry 67567616}

pr1645v2Lan2FGVlanInPQsOctetsDirectTx OBJECT-TYPE
   SYNTAX      Counter64
   MAX-ACCESS  read-only
   STATUS      current
   DESCRIPTION
      "Path: ethernet2.performance.vlan.inPriorityQueues.octets.directTx

       64 bit unsigned wrappable counter."
   ::= {pr1645v2Lan2FGVlanInPQsEntry 67174400}

pr1645v2Lan2FGVlanInPQsOctetsQueued OBJECT-TYPE
   SYNTAX      Counter64
   MAX-ACCESS  read-only
   STATUS      current
   DESCRIPTION
      "Path: ethernet2.performance.vlan.inPriorityQueues.octets.queued

       64 bit unsigned wrappable counter."
   ::= {pr1645v2Lan2FGVlanInPQsEntry 67239936}

pr1645v2Lan2FGVlanInPQsOctetsDropped OBJECT-TYPE
   SYNTAX      Counter64
   MAX-ACCESS  read-only
   STATUS      current
   DESCRIPTION
      "Path: ethernet2.performance.vlan.inPriorityQueues.octets.dropped

       64 bit unsigned wrappable counter."
   ::= {pr1645v2Lan2FGVlanInPQsEntry 67305472}

pr1645v2Lan2FGVlanInPQsOctetsRedDropped OBJECT-TYPE
   SYNTAX      Counter64
   MAX-ACCESS  read-only
   STATUS      current
   DESCRIPTION
      "Path: ethernet2.performance.vlan.inPriorityQueues.octets.redDropped

       64 bit unsigned wrappable counter."
   ::= {pr1645v2Lan2FGVlanInPQsEntry 67502080}

pr1645v2Lan2FGVlanInPQsOctetsCirTx OBJECT-TYPE
   SYNTAX      Counter64
   MAX-ACCESS  read-only
   STATUS      current
   DESCRIPTION
      "Path: ethernet2.performance.vlan.inPriorityQueues.octets.cirTx

       64 bit unsigned wrappable counter."
   ::= {pr1645v2Lan2FGVlanInPQsEntry 67371008}

pr1645v2Lan2FGVlanInPQsOctetsEirTx OBJECT-TYPE
   SYNTAX      Counter64
   MAX-ACCESS  read-only
   STATUS      current
   DESCRIPTION
      "Path: ethernet2.performance.vlan.inPriorityQueues.octets.eirTx

       64 bit unsigned wrappable counter."
   ::= {pr1645v2Lan2FGVlanInPQsEntry 67436544}

pr1645v2Lan2FGVlanInPQsOctetsViolateTx OBJECT-TYPE
   SYNTAX      Counter64
   MAX-ACCESS  read-only
   STATUS      current
   DESCRIPTION
      "Path: ethernet2.performance.vlan.inPriorityQueues.octets.violateTx

       64 bit unsigned wrappable counter."
   ::= {pr1645v2Lan2FGVlanInPQsEntry 67633152}

pr1645v2Lan2FGVlanInPQsOctetsBandwidth15sec OBJECT-TYPE
   SYNTAX      Integer32
   MAX-ACCESS  read-only
   STATUS      current
   DESCRIPTION
      "Path: ethernet2.performance.vlan.inPriorityQueues.octets.bandwidth.15sec

       unit name = bps
       formula = 8 * ; 8 /"
   ::= {pr1645v2Lan2FGVlanInPQsEntry 70386944}

pr1645v2Lan2FGVlanInPQsOctetsBandwidth30sec OBJECT-TYPE
   SYNTAX      Integer32
   MAX-ACCESS  read-only
   STATUS      current
   DESCRIPTION
      "Path: ethernet2.performance.vlan.inPriorityQueues.octets.bandwidth.30sec

       unit name = bps
       formula = 8 * ; 8 /"
   ::= {pr1645v2Lan2FGVlanInPQsEntry 70388224}

pr1645v2Lan2FGVlanInPQsOctetsBandwidth1min OBJECT-TYPE
   SYNTAX      Integer32
   MAX-ACCESS  read-only
   STATUS      current
   DESCRIPTION
      "Path: ethernet2.performance.vlan.inPriorityQueues.octets.bandwidth.1min

       unit name = bps
       formula = 8 * ; 8 /"
   ::= {pr1645v2Lan2FGVlanInPQsEntry 70390784}

pr1645v2Lan2FGVlanInPQsOctetsBandwidth2min OBJECT-TYPE
   SYNTAX      Integer32
   MAX-ACCESS  read-only
   STATUS      current
   DESCRIPTION
      "Path: ethernet2.performance.vlan.inPriorityQueues.octets.bandwidth.2min

       unit name = bps
       formula = 8 * ; 8 /"
   ::= {pr1645v2Lan2FGVlanInPQsEntry 70395904}

pr1645v2Lan2FGVlanInPQsOctetsBandwidth5min OBJECT-TYPE
   SYNTAX      Integer32
   MAX-ACCESS  read-only
   STATUS      current
   DESCRIPTION
      "Path: ethernet2.performance.vlan.inPriorityQueues.octets.bandwidth.5min

       unit name = bps
       formula = 8 * ; 8 /"
   ::= {pr1645v2Lan2FGVlanInPQsEntry 70411264}

pr1645v2Lan2FGVlanInPQsH2Performance OBJECT-TYPE
   SYNTAX      SEQUENCE OF Pr1645v2Lan2FGVlanInPQsH2PerformanceEntry
   MAX-ACCESS  not-accessible
   STATUS      current
   DESCRIPTION
      ""
   ::= {pr1645v2Lan2FGVlan 100990976}

pr1645v2Lan2FGVlanInPQsH2PerformanceEntry OBJECT-TYPE
   SYNTAX      Pr1645v2Lan2FGVlanInPQsH2PerformanceEntry
   MAX-ACCESS  not-accessible
   STATUS      current
   DESCRIPTION
      ""
   INDEX      { pr1645v2Lan2FGVlanTableIx,
                pr1645v2Lan2FGVlanInPQsTableIx,
                pr1645v2Lan2FGVlanInPQsH2PerformanceTableIx }
   ::= {pr1645v2Lan2FGVlanInPQsH2Performance 1}

Pr1645v2Lan2FGVlanInPQsH2PerformanceEntry ::=
   SEQUENCE
      {
      pr1645v2Lan2FGVlanInPQsH2PerformanceTableIx
         TableIndex,
      pr1645v2Lan2FGVlanInPQsH2PerformanceSysUpTime
         TimeTicks,
      pr1645v2Lan2FGVlanInPQsH2PerformanceTotPkts
         Counter64,
      pr1645v2Lan2FGVlanInPQsH2PerformanceDirTxPkts
         Counter64,
      pr1645v2Lan2FGVlanInPQsH2PerformanceQdPkts
         Counter64,
      pr1645v2Lan2FGVlanInPQsH2PerformanceDropPkts
         Counter64,
      pr1645v2Lan2FGVlanInPQsH2PerformanceRDropPkts
         Counter64,
      pr1645v2Lan2FGVlanInPQsH2PerformanceCirTxPkts
         Counter64,
      pr1645v2Lan2FGVlanInPQsH2PerformanceEirTxPkts
         Counter64,
      pr1645v2Lan2FGVlanInPQsH2PerformanceViolTxPkts
         Counter64,
      pr1645v2Lan2FGVlanInPQsH2PerformanceTotOcts
         Counter64,
      pr1645v2Lan2FGVlanInPQsH2PerformanceDirTxOcts
         Counter64,
      pr1645v2Lan2FGVlanInPQsH2PerformanceQdOcts
         Counter64,
      pr1645v2Lan2FGVlanInPQsH2PerformanceDropOcts
         Counter64,
      pr1645v2Lan2FGVlanInPQsH2PerformanceRDropOcts
         Counter64,
      pr1645v2Lan2FGVlanInPQsH2PerformanceCirTxOcts
         Counter64,
      pr1645v2Lan2FGVlanInPQsH2PerformanceEirTxOcts
         Counter64,
      pr1645v2Lan2FGVlanInPQsH2PerformanceViolTxOcts
         Counter64,
      pr1645v2Lan2FGVlanInPQsH2PerformanceBandwidth
         Integer32
      }

pr1645v2Lan2FGVlanInPQsH2PerformanceTableIx OBJECT-TYPE
   SYNTAX      TableIndex
   MAX-ACCESS  not-accessible
   STATUS      current
   DESCRIPTION
      ""
   ::= {pr1645v2Lan2FGVlanInPQsH2PerformanceEntry 11}

pr1645v2Lan2FGVlanInPQsH2PerformanceSysUpTime OBJECT-TYPE
   SYNTAX      TimeTicks
   MAX-ACCESS  read-only
   STATUS      current
   DESCRIPTION
      "Path: ethernet2.performance.vlan.inPriorityQueues.h2Performance.sysUpTime

       Time in centi-second."
   ::= {pr1645v2Lan2FGVlanInPQsH2PerformanceEntry 16777216}

pr1645v2Lan2FGVlanInPQsH2PerformanceTotPkts OBJECT-TYPE
   SYNTAX      Counter64
   MAX-ACCESS  read-only
   STATUS      current
   DESCRIPTION
      "Path: ethernet2.performance.vlan.inPriorityQueues.h2Performance.totalPkts

       64 bit unsigned wrappable counter."
   ::= {pr1645v2Lan2FGVlanInPQsH2PerformanceEntry 234881024}

pr1645v2Lan2FGVlanInPQsH2PerformanceDirTxPkts OBJECT-TYPE
   SYNTAX      Counter64
   MAX-ACCESS  read-only
   STATUS      current
   DESCRIPTION
      "Path: ethernet2.performance.vlan.inPriorityQueues.h2Performance.directTxPkts

       64 bit unsigned wrappable counter."
   ::= {pr1645v2Lan2FGVlanInPQsH2PerformanceEntry 33554432}

pr1645v2Lan2FGVlanInPQsH2PerformanceQdPkts OBJECT-TYPE
   SYNTAX      Counter64
   MAX-ACCESS  read-only
   STATUS      current
   DESCRIPTION
      "Path: ethernet2.performance.vlan.inPriorityQueues.h2Performance.queuedPkts

       64 bit unsigned wrappable counter."
   ::= {pr1645v2Lan2FGVlanInPQsH2PerformanceEntry 50331648}

pr1645v2Lan2FGVlanInPQsH2PerformanceDropPkts OBJECT-TYPE
   SYNTAX      Counter64
   MAX-ACCESS  read-only
   STATUS      current
   DESCRIPTION
      "Path: ethernet2.performance.vlan.inPriorityQueues.h2Performance.droppedPkts

       64 bit unsigned wrappable counter."
   ::= {pr1645v2Lan2FGVlanInPQsH2PerformanceEntry 67108864}

pr1645v2Lan2FGVlanInPQsH2PerformanceRDropPkts OBJECT-TYPE
   SYNTAX      Counter64
   MAX-ACCESS  read-only
   STATUS      current
   DESCRIPTION
      "Path: ethernet2.performance.vlan.inPriorityQueues.h2Performance.redDroppedPkts

       64 bit unsigned wrappable counter."
   ::= {pr1645v2Lan2FGVlanInPQsH2PerformanceEntry 201326592}

pr1645v2Lan2FGVlanInPQsH2PerformanceCirTxPkts OBJECT-TYPE
   SYNTAX      Counter64
   MAX-ACCESS  read-only
   STATUS      current
   DESCRIPTION
      "Path: ethernet2.performance.vlan.inPriorityQueues.h2Performance.cirTxPkts

       64 bit unsigned wrappable counter."
   ::= {pr1645v2Lan2FGVlanInPQsH2PerformanceEntry 83886080}

pr1645v2Lan2FGVlanInPQsH2PerformanceEirTxPkts OBJECT-TYPE
   SYNTAX      Counter64
   MAX-ACCESS  read-only
   STATUS      current
   DESCRIPTION
      "Path: ethernet2.performance.vlan.inPriorityQueues.h2Performance.eirTxPkts

       64 bit unsigned wrappable counter."
   ::= {pr1645v2Lan2FGVlanInPQsH2PerformanceEntry 100663296}

pr1645v2Lan2FGVlanInPQsH2PerformanceViolTxPkts OBJECT-TYPE
   SYNTAX      Counter64
   MAX-ACCESS  read-only
   STATUS      current
   DESCRIPTION
      "Path: ethernet2.performance.vlan.inPriorityQueues.h2Performance.violateTxPkts

       64 bit unsigned wrappable counter."
   ::= {pr1645v2Lan2FGVlanInPQsH2PerformanceEntry 301989888}

pr1645v2Lan2FGVlanInPQsH2PerformanceTotOcts OBJECT-TYPE
   SYNTAX      Counter64
   MAX-ACCESS  read-only
   STATUS      current
   DESCRIPTION
      "Path: ethernet2.performance.vlan.inPriorityQueues.h2Performance.totalOctets

       64 bit unsigned wrappable counter."
   ::= {pr1645v2Lan2FGVlanInPQsH2PerformanceEntry 251658240}

pr1645v2Lan2FGVlanInPQsH2PerformanceDirTxOcts OBJECT-TYPE
   SYNTAX      Counter64
   MAX-ACCESS  read-only
   STATUS      current
   DESCRIPTION
      "Path: ethernet2.performance.vlan.inPriorityQueues.h2Performance.directTxOctets

       64 bit unsigned wrappable counter."
   ::= {pr1645v2Lan2FGVlanInPQsH2PerformanceEntry 117440512}

pr1645v2Lan2FGVlanInPQsH2PerformanceQdOcts OBJECT-TYPE
   SYNTAX      Counter64
   MAX-ACCESS  read-only
   STATUS      current
   DESCRIPTION
      "Path: ethernet2.performance.vlan.inPriorityQueues.h2Performance.queuedOctets

       64 bit unsigned wrappable counter."
   ::= {pr1645v2Lan2FGVlanInPQsH2PerformanceEntry 134217728}

pr1645v2Lan2FGVlanInPQsH2PerformanceDropOcts OBJECT-TYPE
   SYNTAX      Counter64
   MAX-ACCESS  read-only
   STATUS      current
   DESCRIPTION
      "Path: ethernet2.performance.vlan.inPriorityQueues.h2Performance.droppedOctets

       64 bit unsigned wrappable counter."
   ::= {pr1645v2Lan2FGVlanInPQsH2PerformanceEntry 150994944}

pr1645v2Lan2FGVlanInPQsH2PerformanceRDropOcts OBJECT-TYPE
   SYNTAX      Counter64
   MAX-ACCESS  read-only
   STATUS      current
   DESCRIPTION
      "Path: ethernet2.performance.vlan.inPriorityQueues.h2Performance.redDroppedOctets

       64 bit unsigned wrappable counter."
   ::= {pr1645v2Lan2FGVlanInPQsH2PerformanceEntry 218103808}

pr1645v2Lan2FGVlanInPQsH2PerformanceCirTxOcts OBJECT-TYPE
   SYNTAX      Counter64
   MAX-ACCESS  read-only
   STATUS      current
   DESCRIPTION
      "Path: ethernet2.performance.vlan.inPriorityQueues.h2Performance.cirTxOctets

       64 bit unsigned wrappable counter."
   ::= {pr1645v2Lan2FGVlanInPQsH2PerformanceEntry 167772160}

pr1645v2Lan2FGVlanInPQsH2PerformanceEirTxOcts OBJECT-TYPE
   SYNTAX      Counter64
   MAX-ACCESS  read-only
   STATUS      current
   DESCRIPTION
      "Path: ethernet2.performance.vlan.inPriorityQueues.h2Performance.eirTxOctets

       64 bit unsigned wrappable counter."
   ::= {pr1645v2Lan2FGVlanInPQsH2PerformanceEntry 184549376}

pr1645v2Lan2FGVlanInPQsH2PerformanceViolTxOcts OBJECT-TYPE
   SYNTAX      Counter64
   MAX-ACCESS  read-only
   STATUS      current
   DESCRIPTION
      "Path: ethernet2.performance.vlan.inPriorityQueues.h2Performance.violateTxOctets

       64 bit unsigned wrappable counter."
   ::= {pr1645v2Lan2FGVlanInPQsH2PerformanceEntry 318767104}

pr1645v2Lan2FGVlanInPQsH2PerformanceBandwidth OBJECT-TYPE
   SYNTAX      Integer32
   MAX-ACCESS  read-only
   STATUS      current
   DESCRIPTION
      "Path: ethernet2.performance.vlan.inPriorityQueues.h2Performance.bandwidth

       unit name = bps
       formula = 8 * ; 8 /"
   ::= {pr1645v2Lan2FGVlanInPQsH2PerformanceEntry 268435456}

pr1645v2Lan2FGVlanInPQsH24Performance OBJECT-TYPE
   SYNTAX      SEQUENCE OF Pr1645v2Lan2FGVlanInPQsH24PerformanceEntry
   MAX-ACCESS  not-accessible
   STATUS      current
   DESCRIPTION
      ""
   ::= {pr1645v2Lan2FGVlan 101056512}

pr1645v2Lan2FGVlanInPQsH24PerformanceEntry OBJECT-TYPE
   SYNTAX      Pr1645v2Lan2FGVlanInPQsH24PerformanceEntry
   MAX-ACCESS  not-accessible
   STATUS      current
   DESCRIPTION
      ""
   INDEX      { pr1645v2Lan2FGVlanTableIx,
                pr1645v2Lan2FGVlanInPQsTableIx,
                pr1645v2Lan2FGVlanInPQsH24PerformanceTableIx }
   ::= {pr1645v2Lan2FGVlanInPQsH24Performance 1}

Pr1645v2Lan2FGVlanInPQsH24PerformanceEntry ::=
   SEQUENCE
      {
      pr1645v2Lan2FGVlanInPQsH24PerformanceTableIx
         TableIndex,
      pr1645v2Lan2FGVlanInPQsH24PerformanceSysUpTime
         TimeTicks,
      pr1645v2Lan2FGVlanInPQsH24PerformanceTotPkts
         Counter64,
      pr1645v2Lan2FGVlanInPQsH24PerformanceDirTxPkts
         Counter64,
      pr1645v2Lan2FGVlanInPQsH24PerformanceQdPkts
         Counter64,
      pr1645v2Lan2FGVlanInPQsH24PerformanceDropPkts
         Counter64,
      pr1645v2Lan2FGVlanInPQsH24PerformanceRDropPkts
         Counter64,
      pr1645v2Lan2FGVlanInPQsH24PerformanceCirTxPkts
         Counter64,
      pr1645v2Lan2FGVlanInPQsH24PerformanceEirTxPkts
         Counter64,
      pr1645v2Lan2FGVlanInPQsH24PerformanceViolTxPkts
         Counter64,
      pr1645v2Lan2FGVlanInPQsH24PerformanceTotOcts
         Counter64,
      pr1645v2Lan2FGVlanInPQsH24PerformanceDirTxOcts
         Counter64,
      pr1645v2Lan2FGVlanInPQsH24PerformanceQdOcts
         Counter64,
      pr1645v2Lan2FGVlanInPQsH24PerformanceDropOcts
         Counter64,
      pr1645v2Lan2FGVlanInPQsH24PerformanceRDropOcts
         Counter64,
      pr1645v2Lan2FGVlanInPQsH24PerformanceCirTxOcts
         Counter64,
      pr1645v2Lan2FGVlanInPQsH24PerformanceEirTxOcts
         Counter64,
      pr1645v2Lan2FGVlanInPQsH24PerformanceViolTxOcts
         Counter64,
      pr1645v2Lan2FGVlanInPQsH24PerformanceBandwidth
         Integer32
      }

pr1645v2Lan2FGVlanInPQsH24PerformanceTableIx OBJECT-TYPE
   SYNTAX      TableIndex
   MAX-ACCESS  not-accessible
   STATUS      current
   DESCRIPTION
      ""
   ::= {pr1645v2Lan2FGVlanInPQsH24PerformanceEntry 11}

pr1645v2Lan2FGVlanInPQsH24PerformanceSysUpTime OBJECT-TYPE
   SYNTAX      TimeTicks
   MAX-ACCESS  read-only
   STATUS      current
   DESCRIPTION
      "Path: ethernet2.performance.vlan.inPriorityQueues.h24Performance.sysUpTime

       Time in centi-second."
   ::= {pr1645v2Lan2FGVlanInPQsH24PerformanceEntry 16777216}

pr1645v2Lan2FGVlanInPQsH24PerformanceTotPkts OBJECT-TYPE
   SYNTAX      Counter64
   MAX-ACCESS  read-only
   STATUS      current
   DESCRIPTION
      "Path: ethernet2.performance.vlan.inPriorityQueues.h24Performance.totalPkts

       64 bit unsigned wrappable counter."
   ::= {pr1645v2Lan2FGVlanInPQsH24PerformanceEntry 234881024}

pr1645v2Lan2FGVlanInPQsH24PerformanceDirTxPkts OBJECT-TYPE
   SYNTAX      Counter64
   MAX-ACCESS  read-only
   STATUS      current
   DESCRIPTION
      "Path: ethernet2.performance.vlan.inPriorityQueues.h24Performance.directTxPkts

       64 bit unsigned wrappable counter."
   ::= {pr1645v2Lan2FGVlanInPQsH24PerformanceEntry 33554432}

pr1645v2Lan2FGVlanInPQsH24PerformanceQdPkts OBJECT-TYPE
   SYNTAX      Counter64
   MAX-ACCESS  read-only
   STATUS      current
   DESCRIPTION
      "Path: ethernet2.performance.vlan.inPriorityQueues.h24Performance.queuedPkts

       64 bit unsigned wrappable counter."
   ::= {pr1645v2Lan2FGVlanInPQsH24PerformanceEntry 50331648}

pr1645v2Lan2FGVlanInPQsH24PerformanceDropPkts OBJECT-TYPE
   SYNTAX      Counter64
   MAX-ACCESS  read-only
   STATUS      current
   DESCRIPTION
      "Path: ethernet2.performance.vlan.inPriorityQueues.h24Performance.droppedPkts

       64 bit unsigned wrappable counter."
   ::= {pr1645v2Lan2FGVlanInPQsH24PerformanceEntry 67108864}

pr1645v2Lan2FGVlanInPQsH24PerformanceRDropPkts OBJECT-TYPE
   SYNTAX      Counter64
   MAX-ACCESS  read-only
   STATUS      current
   DESCRIPTION
      "Path: ethernet2.performance.vlan.inPriorityQueues.h24Performance.redDroppedPkts

       64 bit unsigned wrappable counter."
   ::= {pr1645v2Lan2FGVlanInPQsH24PerformanceEntry 201326592}

pr1645v2Lan2FGVlanInPQsH24PerformanceCirTxPkts OBJECT-TYPE
   SYNTAX      Counter64
   MAX-ACCESS  read-only
   STATUS      current
   DESCRIPTION
      "Path: ethernet2.performance.vlan.inPriorityQueues.h24Performance.cirTxPkts

       64 bit unsigned wrappable counter."
   ::= {pr1645v2Lan2FGVlanInPQsH24PerformanceEntry 83886080}

pr1645v2Lan2FGVlanInPQsH24PerformanceEirTxPkts OBJECT-TYPE
   SYNTAX      Counter64
   MAX-ACCESS  read-only
   STATUS      current
   DESCRIPTION
      "Path: ethernet2.performance.vlan.inPriorityQueues.h24Performance.eirTxPkts

       64 bit unsigned wrappable counter."
   ::= {pr1645v2Lan2FGVlanInPQsH24PerformanceEntry 100663296}

pr1645v2Lan2FGVlanInPQsH24PerformanceViolTxPkts OBJECT-TYPE
   SYNTAX      Counter64
   MAX-ACCESS  read-only
   STATUS      current
   DESCRIPTION
      "Path: ethernet2.performance.vlan.inPriorityQueues.h24Performance.violateTxPkts

       64 bit unsigned wrappable counter."
   ::= {pr1645v2Lan2FGVlanInPQsH24PerformanceEntry 301989888}

pr1645v2Lan2FGVlanInPQsH24PerformanceTotOcts OBJECT-TYPE
   SYNTAX      Counter64
   MAX-ACCESS  read-only
   STATUS      current
   DESCRIPTION
      "Path: ethernet2.performance.vlan.inPriorityQueues.h24Performance.totalOctets

       64 bit unsigned wrappable counter."
   ::= {pr1645v2Lan2FGVlanInPQsH24PerformanceEntry 251658240}

pr1645v2Lan2FGVlanInPQsH24PerformanceDirTxOcts OBJECT-TYPE
   SYNTAX      Counter64
   MAX-ACCESS  read-only
   STATUS      current
   DESCRIPTION
      "Path: ethernet2.performance.vlan.inPriorityQueues.h24Performance.directTxOctets

       64 bit unsigned wrappable counter."
   ::= {pr1645v2Lan2FGVlanInPQsH24PerformanceEntry 117440512}

pr1645v2Lan2FGVlanInPQsH24PerformanceQdOcts OBJECT-TYPE
   SYNTAX      Counter64
   MAX-ACCESS  read-only
   STATUS      current
   DESCRIPTION
      "Path: ethernet2.performance.vlan.inPriorityQueues.h24Performance.queuedOctets

       64 bit unsigned wrappable counter."
   ::= {pr1645v2Lan2FGVlanInPQsH24PerformanceEntry 134217728}

pr1645v2Lan2FGVlanInPQsH24PerformanceDropOcts OBJECT-TYPE
   SYNTAX      Counter64
   MAX-ACCESS  read-only
   STATUS      current
   DESCRIPTION
      "Path: ethernet2.performance.vlan.inPriorityQueues.h24Performance.droppedOctets

       64 bit unsigned wrappable counter."
   ::= {pr1645v2Lan2FGVlanInPQsH24PerformanceEntry 150994944}

pr1645v2Lan2FGVlanInPQsH24PerformanceRDropOcts OBJECT-TYPE
   SYNTAX      Counter64
   MAX-ACCESS  read-only
   STATUS      current
   DESCRIPTION
      "Path: ethernet2.performance.vlan.inPriorityQueues.h24Performance.redDroppedOctets

       64 bit unsigned wrappable counter."
   ::= {pr1645v2Lan2FGVlanInPQsH24PerformanceEntry 218103808}

pr1645v2Lan2FGVlanInPQsH24PerformanceCirTxOcts OBJECT-TYPE
   SYNTAX      Counter64
   MAX-ACCESS  read-only
   STATUS      current
   DESCRIPTION
      "Path: ethernet2.performance.vlan.inPriorityQueues.h24Performance.cirTxOctets

       64 bit unsigned wrappable counter."
   ::= {pr1645v2Lan2FGVlanInPQsH24PerformanceEntry 167772160}

pr1645v2Lan2FGVlanInPQsH24PerformanceEirTxOcts OBJECT-TYPE
   SYNTAX      Counter64
   MAX-ACCESS  read-only
   STATUS      current
   DESCRIPTION
      "Path: ethernet2.performance.vlan.inPriorityQueues.h24Performance.eirTxOctets

       64 bit unsigned wrappable counter."
   ::= {pr1645v2Lan2FGVlanInPQsH24PerformanceEntry 184549376}

pr1645v2Lan2FGVlanInPQsH24PerformanceViolTxOcts OBJECT-TYPE
   SYNTAX      Counter64
   MAX-ACCESS  read-only
   STATUS      current
   DESCRIPTION
      "Path: ethernet2.performance.vlan.inPriorityQueues.h24Performance.violateTxOctets

       64 bit unsigned wrappable counter."
   ::= {pr1645v2Lan2FGVlanInPQsH24PerformanceEntry 318767104}

pr1645v2Lan2FGVlanInPQsH24PerformanceBandwidth OBJECT-TYPE
   SYNTAX      Integer32
   MAX-ACCESS  read-only
   STATUS      current
   DESCRIPTION
      "Path: ethernet2.performance.vlan.inPriorityQueues.h24Performance.bandwidth

       unit name = bps
       formula = 8 * ; 8 /"
   ::= {pr1645v2Lan2FGVlanInPQsH24PerformanceEntry 268435456}

pr1645v2Lan2FGVlanInPQsD7Performance OBJECT-TYPE
   SYNTAX      SEQUENCE OF Pr1645v2Lan2FGVlanInPQsD7PerformanceEntry
   MAX-ACCESS  not-accessible
   STATUS      current
   DESCRIPTION
      ""
   ::= {pr1645v2Lan2FGVlan 101122048}

pr1645v2Lan2FGVlanInPQsD7PerformanceEntry OBJECT-TYPE
   SYNTAX      Pr1645v2Lan2FGVlanInPQsD7PerformanceEntry
   MAX-ACCESS  not-accessible
   STATUS      current
   DESCRIPTION
      ""
   INDEX      { pr1645v2Lan2FGVlanTableIx,
                pr1645v2Lan2FGVlanInPQsTableIx,
                pr1645v2Lan2FGVlanInPQsD7PerformanceTableIx }
   ::= {pr1645v2Lan2FGVlanInPQsD7Performance 1}

Pr1645v2Lan2FGVlanInPQsD7PerformanceEntry ::=
   SEQUENCE
      {
      pr1645v2Lan2FGVlanInPQsD7PerformanceTableIx
         TableIndex,
      pr1645v2Lan2FGVlanInPQsD7PerformanceSysUpTime
         TimeTicks,
      pr1645v2Lan2FGVlanInPQsD7PerformanceTotPkts
         Counter64,
      pr1645v2Lan2FGVlanInPQsD7PerformanceDirTxPkts
         Counter64,
      pr1645v2Lan2FGVlanInPQsD7PerformanceQdPkts
         Counter64,
      pr1645v2Lan2FGVlanInPQsD7PerformanceDropPkts
         Counter64,
      pr1645v2Lan2FGVlanInPQsD7PerformanceRDropPkts
         Counter64,
      pr1645v2Lan2FGVlanInPQsD7PerformanceCirTxPkts
         Counter64,
      pr1645v2Lan2FGVlanInPQsD7PerformanceEirTxPkts
         Counter64,
      pr1645v2Lan2FGVlanInPQsD7PerformanceViolTxPkts
         Counter64,
      pr1645v2Lan2FGVlanInPQsD7PerformanceTotOcts
         Counter64,
      pr1645v2Lan2FGVlanInPQsD7PerformanceDirTxOcts
         Counter64,
      pr1645v2Lan2FGVlanInPQsD7PerformanceQdOcts
         Counter64,
      pr1645v2Lan2FGVlanInPQsD7PerformanceDropOcts
         Counter64,
      pr1645v2Lan2FGVlanInPQsD7PerformanceRDropOcts
         Counter64,
      pr1645v2Lan2FGVlanInPQsD7PerformanceCirTxOcts
         Counter64,
      pr1645v2Lan2FGVlanInPQsD7PerformanceEirTxOcts
         Counter64,
      pr1645v2Lan2FGVlanInPQsD7PerformanceViolTxOcts
         Counter64,
      pr1645v2Lan2FGVlanInPQsD7PerformanceBandwidth
         Integer32
      }

pr1645v2Lan2FGVlanInPQsD7PerformanceTableIx OBJECT-TYPE
   SYNTAX      TableIndex
   MAX-ACCESS  not-accessible
   STATUS      current
   DESCRIPTION
      ""
   ::= {pr1645v2Lan2FGVlanInPQsD7PerformanceEntry 11}

pr1645v2Lan2FGVlanInPQsD7PerformanceSysUpTime OBJECT-TYPE
   SYNTAX      TimeTicks
   MAX-ACCESS  read-only
   STATUS      current
   DESCRIPTION
      "Path: ethernet2.performance.vlan.inPriorityQueues.d7Performance.sysUpTime

       Time in centi-second."
   ::= {pr1645v2Lan2FGVlanInPQsD7PerformanceEntry 16777216}

pr1645v2Lan2FGVlanInPQsD7PerformanceTotPkts OBJECT-TYPE
   SYNTAX      Counter64
   MAX-ACCESS  read-only
   STATUS      current
   DESCRIPTION
      "Path: ethernet2.performance.vlan.inPriorityQueues.d7Performance.totalPkts

       64 bit unsigned wrappable counter."
   ::= {pr1645v2Lan2FGVlanInPQsD7PerformanceEntry 234881024}

pr1645v2Lan2FGVlanInPQsD7PerformanceDirTxPkts OBJECT-TYPE
   SYNTAX      Counter64
   MAX-ACCESS  read-only
   STATUS      current
   DESCRIPTION
      "Path: ethernet2.performance.vlan.inPriorityQueues.d7Performance.directTxPkts

       64 bit unsigned wrappable counter."
   ::= {pr1645v2Lan2FGVlanInPQsD7PerformanceEntry 33554432}

pr1645v2Lan2FGVlanInPQsD7PerformanceQdPkts OBJECT-TYPE
   SYNTAX      Counter64
   MAX-ACCESS  read-only
   STATUS      current
   DESCRIPTION
      "Path: ethernet2.performance.vlan.inPriorityQueues.d7Performance.queuedPkts

       64 bit unsigned wrappable counter."
   ::= {pr1645v2Lan2FGVlanInPQsD7PerformanceEntry 50331648}

pr1645v2Lan2FGVlanInPQsD7PerformanceDropPkts OBJECT-TYPE
   SYNTAX      Counter64
   MAX-ACCESS  read-only
   STATUS      current
   DESCRIPTION
      "Path: ethernet2.performance.vlan.inPriorityQueues.d7Performance.droppedPkts

       64 bit unsigned wrappable counter."
   ::= {pr1645v2Lan2FGVlanInPQsD7PerformanceEntry 67108864}

pr1645v2Lan2FGVlanInPQsD7PerformanceRDropPkts OBJECT-TYPE
   SYNTAX      Counter64
   MAX-ACCESS  read-only
   STATUS      current
   DESCRIPTION
      "Path: ethernet2.performance.vlan.inPriorityQueues.d7Performance.redDroppedPkts

       64 bit unsigned wrappable counter."
   ::= {pr1645v2Lan2FGVlanInPQsD7PerformanceEntry 201326592}

pr1645v2Lan2FGVlanInPQsD7PerformanceCirTxPkts OBJECT-TYPE
   SYNTAX      Counter64
   MAX-ACCESS  read-only
   STATUS      current
   DESCRIPTION
      "Path: ethernet2.performance.vlan.inPriorityQueues.d7Performance.cirTxPkts

       64 bit unsigned wrappable counter."
   ::= {pr1645v2Lan2FGVlanInPQsD7PerformanceEntry 83886080}

pr1645v2Lan2FGVlanInPQsD7PerformanceEirTxPkts OBJECT-TYPE
   SYNTAX      Counter64
   MAX-ACCESS  read-only
   STATUS      current
   DESCRIPTION
      "Path: ethernet2.performance.vlan.inPriorityQueues.d7Performance.eirTxPkts

       64 bit unsigned wrappable counter."
   ::= {pr1645v2Lan2FGVlanInPQsD7PerformanceEntry 100663296}

pr1645v2Lan2FGVlanInPQsD7PerformanceViolTxPkts OBJECT-TYPE
   SYNTAX      Counter64
   MAX-ACCESS  read-only
   STATUS      current
   DESCRIPTION
      "Path: ethernet2.performance.vlan.inPriorityQueues.d7Performance.violateTxPkts

       64 bit unsigned wrappable counter."
   ::= {pr1645v2Lan2FGVlanInPQsD7PerformanceEntry 301989888}

pr1645v2Lan2FGVlanInPQsD7PerformanceTotOcts OBJECT-TYPE
   SYNTAX      Counter64
   MAX-ACCESS  read-only
   STATUS      current
   DESCRIPTION
      "Path: ethernet2.performance.vlan.inPriorityQueues.d7Performance.totalOctets

       64 bit unsigned wrappable counter."
   ::= {pr1645v2Lan2FGVlanInPQsD7PerformanceEntry 251658240}

pr1645v2Lan2FGVlanInPQsD7PerformanceDirTxOcts OBJECT-TYPE
   SYNTAX      Counter64
   MAX-ACCESS  read-only
   STATUS      current
   DESCRIPTION
      "Path: ethernet2.performance.vlan.inPriorityQueues.d7Performance.directTxOctets

       64 bit unsigned wrappable counter."
   ::= {pr1645v2Lan2FGVlanInPQsD7PerformanceEntry 117440512}

pr1645v2Lan2FGVlanInPQsD7PerformanceQdOcts OBJECT-TYPE
   SYNTAX      Counter64
   MAX-ACCESS  read-only
   STATUS      current
   DESCRIPTION
      "Path: ethernet2.performance.vlan.inPriorityQueues.d7Performance.queuedOctets

       64 bit unsigned wrappable counter."
   ::= {pr1645v2Lan2FGVlanInPQsD7PerformanceEntry 134217728}

pr1645v2Lan2FGVlanInPQsD7PerformanceDropOcts OBJECT-TYPE
   SYNTAX      Counter64
   MAX-ACCESS  read-only
   STATUS      current
   DESCRIPTION
      "Path: ethernet2.performance.vlan.inPriorityQueues.d7Performance.droppedOctets

       64 bit unsigned wrappable counter."
   ::= {pr1645v2Lan2FGVlanInPQsD7PerformanceEntry 150994944}

pr1645v2Lan2FGVlanInPQsD7PerformanceRDropOcts OBJECT-TYPE
   SYNTAX      Counter64
   MAX-ACCESS  read-only
   STATUS      current
   DESCRIPTION
      "Path: ethernet2.performance.vlan.inPriorityQueues.d7Performance.redDroppedOctets

       64 bit unsigned wrappable counter."
   ::= {pr1645v2Lan2FGVlanInPQsD7PerformanceEntry 218103808}

pr1645v2Lan2FGVlanInPQsD7PerformanceCirTxOcts OBJECT-TYPE
   SYNTAX      Counter64
   MAX-ACCESS  read-only
   STATUS      current
   DESCRIPTION
      "Path: ethernet2.performance.vlan.inPriorityQueues.d7Performance.cirTxOctets

       64 bit unsigned wrappable counter."
   ::= {pr1645v2Lan2FGVlanInPQsD7PerformanceEntry 167772160}

pr1645v2Lan2FGVlanInPQsD7PerformanceEirTxOcts OBJECT-TYPE
   SYNTAX      Counter64
   MAX-ACCESS  read-only
   STATUS      current
   DESCRIPTION
      "Path: ethernet2.performance.vlan.inPriorityQueues.d7Performance.eirTxOctets

       64 bit unsigned wrappable counter."
   ::= {pr1645v2Lan2FGVlanInPQsD7PerformanceEntry 184549376}

pr1645v2Lan2FGVlanInPQsD7PerformanceViolTxOcts OBJECT-TYPE
   SYNTAX      Counter64
   MAX-ACCESS  read-only
   STATUS      current
   DESCRIPTION
      "Path: ethernet2.performance.vlan.inPriorityQueues.d7Performance.violateTxOctets

       64 bit unsigned wrappable counter."
   ::= {pr1645v2Lan2FGVlanInPQsD7PerformanceEntry 318767104}

pr1645v2Lan2FGVlanInPQsD7PerformanceBandwidth OBJECT-TYPE
   SYNTAX      Integer32
   MAX-ACCESS  read-only
   STATUS      current
   DESCRIPTION
      "Path: ethernet2.performance.vlan.inPriorityQueues.d7Performance.bandwidth

       unit name = bps
       formula = 8 * ; 8 /"
   ::= {pr1645v2Lan2FGVlanInPQsD7PerformanceEntry 268435456}

pr1645v2Lan2FGVlanOutPQs OBJECT-TYPE
   SYNTAX      SEQUENCE OF Pr1645v2Lan2FGVlanOutPQsEntry
   MAX-ACCESS  not-accessible
   STATUS      current
   DESCRIPTION
      ""
   ::= {pr1645v2Lan2FGVlan 83886080}

pr1645v2Lan2FGVlanOutPQsEntry OBJECT-TYPE
   SYNTAX      Pr1645v2Lan2FGVlanOutPQsEntry
   MAX-ACCESS  not-accessible
   STATUS      current
   DESCRIPTION
      ""
   INDEX      { pr1645v2Lan2FGVlanTableIx,
                pr1645v2Lan2FGVlanOutPQsTableIx }
   ::= {pr1645v2Lan2FGVlanOutPQs 1}

Pr1645v2Lan2FGVlanOutPQsEntry ::=
   SEQUENCE
      {
      pr1645v2Lan2FGVlanOutPQsTableIx
         TableIndex,
      pr1645v2Lan2FGVlanOutPQsName
         INTEGER,
      pr1645v2Lan2FGVlanOutPQsLength
         Integer32,
      pr1645v2Lan2FGVlanOutPQsOctetLength
         Integer32,
      pr1645v2Lan2FGVlanOutPQsRedLength
         Integer32,
      pr1645v2Lan2FGVlanOutPQsPacketsTotal
         Counter64,
      pr1645v2Lan2FGVlanOutPQsPacketsDirectTx
         Counter64,
      pr1645v2Lan2FGVlanOutPQsPacketsQueued
         Counter64,
      pr1645v2Lan2FGVlanOutPQsPacketsDropped
         Counter64,
      pr1645v2Lan2FGVlanOutPQsPacketsRedDropped
         Counter64,
      pr1645v2Lan2FGVlanOutPQsPacketsCirTx
         Counter64,
      pr1645v2Lan2FGVlanOutPQsPacketsEirTx
         Counter64,
      pr1645v2Lan2FGVlanOutPQsPacketsViolateTx
         Counter64,
      pr1645v2Lan2FGVlanOutPQsOctetsTotal
         Counter64,
      pr1645v2Lan2FGVlanOutPQsOctetsDirectTx
         Counter64,
      pr1645v2Lan2FGVlanOutPQsOctetsQueued
         Counter64,
      pr1645v2Lan2FGVlanOutPQsOctetsDropped
         Counter64,
      pr1645v2Lan2FGVlanOutPQsOctetsRedDropped
         Counter64,
      pr1645v2Lan2FGVlanOutPQsOctetsCirTx
         Counter64,
      pr1645v2Lan2FGVlanOutPQsOctetsEirTx
         Counter64,
      pr1645v2Lan2FGVlanOutPQsOctetsViolateTx
         Counter64,
      pr1645v2Lan2FGVlanOutPQsOctetsBandwidth15sec
         Integer32,
      pr1645v2Lan2FGVlanOutPQsOctetsBandwidth30sec
         Integer32,
      pr1645v2Lan2FGVlanOutPQsOctetsBandwidth1min
         Integer32,
      pr1645v2Lan2FGVlanOutPQsOctetsBandwidth2min
         Integer32,
      pr1645v2Lan2FGVlanOutPQsOctetsBandwidth5min
         Integer32
      }

pr1645v2Lan2FGVlanOutPQsTableIx OBJECT-TYPE
   SYNTAX      TableIndex
   MAX-ACCESS  not-accessible
   STATUS      current
   DESCRIPTION
      ""
   ::= {pr1645v2Lan2FGVlanOutPQsEntry 11}

pr1645v2Lan2FGVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGVlanOutPQsEntry 16777216}

pr1645v2Lan2FGVlanOutPQsLength OBJECT-TYPE
   SYNTAX      Integer32
   MAX-ACCESS  read-only
   STATUS      current
   DESCRIPTION
      "Path: ethernet2.performance.vlan.outPriorityQueues.length"
   ::= {pr1645v2Lan2FGVlanOutPQsEntry 33554432}

pr1645v2Lan2FGVlanOutPQsOctetLength OBJECT-TYPE
   SYNTAX      Integer32
   MAX-ACCESS  read-only
   STATUS      current
   DESCRIPTION
      "Path: ethernet2.performance.vlan.outPriorityQueues.octetLength"
   ::= {pr1645v2Lan2FGVlanOutPQsEntry 150994944}

pr1645v2Lan2FGVlanOutPQsRedLength OBJECT-TYPE
   SYNTAX      Integer32
   MAX-ACCESS  read-only
   STATUS      current
   DESCRIPTION
      "Path: ethernet2.performance.vlan.outPriorityQueues.redLength"
   ::= {pr1645v2Lan2FGVlanOutPQsEntry 134217728}

pr1645v2Lan2FGVlanOutPQsPacketsTotal OBJECT-TYPE
   SYNTAX      Counter64
   MAX-ACCESS  read-only
   STATUS      current
   DESCRIPTION
      "Path: ethernet2.performance.vlan.outPriorityQueues.packets.total

       64 bit unsigned wrappable counter."
   ::= {pr1645v2Lan2FGVlanOutPQsEntry 50790400}

pr1645v2Lan2FGVlanOutPQsPacketsDirectTx OBJECT-TYPE
   SYNTAX      Counter64
   MAX-ACCESS  read-only
   STATUS      current
   DESCRIPTION
      "Path: ethernet2.performance.vlan.outPriorityQueues.packets.directTx

       64 bit unsigned wrappable counter."
   ::= {pr1645v2Lan2FGVlanOutPQsEntry 50397184}

pr1645v2Lan2FGVlanOutPQsPacketsQueued OBJECT-TYPE
   SYNTAX      Counter64
   MAX-ACCESS  read-only
   STATUS      current
   DESCRIPTION
      "Path: ethernet2.performance.vlan.outPriorityQueues.packets.queued

       64 bit unsigned wrappable counter."
   ::= {pr1645v2Lan2FGVlanOutPQsEntry 50462720}

pr1645v2Lan2FGVlanOutPQsPacketsDropped OBJECT-TYPE
   SYNTAX      Counter64
   MAX-ACCESS  read-only
   STATUS      current
   DESCRIPTION
      "Path: ethernet2.performance.vlan.outPriorityQueues.packets.dropped

       64 bit unsigned wrappable counter."
   ::= {pr1645v2Lan2FGVlanOutPQsEntry 50528256}

pr1645v2Lan2FGVlanOutPQsPacketsRedDropped OBJECT-TYPE
   SYNTAX      Counter64
   MAX-ACCESS  read-only
   STATUS      current
   DESCRIPTION
      "Path: ethernet2.performance.vlan.outPriorityQueues.packets.redDropped

       64 bit unsigned wrappable counter."
   ::= {pr1645v2Lan2FGVlanOutPQsEntry 50724864}

pr1645v2Lan2FGVlanOutPQsPacketsCirTx OBJECT-TYPE
   SYNTAX      Counter64
   MAX-ACCESS  read-only
   STATUS      current
   DESCRIPTION
      "Path: ethernet2.performance.vlan.outPriorityQueues.packets.cirTx

       64 bit unsigned wrappable counter."
   ::= {pr1645v2Lan2FGVlanOutPQsEntry 50593792}

pr1645v2Lan2FGVlanOutPQsPacketsEirTx OBJECT-TYPE
   SYNTAX      Counter64
   MAX-ACCESS  read-only
   STATUS      current
   DESCRIPTION
      "Path: ethernet2.performance.vlan.outPriorityQueues.packets.eirTx

       64 bit unsigned wrappable counter."
   ::= {pr1645v2Lan2FGVlanOutPQsEntry 50659328}

pr1645v2Lan2FGVlanOutPQsPacketsViolateTx OBJECT-TYPE
   SYNTAX      Counter64
   MAX-ACCESS  read-only
   STATUS      current
   DESCRIPTION
      "Path: ethernet2.performance.vlan.outPriorityQueues.packets.violateTx

       64 bit unsigned wrappable counter."
   ::= {pr1645v2Lan2FGVlanOutPQsEntry 50855936}

pr1645v2Lan2FGVlanOutPQsOctetsTotal OBJECT-TYPE
   SYNTAX      Counter64
   MAX-ACCESS  read-only
   STATUS      current
   DESCRIPTION
      "Path: ethernet2.performance.vlan.outPriorityQueues.octets.total

       64 bit unsigned wrappable counter."
   ::= {pr1645v2Lan2FGVlanOutPQsEntry 67567616}

pr1645v2Lan2FGVlanOutPQsOctetsDirectTx OBJECT-TYPE
   SYNTAX      Counter64
   MAX-ACCESS  read-only
   STATUS      current
   DESCRIPTION
      "Path: ethernet2.performance.vlan.outPriorityQueues.octets.directTx

       64 bit unsigned wrappable counter."
   ::= {pr1645v2Lan2FGVlanOutPQsEntry 67174400}

pr1645v2Lan2FGVlanOutPQsOctetsQueued OBJECT-TYPE
   SYNTAX      Counter64
   MAX-ACCESS  read-only
   STATUS      current
   DESCRIPTION
      "Path: ethernet2.performance.vlan.outPriorityQueues.octets.queued

       64 bit unsigned wrappable counter."
   ::= {pr1645v2Lan2FGVlanOutPQsEntry 67239936}

pr1645v2Lan2FGVlanOutPQsOctetsDropped OBJECT-TYPE
   SYNTAX      Counter64
   MAX-ACCESS  read-only
   STATUS      current
   DESCRIPTION
      "Path: ethernet2.performance.vlan.outPriorityQueues.octets.dropped

       64 bit unsigned wrappable counter."
   ::= {pr1645v2Lan2FGVlanOutPQsEntry 67305472}

pr1645v2Lan2FGVlanOutPQsOctetsRedDropped OBJECT-TYPE
   SYNTAX      Counter64
   MAX-ACCESS  read-only
   STATUS      current
   DESCRIPTION
      "Path: ethernet2.performance.vlan.outPriorityQueues.octets.redDropped

       64 bit unsigned wrappable counter."
   ::= {pr1645v2Lan2FGVlanOutPQsEntry 67502080}

pr1645v2Lan2FGVlanOutPQsOctetsCirTx OBJECT-TYPE
   SYNTAX      Counter64
   MAX-ACCESS  read-only
   STATUS      current
   DESCRIPTION
      "Path: ethernet2.performance.vlan.outPriorityQueues.octets.cirTx

       64 bit unsigned wrappable counter."
   ::= {pr1645v2Lan2FGVlanOutPQsEntry 67371008}

pr1645v2Lan2FGVlanOutPQsOctetsEirTx OBJECT-TYPE
   SYNTAX      Counter64
   MAX-ACCESS  read-only
   STATUS      current
   DESCRIPTION
      "Path: ethernet2.performance.vlan.outPriorityQueues.octets.eirTx

       64 bit unsigned wrappable counter."
   ::= {pr1645v2Lan2FGVlanOutPQsEntry 67436544}

pr1645v2Lan2FGVlanOutPQsOctetsViolateTx OBJECT-TYPE
   SYNTAX      Counter64
   MAX-ACCESS  read-only
   STATUS      current
   DESCRIPTION
      "Path: ethernet2.performance.vlan.outPriorityQueues.octets.violateTx

       64 bit unsigned wrappable counter."
   ::= {pr1645v2Lan2FGVlanOutPQsEntry 67633152}

pr1645v2Lan2FGVlanOutPQsOctetsBandwidth15sec OBJECT-TYPE
   SYNTAX      Integer32
   MAX-ACCESS  read-only
   STATUS      current
   DESCRIPTION
      "Path: ethernet2.performance.vlan.outPriorityQueues.octets.bandwidth.15sec

       unit name = bps
       formula = 8 * ; 8 /"
   ::= {pr1645v2Lan2FGVlanOutPQsEntry 70386944}

pr1645v2Lan2FGVlanOutPQsOctetsBandwidth30sec OBJECT-TYPE
   SYNTAX      Integer32
   MAX-ACCESS  read-only
   STATUS      current
   DESCRIPTION
      "Path: ethernet2.performance.vlan.outPriorityQueues.octets.bandwidth.30sec

       unit name = bps
       formula = 8 * ; 8 /"
   ::= {pr1645v2Lan2FGVlanOutPQsEntry 70388224}

pr1645v2Lan2FGVlanOutPQsOctetsBandwidth1min OBJECT-TYPE
   SYNTAX      Integer32
   MAX-ACCESS  read-only
   STATUS      current
   DESCRIPTION
      "Path: ethernet2.performance.vlan.outPriorityQueues.octets.bandwidth.1min

       unit name = bps
       formula = 8 * ; 8 /"
   ::= {pr1645v2Lan2FGVlanOutPQsEntry 70390784}

pr1645v2Lan2FGVlanOutPQsOctetsBandwidth2min OBJECT-TYPE
   SYNTAX      Integer32
   MAX-ACCESS  read-only
   STATUS      current
   DESCRIPTION
      "Path: ethernet2.performance.vlan.outPriorityQueues.octets.bandwidth.2min

       unit name = bps
       formula = 8 * ; 8 /"
   ::= {pr1645v2Lan2FGVlanOutPQsEntry 70395904}

pr1645v2Lan2FGVlanOutPQsOctetsBandwidth5min OBJECT-TYPE
   SYNTAX      Integer32
   MAX-ACCESS  read-only
   STATUS      current
   DESCRIPTION
      "Path: ethernet2.performance.vlan.outPriorityQueues.octets.bandwidth.5min

       unit name = bps
       formula = 8 * ; 8 /"
   ::= {pr1645v2Lan2FGVlanOutPQsEntry 70411264}

pr1645v2Lan2FGVlanOutPQsH2Performance OBJECT-TYPE
   SYNTAX      SEQUENCE OF Pr1645v2Lan2FGVlanOutPQsH2PerformanceEntry
   MAX-ACCESS  not-accessible
   STATUS      current
   DESCRIPTION
      ""
   ::= {pr1645v2Lan2FGVlan 84213760}

pr1645v2Lan2FGVlanOutPQsH2PerformanceEntry OBJECT-TYPE
   SYNTAX      Pr1645v2Lan2FGVlanOutPQsH2PerformanceEntry
   MAX-ACCESS  not-accessible
   STATUS      current
   DESCRIPTION
      ""
   INDEX      { pr1645v2Lan2FGVlanTableIx,
                pr1645v2Lan2FGVlanOutPQsTableIx,
                pr1645v2Lan2FGVlanOutPQsH2PerformanceTableIx }
   ::= {pr1645v2Lan2FGVlanOutPQsH2Performance 1}

Pr1645v2Lan2FGVlanOutPQsH2PerformanceEntry ::=
   SEQUENCE
      {
      pr1645v2Lan2FGVlanOutPQsH2PerformanceTableIx
         TableIndex,
      pr1645v2Lan2FGVlanOutPQsH2PerformanceSysUpTime
         TimeTicks,
      pr1645v2Lan2FGVlanOutPQsH2PerformanceTotPkts
         Counter64,
      pr1645v2Lan2FGVlanOutPQsH2PerformanceDirTxPkts
         Counter64,
      pr1645v2Lan2FGVlanOutPQsH2PerformanceQdPkts
         Counter64,
      pr1645v2Lan2FGVlanOutPQsH2PerformanceDropPkts
         Counter64,
      pr1645v2Lan2FGVlanOutPQsH2PerformanceRDropPkts
         Counter64,
      pr1645v2Lan2FGVlanOutPQsH2PerformanceCirTxPkts
         Counter64,
      pr1645v2Lan2FGVlanOutPQsH2PerformanceEirTxPkts
         Counter64,
      pr1645v2Lan2FGVlanOutPQsH2PerformanceViolTxPkts
         Counter64,
      pr1645v2Lan2FGVlanOutPQsH2PerformanceTotOcts
         Counter64,
      pr1645v2Lan2FGVlanOutPQsH2PerformanceDirTxOcts
         Counter64,
      pr1645v2Lan2FGVlanOutPQsH2PerformanceQdOcts
         Counter64,
      pr1645v2Lan2FGVlanOutPQsH2PerformanceDropOcts
         Counter64,
      pr1645v2Lan2FGVlanOutPQsH2PerformanceRDropOcts
         Counter64,
      pr1645v2Lan2FGVlanOutPQsH2PerformanceCirTxOcts
         Counter64,
      pr1645v2Lan2FGVlanOutPQsH2PerformanceEirTxOcts
         Counter64,
      pr1645v2Lan2FGVlanOutPQsH2PerformanceViolTxOcts
         Counter64,
      pr1645v2Lan2FGVlanOutPQsH2PerformanceBandwidth
         Integer32
      }

pr1645v2Lan2FGVlanOutPQsH2PerformanceTableIx OBJECT-TYPE
   SYNTAX      TableIndex
   MAX-ACCESS  not-accessible
   STATUS      current
   DESCRIPTION
      ""
   ::= {pr1645v2Lan2FGVlanOutPQsH2PerformanceEntry 11}

pr1645v2Lan2FGVlanOutPQsH2PerformanceSysUpTime OBJECT-TYPE
   SYNTAX      TimeTicks
   MAX-ACCESS  read-only
   STATUS      current
   DESCRIPTION
      "Path: ethernet2.performance.vlan.outPriorityQueues.h2Performance.sysUpTime

       Time in centi-second."
   ::= {pr1645v2Lan2FGVlanOutPQsH2PerformanceEntry 16777216}

pr1645v2Lan2FGVlanOutPQsH2PerformanceTotPkts OBJECT-TYPE
   SYNTAX      Counter64
   MAX-ACCESS  read-only
   STATUS      current
   DESCRIPTION
      "Path: ethernet2.performance.vlan.outPriorityQueues.h2Performance.totalPkts

       64 bit unsigned wrappable counter."
   ::= {pr1645v2Lan2FGVlanOutPQsH2PerformanceEntry 234881024}

pr1645v2Lan2FGVlanOutPQsH2PerformanceDirTxPkts OBJECT-TYPE
   SYNTAX      Counter64
   MAX-ACCESS  read-only
   STATUS      current
   DESCRIPTION
      "Path: ethernet2.performance.vlan.outPriorityQueues.h2Performance.directTxPkts

       64 bit unsigned wrappable counter."
   ::= {pr1645v2Lan2FGVlanOutPQsH2PerformanceEntry 33554432}

pr1645v2Lan2FGVlanOutPQsH2PerformanceQdPkts OBJECT-TYPE
   SYNTAX      Counter64
   MAX-ACCESS  read-only
   STATUS      current
   DESCRIPTION
      "Path: ethernet2.performance.vlan.outPriorityQueues.h2Performance.queuedPkts

       64 bit unsigned wrappable counter."
   ::= {pr1645v2Lan2FGVlanOutPQsH2PerformanceEntry 50331648}

pr1645v2Lan2FGVlanOutPQsH2PerformanceDropPkts OBJECT-TYPE
   SYNTAX      Counter64
   MAX-ACCESS  read-only
   STATUS      current
   DESCRIPTION
      "Path: ethernet2.performance.vlan.outPriorityQueues.h2Performance.droppedPkts

       64 bit unsigned wrappable counter."
   ::= {pr1645v2Lan2FGVlanOutPQsH2PerformanceEntry 67108864}

pr1645v2Lan2FGVlanOutPQsH2PerformanceRDropPkts OBJECT-TYPE
   SYNTAX      Counter64
   MAX-ACCESS  read-only
   STATUS      current
   DESCRIPTION
      "Path: ethernet2.performance.vlan.outPriorityQueues.h2Performance.redDroppedPkts

       64 bit unsigned wrappable counter."
   ::= {pr1645v2Lan2FGVlanOutPQsH2PerformanceEntry 201326592}

pr1645v2Lan2FGVlanOutPQsH2PerformanceCirTxPkts OBJECT-TYPE
   SYNTAX      Counter64
   MAX-ACCESS  read-only
   STATUS      current
   DESCRIPTION
      "Path: ethernet2.performance.vlan.outPriorityQueues.h2Performance.cirTxPkts

       64 bit unsigned wrappable counter."
   ::= {pr1645v2Lan2FGVlanOutPQsH2PerformanceEntry 83886080}

pr1645v2Lan2FGVlanOutPQsH2PerformanceEirTxPkts OBJECT-TYPE
   SYNTAX      Counter64
   MAX-ACCESS  read-only
   STATUS      current
   DESCRIPTION
      "Path: ethernet2.performance.vlan.outPriorityQueues.h2Performance.eirTxPkts

       64 bit unsigned wrappable counter."
   ::= {pr1645v2Lan2FGVlanOutPQsH2PerformanceEntry 100663296}

pr1645v2Lan2FGVlanOutPQsH2PerformanceViolTxPkts OBJECT-TYPE
   SYNTAX      Counter64
   MAX-ACCESS  read-only
   STATUS      current
   DESCRIPTION
      "Path: ethernet2.performance.vlan.outPriorityQueues.h2Performance.violateTxPkts

       64 bit unsigned wrappable counter."
   ::= {pr1645v2Lan2FGVlanOutPQsH2PerformanceEntry 301989888}

pr1645v2Lan2FGVlanOutPQsH2PerformanceTotOcts OBJECT-TYPE
   SYNTAX      Counter64
   MAX-ACCESS  read-only
   STATUS      current
   DESCRIPTION
      "Path: ethernet2.performance.vlan.outPriorityQueues.h2Performance.totalOctets

       64 bit unsigned wrappable counter."
   ::= {pr1645v2Lan2FGVlanOutPQsH2PerformanceEntry 251658240}

pr1645v2Lan2FGVlanOutPQsH2PerformanceDirTxOcts OBJECT-TYPE
   SYNTAX      Counter64
   MAX-ACCESS  read-only
   STATUS      current
   DESCRIPTION
      "Path: ethernet2.performance.vlan.outPriorityQueues.h2Performance.directTxOctets

       64 bit unsigned wrappable counter."
   ::= {pr1645v2Lan2FGVlanOutPQsH2PerformanceEntry 117440512}

pr1645v2Lan2FGVlanOutPQsH2PerformanceQdOcts OBJECT-TYPE
   SYNTAX      Counter64
   MAX-ACCESS  read-only
   STATUS      current
   DESCRIPTION
      "Path: ethernet2.performance.vlan.outPriorityQueues.h2Performance.queuedOctets

       64 bit unsigned wrappable counter."
   ::= {pr1645v2Lan2FGVlanOutPQsH2PerformanceEntry 134217728}

pr1645v2Lan2FGVlanOutPQsH2PerformanceDropOcts OBJECT-TYPE
   SYNTAX      Counter64
   MAX-ACCESS  read-only
   STATUS      current
   DESCRIPTION
      "Path: ethernet2.performance.vlan.outPriorityQueues.h2Performance.droppedOctets

       64 bit unsigned wrappable counter."
   ::= {pr1645v2Lan2FGVlanOutPQsH2PerformanceEntry 150994944}

pr1645v2Lan2FGVlanOutPQsH2PerformanceRDropOcts OBJECT-TYPE
   SYNTAX      Counter64
   MAX-ACCESS  read-only
   STATUS      current
   DESCRIPTION
      "Path: ethernet2.performance.vlan.outPriorityQueues.h2Performance.redDroppedOctets

       64 bit unsigned wrappable counter."
   ::= {pr1645v2Lan2FGVlanOutPQsH2PerformanceEntry 218103808}

pr1645v2Lan2FGVlanOutPQsH2PerformanceCirTxOcts OBJECT-TYPE
   SYNTAX      Counter64
   MAX-ACCESS  read-only
   STATUS      current
   DESCRIPTION
      "Path: ethernet2.performance.vlan.outPriorityQueues.h2Performance.cirTxOctets

       64 bit unsigned wrappable counter."
   ::= {pr1645v2Lan2FGVlanOutPQsH2PerformanceEntry 167772160}

pr1645v2Lan2FGVlanOutPQsH2PerformanceEirTxOcts OBJECT-TYPE
   SYNTAX      Counter64
   MAX-ACCESS  read-only
   STATUS      current
   DESCRIPTION
      "Path: ethernet2.performance.vlan.outPriorityQueues.h2Performance.eirTxOctets

       64 bit unsigned wrappable counter."
   ::= {pr1645v2Lan2FGVlanOutPQsH2PerformanceEntry 184549376}

pr1645v2Lan2FGVlanOutPQsH2PerformanceViolTxOcts OBJECT-TYPE
   SYNTAX      Counter64
   MAX-ACCESS  read-only
   STATUS      current
   DESCRIPTION
      "Path: ethernet2.performance.vlan.outPriorityQueues.h2Performance.violateTxOctets

       64 bit unsigned wrappable counter."
   ::= {pr1645v2Lan2FGVlanOutPQsH2PerformanceEntry 318767104}

pr1645v2Lan2FGVlanOutPQsH2PerformanceBandwidth OBJECT-TYPE
   SYNTAX      Integer32
   MAX-ACCESS  read-only
   STATUS      current
   DESCRIPTION
      "Path: ethernet2.performance.vlan.outPriorityQueues.h2Performance.bandwidth

       unit name = bps
       formula = 8 * ; 8 /"
   ::= {pr1645v2Lan2FGVlanOutPQsH2PerformanceEntry 268435456}

pr1645v2Lan2FGVlanOutPQsH24Performance OBJECT-TYPE
   SYNTAX      SEQUENCE OF Pr1645v2Lan2FGVlanOutPQsH24PerformanceEntry
   MAX-ACCESS  not-accessible
   STATUS      current
   DESCRIPTION
      ""
   ::= {pr1645v2Lan2FGVlan 84279296}

pr1645v2Lan2FGVlanOutPQsH24PerformanceEntry OBJECT-TYPE
   SYNTAX      Pr1645v2Lan2FGVlanOutPQsH24PerformanceEntry
   MAX-ACCESS  not-accessible
   STATUS      current
   DESCRIPTION
      ""
   INDEX      { pr1645v2Lan2FGVlanTableIx,
                pr1645v2Lan2FGVlanOutPQsTableIx,
                pr1645v2Lan2FGVlanOutPQsH24PerformanceTableIx }
   ::= {pr1645v2Lan2FGVlanOutPQsH24Performance 1}

Pr1645v2Lan2FGVlanOutPQsH24PerformanceEntry ::=
   SEQUENCE
      {
      pr1645v2Lan2FGVlanOutPQsH24PerformanceTableIx
         TableIndex,
      pr1645v2Lan2FGVlanOutPQsH24PerformanceSysUpTime
         TimeTicks,
      pr1645v2Lan2FGVlanOutPQsH24PerformanceTotPkts
         Counter64,
      pr1645v2Lan2FGVlanOutPQsH24PerformanceDirTxPkts
         Counter64,
      pr1645v2Lan2FGVlanOutPQsH24PerformanceQdPkts
         Counter64,
      pr1645v2Lan2FGVlanOutPQsH24PerformanceDropPkts
         Counter64,
      pr1645v2Lan2FGVlanOutPQsH24PerformanceRDropPkts
         Counter64,
      pr1645v2Lan2FGVlanOutPQsH24PerformanceCirTxPkts
         Counter64,
      pr1645v2Lan2FGVlanOutPQsH24PerformanceEirTxPkts
         Counter64,
      pr1645v2Lan2FGVlanOutPQsH24PerformanceViolTxPkts
         Counter64,
      pr1645v2Lan2FGVlanOutPQsH24PerformanceTotOcts
         Counter64,
      pr1645v2Lan2FGVlanOutPQsH24PerformanceDirTxOcts
         Counter64,
      pr1645v2Lan2FGVlanOutPQsH24PerformanceQdOcts
         Counter64,
      pr1645v2Lan2FGVlanOutPQsH24PerformanceDropOcts
         Counter64,
      pr1645v2Lan2FGVlanOutPQsH24PerformanceRDropOcts
         Counter64,
      pr1645v2Lan2FGVlanOutPQsH24PerformanceCirTxOcts
         Counter64,
      pr1645v2Lan2FGVlanOutPQsH24PerformanceEirTxOcts
         Counter64,
      pr1645v2Lan2FGVlanOutPQsH24PerformanceViolTxOcts
         Counter64,
      pr1645v2Lan2FGVlanOutPQsH24PerformanceBandwidth
         Integer32
      }

pr1645v2Lan2FGVlanOutPQsH24PerformanceTableIx OBJECT-TYPE
   SYNTAX      TableIndex
   MAX-ACCESS  not-accessible
   STATUS      current
   DESCRIPTION
      ""
   ::= {pr1645v2Lan2FGVlanOutPQsH24PerformanceEntry 11}

pr1645v2Lan2FGVlanOutPQsH24PerformanceSysUpTime OBJECT-TYPE
   SYNTAX      TimeTicks
   MAX-ACCESS  read-only
   STATUS      current
   DESCRIPTION
      "Path: ethernet2.performance.vlan.outPriorityQueues.h24Performance.sysUpTime

       Time in centi-second."
   ::= {pr1645v2Lan2FGVlanOutPQsH24PerformanceEntry 16777216}

pr1645v2Lan2FGVlanOutPQsH24PerformanceTotPkts OBJECT-TYPE
   SYNTAX      Counter64
   MAX-ACCESS  read-only
   STATUS      current
   DESCRIPTION
      "Path: ethernet2.performance.vlan.outPriorityQueues.h24Performance.totalPkts

       64 bit unsigned wrappable counter."
   ::= {pr1645v2Lan2FGVlanOutPQsH24PerformanceEntry 234881024}

pr1645v2Lan2FGVlanOutPQsH24PerformanceDirTxPkts OBJECT-TYPE
   SYNTAX      Counter64
   MAX-ACCESS  read-only
   STATUS      current
   DESCRIPTION
      "Path: ethernet2.performance.vlan.outPriorityQueues.h24Performance.directTxPkts

       64 bit unsigned wrappable counter."
   ::= {pr1645v2Lan2FGVlanOutPQsH24PerformanceEntry 33554432}

pr1645v2Lan2FGVlanOutPQsH24PerformanceQdPkts OBJECT-TYPE
   SYNTAX      Counter64
   MAX-ACCESS  read-only
   STATUS      current
   DESCRIPTION
      "Path: ethernet2.performance.vlan.outPriorityQueues.h24Performance.queuedPkts

       64 bit unsigned wrappable counter."
   ::= {pr1645v2Lan2FGVlanOutPQsH24PerformanceEntry 50331648}

pr1645v2Lan2FGVlanOutPQsH24PerformanceDropPkts OBJECT-TYPE
   SYNTAX      Counter64
   MAX-ACCESS  read-only
   STATUS      current
   DESCRIPTION
      "Path: ethernet2.performance.vlan.outPriorityQueues.h24Performance.droppedPkts

       64 bit unsigned wrappable counter."
   ::= {pr1645v2Lan2FGVlanOutPQsH24PerformanceEntry 67108864}

pr1645v2Lan2FGVlanOutPQsH24PerformanceRDropPkts OBJECT-TYPE
   SYNTAX      Counter64
   MAX-ACCESS  read-only
   STATUS      current
   DESCRIPTION
      "Path: ethernet2.performance.vlan.outPriorityQueues.h24Performance.redDroppedPkts

       64 bit unsigned wrappable counter."
   ::= {pr1645v2Lan2FGVlanOutPQsH24PerformanceEntry 201326592}

pr1645v2Lan2FGVlanOutPQsH24PerformanceCirTxPkts OBJECT-TYPE
   SYNTAX      Counter64
   MAX-ACCESS  read-only
   STATUS      current
   DESCRIPTION
      "Path: ethernet2.performance.vlan.outPriorityQueues.h24Performance.cirTxPkts

       64 bit unsigned wrappable counter."
   ::= {pr1645v2Lan2FGVlanOutPQsH24PerformanceEntry 83886080}

pr1645v2Lan2FGVlanOutPQsH24PerformanceEirTxPkts OBJECT-TYPE
   SYNTAX      Counter64
   MAX-ACCESS  read-only
   STATUS      current
   DESCRIPTION
      "Path: ethernet2.performance.vlan.outPriorityQueues.h24Performance.eirTxPkts

       64 bit unsigned wrappable counter."
   ::= {pr1645v2Lan2FGVlanOutPQsH24PerformanceEntry 100663296}

pr1645v2Lan2FGVlanOutPQsH24PerformanceViolTxPkts OBJECT-TYPE
   SYNTAX      Counter64
   MAX-ACCESS  read-only
   STATUS      current
   DESCRIPTION
      "Path: ethernet2.performance.vlan.outPriorityQueues.h24Performance.violateTxPkts

       64 bit unsigned wrappable counter."
   ::= {pr1645v2Lan2FGVlanOutPQsH24PerformanceEntry 301989888}

pr1645v2Lan2FGVlanOutPQsH24PerformanceTotOcts OBJECT-TYPE
   SYNTAX      Counter64
   MAX-ACCESS  read-only
   STATUS      current
   DESCRIPTION
      "Path: ethernet2.performance.vlan.outPriorityQueues.h24Performance.totalOctets

       64 bit unsigned wrappable counter."
   ::= {pr1645v2Lan2FGVlanOutPQsH24PerformanceEntry 251658240}

pr1645v2Lan2FGVlanOutPQsH24PerformanceDirTxOcts OBJECT-TYPE
   SYNTAX      Counter64
   MAX-ACCESS  read-only
   STATUS      current
   DESCRIPTION
      "Path: ethernet2.performance.vlan.outPriorityQueues.h24Performance.directTxOctets

       64 bit unsigned wrappable counter."
   ::= {pr1645v2Lan2FGVlanOutPQsH24PerformanceEntry 117440512}

pr1645v2Lan2FGVlanOutPQsH24PerformanceQdOcts OBJECT-TYPE
   SYNTAX      Counter64
   MAX-ACCESS  read-only
   STATUS      current
   DESCRIPTION
      "Path: ethernet2.performance.vlan.outPriorityQueues.h24Performance.queuedOctets

       64 bit unsigned wrappable counter."
   ::= {pr1645v2Lan2FGVlanOutPQsH24PerformanceEntry 134217728}

pr1645v2Lan2FGVlanOutPQsH24PerformanceDropOcts OBJECT-TYPE
   SYNTAX      Counter64
   MAX-ACCESS  read-only
   STATUS      current
   DESCRIPTION
      "Path: ethernet2.performance.vlan.outPriorityQueues.h24Performance.droppedOctets

       64 bit unsigned wrappable counter."
   ::= {pr1645v2Lan2FGVlanOutPQsH24PerformanceEntry 150994944}

pr1645v2Lan2FGVlanOutPQsH24PerformanceRDropOcts OBJECT-TYPE
   SYNTAX      Counter64
   MAX-ACCESS  read-only
   STATUS      current
   DESCRIPTION
      "Path: ethernet2.performance.vlan.outPriorityQueues.h24Performance.redDroppedOctets

       64 bit unsigned wrappable counter."
   ::= {pr1645v2Lan2FGVlanOutPQsH24PerformanceEntry 218103808}

pr1645v2Lan2FGVlanOutPQsH24PerformanceCirTxOcts OBJECT-TYPE
   SYNTAX      Counter64
   MAX-ACCESS  read-only
   STATUS      current
   DESCRIPTION
      "Path: ethernet2.performance.vlan.outPriorityQueues.h24Performance.cirTxOctets

       64 bit unsigned wrappable counter."
   ::= {pr1645v2Lan2FGVlanOutPQsH24PerformanceEntry 167772160}

pr1645v2Lan2FGVlanOutPQsH24PerformanceEirTxOcts OBJECT-TYPE
   SYNTAX      Counter64
   MAX-ACCESS  read-only
   STATUS      current
   DESCRIPTION
      "Path: ethernet2.performance.vlan.outPriorityQueues.h24Performance.eirTxOctets

       64 bit unsigned wrappable counter."
   ::= {pr1645v2Lan2FGVlanOutPQsH24PerformanceEntry 184549376}

pr1645v2Lan2FGVlanOutPQsH24PerformanceViolTxOcts OBJECT-TYPE
   SYNTAX      Counter64
   MAX-ACCESS  read-only
   STATUS      current
   DESCRIPTION
      "Path: ethernet2.performance.vlan.outPriorityQueues.h24Performance.violateTxOctets

       64 bit unsigned wrappable counter."
   ::= {pr1645v2Lan2FGVlanOutPQsH24PerformanceEntry 318767104}

pr1645v2Lan2FGVlanOutPQsH24PerformanceBandwidth OBJECT-TYPE
   SYNTAX      Integer32
   MAX-ACCESS  read-only
   STATUS      current
   DESCRIPTION
      "Path: ethernet2.performance.vlan.outPriorityQueues.h24Performance.bandwidth

       unit name = bps
       formula = 8 * ; 8 /"
   ::= {pr1645v2Lan2FGVlanOutPQsH24PerformanceEntry 268435456}

pr1645v2Lan2FGVlanOutPQsD7Performance OBJECT-TYPE
   SYNTAX      SEQUENCE OF Pr1645v2Lan2FGVlanOutPQsD7PerformanceEntry
   MAX-ACCESS  not-accessible
   STATUS      current
   DESCRIPTION
      ""
   ::= {pr1645v2Lan2FGVlan 84344832}

pr1645v2Lan2FGVlanOutPQsD7PerformanceEntry OBJECT-TYPE
   SYNTAX      Pr1645v2Lan2FGVlanOutPQsD7PerformanceEntry
   MAX-ACCESS  not-accessible
   STATUS      current
   DESCRIPTION
      ""
   INDEX      { pr1645v2Lan2FGVlanTableIx,
                pr1645v2Lan2FGVlanOutPQsTableIx,
                pr1645v2Lan2FGVlanOutPQsD7PerformanceTableIx }
   ::= {pr1645v2Lan2FGVlanOutPQsD7Performance 1}

Pr1645v2Lan2FGVlanOutPQsD7PerformanceEntry ::=
   SEQUENCE
      {
      pr1645v2Lan2FGVlanOutPQsD7PerformanceTableIx
         TableIndex,
      pr1645v2Lan2FGVlanOutPQsD7PerformanceSysUpTime
         TimeTicks,
      pr1645v2Lan2FGVlanOutPQsD7PerformanceTotPkts
         Counter64,
      pr1645v2Lan2FGVlanOutPQsD7PerformanceDirTxPkts
         Counter64,
      pr1645v2Lan2FGVlanOutPQsD7PerformanceQdPkts
         Counter64,
      pr1645v2Lan2FGVlanOutPQsD7PerformanceDropPkts
         Counter64,
      pr1645v2Lan2FGVlanOutPQsD7PerformanceRDropPkts
         Counter64,
      pr1645v2Lan2FGVlanOutPQsD7PerformanceCirTxPkts
         Counter64,
      pr1645v2Lan2FGVlanOutPQsD7PerformanceEirTxPkts
         Counter64,
      pr1645v2Lan2FGVlanOutPQsD7PerformanceViolTxPkts
         Counter64,
      pr1645v2Lan2FGVlanOutPQsD7PerformanceTotOcts
         Counter64,
      pr1645v2Lan2FGVlanOutPQsD7PerformanceDirTxOcts
         Counter64,
      pr1645v2Lan2FGVlanOutPQsD7PerformanceQdOcts
         Counter64,
      pr1645v2Lan2FGVlanOutPQsD7PerformanceDropOcts
         Counter64,
      pr1645v2Lan2FGVlanOutPQsD7PerformanceRDropOcts
         Counter64,
      pr1645v2Lan2FGVlanOutPQsD7PerformanceCirTxOcts
         Counter64,
      pr1645v2Lan2FGVlanOutPQsD7PerformanceEirTxOcts
         Counter64,
      pr1645v2Lan2FGVlanOutPQsD7PerformanceViolTxOcts
         Counter64,
      pr1645v2Lan2FGVlanOutPQsD7PerformanceBandwidth
         Integer32
      }

pr1645v2Lan2FGVlanOutPQsD7PerformanceTableIx OBJECT-TYPE
   SYNTAX      TableIndex
   MAX-ACCESS  not-accessible
   STATUS      current
   DESCRIPTION
      ""
   ::= {pr1645v2Lan2FGVlanOutPQsD7PerformanceEntry 11}

pr1645v2Lan2FGVlanOutPQsD7PerformanceSysUpTime OBJECT-TYPE
   SYNTAX      TimeTicks
   MAX-ACCESS  read-only
   STATUS      current
   DESCRIPTION
      "Path: ethernet2.performance.vlan.outPriorityQueues.d7Performance.sysUpTime

       Time in centi-second."
   ::= {pr1645v2Lan2FGVlanOutPQsD7PerformanceEntry 16777216}

pr1645v2Lan2FGVlanOutPQsD7PerformanceTotPkts OBJECT-TYPE
   SYNTAX      Counter64
   MAX-ACCESS  read-only
   STATUS      current
   DESCRIPTION
      "Path: ethernet2.performance.vlan.outPriorityQueues.d7Performance.totalPkts

       64 bit unsigned wrappable counter."
   ::= {pr1645v2Lan2FGVlanOutPQsD7PerformanceEntry 234881024}

pr1645v2Lan2FGVlanOutPQsD7PerformanceDirTxPkts OBJECT-TYPE
   SYNTAX      Counter64
   MAX-ACCESS  read-only
   STATUS      current
   DESCRIPTION
      "Path: ethernet2.performance.vlan.outPriorityQueues.d7Performance.directTxPkts

       64 bit unsigned wrappable counter."
   ::= {pr1645v2Lan2FGVlanOutPQsD7PerformanceEntry 33554432}

pr1645v2Lan2FGVlanOutPQsD7PerformanceQdPkts OBJECT-TYPE
   SYNTAX      Counter64
   MAX-ACCESS  read-only
   STATUS      current
   DESCRIPTION
      "Path: ethernet2.performance.vlan.outPriorityQueues.d7Performance.queuedPkts

       64 bit unsigned wrappable counter."
   ::= {pr1645v2Lan2FGVlanOutPQsD7PerformanceEntry 50331648}

pr1645v2Lan2FGVlanOutPQsD7PerformanceDropPkts OBJECT-TYPE
   SYNTAX      Counter64
   MAX-ACCESS  read-only
   STATUS      current
   DESCRIPTION
      "Path: ethernet2.performance.vlan.outPriorityQueues.d7Performance.droppedPkts

       64 bit unsigned wrappable counter."
   ::= {pr1645v2Lan2FGVlanOutPQsD7PerformanceEntry 67108864}

pr1645v2Lan2FGVlanOutPQsD7PerformanceRDropPkts OBJECT-TYPE
   SYNTAX      Counter64
   MAX-ACCESS  read-only
   STATUS      current
   DESCRIPTION
      "Path: ethernet2.performance.vlan.outPriorityQueues.d7Performance.redDroppedPkts

       64 bit unsigned wrappable counter."
   ::= {pr1645v2Lan2FGVlanOutPQsD7PerformanceEntry 201326592}

pr1645v2Lan2FGVlanOutPQsD7PerformanceCirTxPkts OBJECT-TYPE
   SYNTAX      Counter64
   MAX-ACCESS  read-only
   STATUS      current
   DESCRIPTION
      "Path: ethernet2.performance.vlan.outPriorityQueues.d7Performance.cirTxPkts

       64 bit unsigned wrappable counter."
   ::= {pr1645v2Lan2FGVlanOutPQsD7PerformanceEntry 83886080}

pr1645v2Lan2FGVlanOutPQsD7PerformanceEirTxPkts OBJECT-TYPE
   SYNTAX      Counter64
   MAX-ACCESS  read-only
   STATUS      current
   DESCRIPTION
      "Path: ethernet2.performance.vlan.outPriorityQueues.d7Performance.eirTxPkts

       64 bit unsigned wrappable counter."
   ::= {pr1645v2Lan2FGVlanOutPQsD7PerformanceEntry 100663296}

pr1645v2Lan2FGVlanOutPQsD7PerformanceViolTxPkts OBJECT-TYPE
   SYNTAX      Counter64
   MAX-ACCESS  read-only
   STATUS      current
   DESCRIPTION
      "Path: ethernet2.performance.vlan.outPriorityQueues.d7Performance.violateTxPkts

       64 bit unsigned wrappable counter."
   ::= {pr1645v2Lan2FGVlanOutPQsD7PerformanceEntry 301989888}

pr1645v2Lan2FGVlanOutPQsD7PerformanceTotOcts OBJECT-TYPE
   SYNTAX      Counter64
   MAX-ACCESS  read-only
   STATUS      current
   DESCRIPTION
      "Path: ethernet2.performance.vlan.outPriorityQueues.d7Performance.totalOctets

       64 bit unsigned wrappable counter."
   ::= {pr1645v2Lan2FGVlanOutPQsD7PerformanceEntry 251658240}

pr1645v2Lan2FGVlanOutPQsD7PerformanceDirTxOcts OBJECT-TYPE
   SYNTAX      Counter64
   MAX-ACCESS  read-only
   STATUS      current
   DESCRIPTION
      "Path: ethernet2.performance.vlan.outPriorityQueues.d7Performance.directTxOctets

       64 bit unsigned wrappable counter."
   ::= {pr1645v2Lan2FGVlanOutPQsD7PerformanceEntry 117440512}

pr1645v2Lan2FGVlanOutPQsD7PerformanceQdOcts OBJECT-TYPE
   SYNTAX      Counter64
   MAX-ACCESS  read-only
   STATUS      current
   DESCRIPTION
      "Path: ethernet2.performance.vlan.outPriorityQueues.d7Performance.queuedOctets

       64 bit unsigned wrappable counter."
   ::= {pr1645v2Lan2FGVlanOutPQsD7PerformanceEntry 134217728}

pr1645v2Lan2FGVlanOutPQsD7PerformanceDropOcts OBJECT-TYPE
   SYNTAX      Counter64
   MAX-ACCESS  read-only
   STATUS      current
   DESCRIPTION
      "Path: ethernet2.performance.vlan.outPriorityQueues.d7Performance.droppedOctets

       64 bit unsigned wrappable counter."
   ::= {pr1645v2Lan2FGVlanOutPQsD7PerformanceEntry 150994944}

pr1645v2Lan2FGVlanOutPQsD7PerformanceRDropOcts OBJECT-TYPE
   SYNTAX      Counter64
   MAX-ACCESS  read-only
   STATUS      current
   DESCRIPTION
      "Path: ethernet2.performance.vlan.outPriorityQueues.d7Performance.redDroppedOctets

       64 bit unsigned wrappable counter."
   ::= {pr1645v2Lan2FGVlanOutPQsD7PerformanceEntry 218103808}

pr1645v2Lan2FGVlanOutPQsD7PerformanceCirTxOcts OBJECT-TYPE
   SYNTAX      Counter64
   MAX-ACCESS  read-only
   STATUS      current
   DESCRIPTION
      "Path: ethernet2.performance.vlan.outPriorityQueues.d7Performance.cirTxOctets

       64 bit unsigned wrappable counter."
   ::= {pr1645v2Lan2FGVlanOutPQsD7PerformanceEntry 167772160}

pr1645v2Lan2FGVlanOutPQsD7PerformanceEirTxOcts OBJECT-TYPE
   SYNTAX      Counter64
   MAX-ACCESS  read-only
   STATUS      current
   DESCRIPTION
      "Path: ethernet2.performance.vlan.outPriorityQueues.d7Performance.eirTxOctets

       64 bit unsigned wrappable counter."
   ::= {pr1645v2Lan2FGVlanOutPQsD7PerformanceEntry 184549376}

pr1645v2Lan2FGVlanOutPQsD7PerformanceViolTxOcts OBJECT-TYPE
   SYNTAX      Counter64
   MAX-ACCESS  read-only
   STATUS      current
   DESCRIPTION
      "Path: ethernet2.performance.vlan.outPriorityQueues.d7Performance.violateTxOctets

       64 bit unsigned wrappable counter."
   ::= {pr1645v2Lan2FGVlanOutPQsD7PerformanceEntry 318767104}

pr1645v2Lan2FGVlanOutPQsD7PerformanceBandwidth OBJECT-TYPE
   SYNTAX      Integer32
   MAX-ACCESS  read-only
   STATUS      current
   DESCRIPTION
      "Path: ethernet2.performance.vlan.outPriorityQueues.d7Performance.bandwidth

       unit name = bps
       formula = 8 * ; 8 /"
   ::= {pr1645v2Lan2FGVlanOutPQsD7PerformanceEntry 268435456}


pr1645v2Lan2FGPPPoE OBJECT IDENTIFIER ::= {pr1645v2Lan2FG 53}

pr1645v2Lan2FGPPPoESSCTable OBJECT-TYPE
   SYNTAX      SEQUENCE OF Pr1645v2Lan2FGPPPoEEntry
   MAX-ACCESS  not-accessible
   STATUS      current
   DESCRIPTION
      ""
   ::= {pr1645v2Lan2FGPPPoE 1}

pr1645v2Lan2FGPPPoEEntry OBJECT-TYPE
   SYNTAX      Pr1645v2Lan2FGPPPoEEntry
   MAX-ACCESS  not-accessible
   STATUS      current
   DESCRIPTION
      ""
   INDEX      { pr1645v2Lan2FGPPPoETableIx }
   ::= {pr1645v2Lan2FGPPPoESSCTable 1}

Pr1645v2Lan2FGPPPoEEntry ::=
   SEQUENCE
      {
      pr1645v2Lan2FGPPPoETableIx
         TableIndex,
      pr1645v2Lan2FGPPPoEName
         DisplayString,
      pr1645v2Lan2FGPPPoEMCInOctets
         Counter64,
      pr1645v2Lan2FGPPPoEMCInUcast
         Counter64,
      pr1645v2Lan2FGPPPoEMCInNUcastPkts
         Counter64,
      pr1645v2Lan2FGPPPoEMCInBcastPkts
         Counter64,
      pr1645v2Lan2FGPPPoEMCInMcastPkts
         Counter64,
      pr1645v2Lan2FGPPPoEMCInDiscards
         Counter64,
      pr1645v2Lan2FGPPPoEMCInErrors
         Counter64,
      pr1645v2Lan2FGPPPoEMCInUnknownProtos
         Counter64,
      pr1645v2Lan2FGPPPoEMCInDropEx
         Counter64,
      pr1645v2Lan2FGPPPoEMCInDropNoMac
         Counter64,
      pr1645v2Lan2FGPPPoEMCInDropNUCast
         Counter64,
      pr1645v2Lan2FGPPPoEMCInDropFilter
         Counter64,
      pr1645v2Lan2FGPPPoEMCInBandwidth15sec
         Integer32,
      pr1645v2Lan2FGPPPoEMCInBandwidth30sec
         Integer32,
      pr1645v2Lan2FGPPPoEMCInBandwidth1min
         Integer32,
      pr1645v2Lan2FGPPPoEMCInBandwidth2min
         Integer32,
      pr1645v2Lan2FGPPPoEMCInBandwidth5min
         Integer32,
      pr1645v2Lan2FGPPPoEMCOutOctets
         Counter64,
      pr1645v2Lan2FGPPPoEMCOutUcastPkts
         Counter64,
      pr1645v2Lan2FGPPPoEMCOutNUcastPkts
         Counter64,
      pr1645v2Lan2FGPPPoEMCOutBcastPkts
         Counter64,
      pr1645v2Lan2FGPPPoEMCOutMcastPkts
         Counter64,
      pr1645v2Lan2FGPPPoEMCOutDiscards
         Counter64,
      pr1645v2Lan2FGPPPoEMCOutErrors
         Counter64,
      pr1645v2Lan2FGPPPoEMCOutQLen
         Counter32,
      pr1645v2Lan2FGPPPoEMCOutDropEx
         Counter64,
      pr1645v2Lan2FGPPPoEMCOutDropNoArp
         Counter64,
      pr1645v2Lan2FGPPPoEMCOutDropFilter
         Counter64,
      pr1645v2Lan2FGPPPoEMCOutBandwidth15sec
         Integer32,
      pr1645v2Lan2FGPPPoEMCOutBandwidth30sec
         Integer32,
      pr1645v2Lan2FGPPPoEMCOutBandwidth1min
         Integer32,
      pr1645v2Lan2FGPPPoEMCOutBandwidth2min
         Integer32,
      pr1645v2Lan2FGPPPoEMCOutBandwidth5min
         Integer32,
      pr1645v2Lan2FGPPPoEPppLinkMonitoringRequestsSent
         Gauge32,
      pr1645v2Lan2FGPPPoEPppLinkMonitoringRepliesRcvd
         Gauge32,
      pr1645v2Lan2FGPPPoEPppLinkMonitoringRequestsRcvd
         Gauge32,
      pr1645v2Lan2FGPPPoEPppLinkMonitoringRepliesSent
         Gauge32
      }

pr1645v2Lan2FGPPPoETableIx OBJECT-TYPE
   SYNTAX      TableIndex
   MAX-ACCESS  not-accessible
   STATUS      current
   DESCRIPTION
      ""
   ::= {pr1645v2Lan2FGPPPoEEntry 11}

pr1645v2Lan2FGPPPoEName OBJECT-TYPE
   SYNTAX      DisplayString
   MAX-ACCESS  read-only
   STATUS      current
   DESCRIPTION
      "Path: ethernet2.performance.pppoEClient.name"
   ::= {pr1645v2Lan2FGPPPoEEntry 16777216}

pr1645v2Lan2FGPPPoEMCInOctets OBJECT-TYPE
   SYNTAX      Counter64
   MAX-ACCESS  read-only
   STATUS      current
   DESCRIPTION
      "Path: ethernet2.performance.pppoEClient.mibCounters.ifInOctets

       64 bit unsigned wrappable counter."
   ::= {pr1645v2Lan2FGPPPoEEntry 40697856}

pr1645v2Lan2FGPPPoEMCInUcast OBJECT-TYPE
   SYNTAX      Counter64
   MAX-ACCESS  read-only
   STATUS      current
   DESCRIPTION
      "Path: ethernet2.performance.pppoEClient.mibCounters.ifInUcastPkts

       64 bit unsigned wrappable counter."
   ::= {pr1645v2Lan2FGPPPoEEntry 40763392}

pr1645v2Lan2FGPPPoEMCInNUcastPkts OBJECT-TYPE
   SYNTAX      Counter64
   MAX-ACCESS  read-only
   STATUS      current
   DESCRIPTION
      "Path: ethernet2.performance.pppoEClient.mibCounters.ifInNUcastPkts

       64 bit unsigned wrappable counter."
   ::= {pr1645v2Lan2FGPPPoEEntry 40828928}

pr1645v2Lan2FGPPPoEMCInBcastPkts OBJECT-TYPE
   SYNTAX      Counter64
   MAX-ACCESS  read-only
   STATUS      current
   DESCRIPTION
      "Path: ethernet2.performance.pppoEClient.mibCounters.ifInBcastPkts

       64 bit unsigned wrappable counter."
   ::= {pr1645v2Lan2FGPPPoEEntry 47382528}

pr1645v2Lan2FGPPPoEMCInMcastPkts OBJECT-TYPE
   SYNTAX      Counter64
   MAX-ACCESS  read-only
   STATUS      current
   DESCRIPTION
      "Path: ethernet2.performance.pppoEClient.mibCounters.ifInMcastPkts

       64 bit unsigned wrappable counter."
   ::= {pr1645v2Lan2FGPPPoEEntry 48037888}

pr1645v2Lan2FGPPPoEMCInDiscards OBJECT-TYPE
   SYNTAX      Counter64
   MAX-ACCESS  read-only
   STATUS      current
   DESCRIPTION
      "Path: ethernet2.performance.pppoEClient.mibCounters.ifInDiscards

       64 bit unsigned wrappable counter."
   ::= {pr1645v2Lan2FGPPPoEEntry 40894464}

pr1645v2Lan2FGPPPoEMCInErrors OBJECT-TYPE
   SYNTAX      Counter64
   MAX-ACCESS  read-only
   STATUS      current
   DESCRIPTION
      "Path: ethernet2.performance.pppoEClient.mibCounters.ifInErrors

       64 bit unsigned wrappable counter."
   ::= {pr1645v2Lan2FGPPPoEEntry 40960000}

pr1645v2Lan2FGPPPoEMCInUnknownProtos OBJECT-TYPE
   SYNTAX      Counter64
   MAX-ACCESS  read-only
   STATUS      current
   DESCRIPTION
      "Path: ethernet2.performance.pppoEClient.mibCounters.ifInUnknownProtos

       64 bit unsigned wrappable counter."
   ::= {pr1645v2Lan2FGPPPoEEntry 41025536}

pr1645v2Lan2FGPPPoEMCInDropEx OBJECT-TYPE
   SYNTAX      Counter64
   MAX-ACCESS  read-only
   STATUS      current
   DESCRIPTION
      "Path: ethernet2.performance.pppoEClient.mibCounters.ifInDropLevelExceeded

       64 bit unsigned wrappable counter."
   ::= {pr1645v2Lan2FGPPPoEEntry 42074112}

pr1645v2Lan2FGPPPoEMCInDropNoMac OBJECT-TYPE
   SYNTAX      Counter64
   MAX-ACCESS  read-only
   STATUS      current
   DESCRIPTION
      "Path: ethernet2.performance.pppoEClient.mibCounters.ifInDiscardsNoMacFit

       64 bit unsigned wrappable counter."
   ::= {pr1645v2Lan2FGPPPoEEntry 42270720}

pr1645v2Lan2FGPPPoEMCInDropNUCast OBJECT-TYPE
   SYNTAX      Counter64
   MAX-ACCESS  read-only
   STATUS      current
   DESCRIPTION
      "Path: ethernet2.performance.pppoEClient.mibCounters.ifInDiscardsNUCast

       64 bit unsigned wrappable counter."
   ::= {pr1645v2Lan2FGPPPoEEntry 42467328}

pr1645v2Lan2FGPPPoEMCInDropFilter OBJECT-TYPE
   SYNTAX      Counter64
   MAX-ACCESS  read-only
   STATUS      current
   DESCRIPTION
      "Path: ethernet2.performance.pppoEClient.mibCounters.ifInDiscardsFilter

       64 bit unsigned wrappable counter."
   ::= {pr1645v2Lan2FGPPPoEEntry 42532864}

pr1645v2Lan2FGPPPoEMCInBandwidth15sec OBJECT-TYPE
   SYNTAX      Integer32
   MAX-ACCESS  read-only
   STATUS      current
   DESCRIPTION
      "Path: ethernet2.performance.pppoEClient.mibCounters.ifInBandwidth.15sec

       unit name = bps
       formula = 8 * ; 8 /"
   ::= {pr1645v2Lan2FGPPPoEEntry 45417728}

pr1645v2Lan2FGPPPoEMCInBandwidth30sec OBJECT-TYPE
   SYNTAX      Integer32
   MAX-ACCESS  read-only
   STATUS      current
   DESCRIPTION
      "Path: ethernet2.performance.pppoEClient.mibCounters.ifInBandwidth.30sec

       unit name = bps
       formula = 8 * ; 8 /"
   ::= {pr1645v2Lan2FGPPPoEEntry 45419008}

pr1645v2Lan2FGPPPoEMCInBandwidth1min OBJECT-TYPE
   SYNTAX      Integer32
   MAX-ACCESS  read-only
   STATUS      current
   DESCRIPTION
      "Path: ethernet2.performance.pppoEClient.mibCounters.ifInBandwidth.1min

       unit name = bps
       formula = 8 * ; 8 /"
   ::= {pr1645v2Lan2FGPPPoEEntry 45421568}

pr1645v2Lan2FGPPPoEMCInBandwidth2min OBJECT-TYPE
   SYNTAX      Integer32
   MAX-ACCESS  read-only
   STATUS      current
   DESCRIPTION
      "Path: ethernet2.performance.pppoEClient.mibCounters.ifInBandwidth.2min

       unit name = bps
       formula = 8 * ; 8 /"
   ::= {pr1645v2Lan2FGPPPoEEntry 45426688}

pr1645v2Lan2FGPPPoEMCInBandwidth5min OBJECT-TYPE
   SYNTAX      Integer32
   MAX-ACCESS  read-only
   STATUS      current
   DESCRIPTION
      "Path: ethernet2.performance.pppoEClient.mibCounters.ifInBandwidth.5min

       unit name = bps
       formula = 8 * ; 8 /"
   ::= {pr1645v2Lan2FGPPPoEEntry 45442048}

pr1645v2Lan2FGPPPoEMCOutOctets OBJECT-TYPE
   SYNTAX      Counter64
   MAX-ACCESS  read-only
   STATUS      current
   DESCRIPTION
      "Path: ethernet2.performance.pppoEClient.mibCounters.ifOutOctets

       64 bit unsigned wrappable counter."
   ::= {pr1645v2Lan2FGPPPoEEntry 41091072}

pr1645v2Lan2FGPPPoEMCOutUcastPkts OBJECT-TYPE
   SYNTAX      Counter64
   MAX-ACCESS  read-only
   STATUS      current
   DESCRIPTION
      "Path: ethernet2.performance.pppoEClient.mibCounters.ifOutUcastPkts

       64 bit unsigned wrappable counter."
   ::= {pr1645v2Lan2FGPPPoEEntry 41156608}

pr1645v2Lan2FGPPPoEMCOutNUcastPkts OBJECT-TYPE
   SYNTAX      Counter64
   MAX-ACCESS  read-only
   STATUS      current
   DESCRIPTION
      "Path: ethernet2.performance.pppoEClient.mibCounters.ifOutNUcastPkts

       64 bit unsigned wrappable counter."
   ::= {pr1645v2Lan2FGPPPoEEntry 41222144}

pr1645v2Lan2FGPPPoEMCOutBcastPkts OBJECT-TYPE
   SYNTAX      Counter64
   MAX-ACCESS  read-only
   STATUS      current
   DESCRIPTION
      "Path: ethernet2.performance.pppoEClient.mibCounters.ifOutBcastPkts

       64 bit unsigned wrappable counter."
   ::= {pr1645v2Lan2FGPPPoEEntry 47775744}

pr1645v2Lan2FGPPPoEMCOutMcastPkts OBJECT-TYPE
   SYNTAX      Counter64
   MAX-ACCESS  read-only
   STATUS      current
   DESCRIPTION
      "Path: ethernet2.performance.pppoEClient.mibCounters.ifOutMcastPkts

       64 bit unsigned wrappable counter."
   ::= {pr1645v2Lan2FGPPPoEEntry 48431104}

pr1645v2Lan2FGPPPoEMCOutDiscards OBJECT-TYPE
   SYNTAX      Counter64
   MAX-ACCESS  read-only
   STATUS      current
   DESCRIPTION
      "Path: ethernet2.performance.pppoEClient.mibCounters.ifOutDiscards

       64 bit unsigned wrappable counter."
   ::= {pr1645v2Lan2FGPPPoEEntry 41287680}

pr1645v2Lan2FGPPPoEMCOutErrors OBJECT-TYPE
   SYNTAX      Counter64
   MAX-ACCESS  read-only
   STATUS      current
   DESCRIPTION
      "Path: ethernet2.performance.pppoEClient.mibCounters.ifOutErrors

       64 bit unsigned wrappable counter."
   ::= {pr1645v2Lan2FGPPPoEEntry 41353216}

pr1645v2Lan2FGPPPoEMCOutQLen OBJECT-TYPE
   SYNTAX      Counter32
   MAX-ACCESS  read-only
   STATUS      current
   DESCRIPTION
      "Path: ethernet2.performance.pppoEClient.mibCounters.ifOutQLen

       32 bit unsigned wrappable counter."
   ::= {pr1645v2Lan2FGPPPoEEntry 41418752}

pr1645v2Lan2FGPPPoEMCOutDropEx OBJECT-TYPE
   SYNTAX      Counter64
   MAX-ACCESS  read-only
   STATUS      current
   DESCRIPTION
      "Path: ethernet2.performance.pppoEClient.mibCounters.ifOutDropLevelExceeded

       64 bit unsigned wrappable counter."
   ::= {pr1645v2Lan2FGPPPoEEntry 41484288}

pr1645v2Lan2FGPPPoEMCOutDropNoArp OBJECT-TYPE
   SYNTAX      Counter64
   MAX-ACCESS  read-only
   STATUS      current
   DESCRIPTION
      "Path: ethernet2.performance.pppoEClient.mibCounters.ifOutDiscardsNoArp

       64 bit unsigned wrappable counter."
   ::= {pr1645v2Lan2FGPPPoEEntry 42336256}

pr1645v2Lan2FGPPPoEMCOutDropFilter OBJECT-TYPE
   SYNTAX      Counter64
   MAX-ACCESS  read-only
   STATUS      current
   DESCRIPTION
      "Path: ethernet2.performance.pppoEClient.mibCounters.ifOutDiscardsFilter

       64 bit unsigned wrappable counter."
   ::= {pr1645v2Lan2FGPPPoEEntry 42598400}

pr1645v2Lan2FGPPPoEMCOutBandwidth15sec OBJECT-TYPE
   SYNTAX      Integer32
   MAX-ACCESS  read-only
   STATUS      current
   DESCRIPTION
      "Path: ethernet2.performance.pppoEClient.mibCounters.ifOutBandwidth.15sec

       unit name = bps
       formula = 8 * ; 8 /"
   ::= {pr1645v2Lan2FGPPPoEEntry 45483264}

pr1645v2Lan2FGPPPoEMCOutBandwidth30sec OBJECT-TYPE
   SYNTAX      Integer32
   MAX-ACCESS  read-only
   STATUS      current
   DESCRIPTION
      "Path: ethernet2.performance.pppoEClient.mibCounters.ifOutBandwidth.30sec

       unit name = bps
       formula = 8 * ; 8 /"
   ::= {pr1645v2Lan2FGPPPoEEntry 45484544}

pr1645v2Lan2FGPPPoEMCOutBandwidth1min OBJECT-TYPE
   SYNTAX      Integer32
   MAX-ACCESS  read-only
   STATUS      current
   DESCRIPTION
      "Path: ethernet2.performance.pppoEClient.mibCounters.ifOutBandwidth.1min

       unit name = bps
       formula = 8 * ; 8 /"
   ::= {pr1645v2Lan2FGPPPoEEntry 45487104}

pr1645v2Lan2FGPPPoEMCOutBandwidth2min OBJECT-TYPE
   SYNTAX      Integer32
   MAX-ACCESS  read-only
   STATUS      current
   DESCRIPTION
      "Path: ethernet2.performance.pppoEClient.mibCounters.ifOutBandwidth.2min

       unit name = bps
       formula = 8 * ; 8 /"
   ::= {pr1645v2Lan2FGPPPoEEntry 45492224}

pr1645v2Lan2FGPPPoEMCOutBandwidth5min OBJECT-TYPE
   SYNTAX      Integer32
   MAX-ACCESS  read-only
   STATUS      current
   DESCRIPTION
      "Path: ethernet2.performance.pppoEClient.mibCounters.ifOutBandwidth.5min

       unit name = bps
       formula = 8 * ; 8 /"
   ::= {pr1645v2Lan2FGPPPoEEntry 45507584}

pr1645v2Lan2FGPPPoEPppLinkMonitoringRequestsSent OBJECT-TYPE
   SYNTAX      Gauge32
   MAX-ACCESS  read-only
   STATUS      current
   DESCRIPTION
      "Path: ethernet2.performance.pppoEClient.ppp.linkMonitoring.requestsSent

       32 bit unsigned gauge value."
   ::= {pr1645v2Lan2FGPPPoEEntry 50397440}

pr1645v2Lan2FGPPPoEPppLinkMonitoringRepliesRcvd OBJECT-TYPE
   SYNTAX      Gauge32
   MAX-ACCESS  read-only
   STATUS      current
   DESCRIPTION
      "Path: ethernet2.performance.pppoEClient.ppp.linkMonitoring.repliesRcvd

       32 bit unsigned gauge value."
   ::= {pr1645v2Lan2FGPPPoEEntry 50397696}

pr1645v2Lan2FGPPPoEPppLinkMonitoringRequestsRcvd OBJECT-TYPE
   SYNTAX      Gauge32
   MAX-ACCESS  read-only
   STATUS      current
   DESCRIPTION
      "Path: ethernet2.performance.pppoEClient.ppp.linkMonitoring.requestsRcvd

       32 bit unsigned gauge value."
   ::= {pr1645v2Lan2FGPPPoEEntry 50397952}

pr1645v2Lan2FGPPPoEPppLinkMonitoringRepliesSent OBJECT-TYPE
   SYNTAX      Gauge32
   MAX-ACCESS  read-only
   STATUS      current
   DESCRIPTION
      "Path: ethernet2.performance.pppoEClient.ppp.linkMonitoring.repliesSent

       32 bit unsigned gauge value."
   ::= {pr1645v2Lan2FGPPPoEEntry 50398208}

pr1645v2Lan2FGPPPoEMCH2P OBJECT-TYPE
   SYNTAX      SEQUENCE OF Pr1645v2Lan2FGPPPoEMCH2PEntry
   MAX-ACCESS  not-accessible
   STATUS      current
   DESCRIPTION
      ""
   ::= {pr1645v2Lan2FGPPPoE 41549824}

pr1645v2Lan2FGPPPoEMCH2PEntry OBJECT-TYPE
   SYNTAX      Pr1645v2Lan2FGPPPoEMCH2PEntry
   MAX-ACCESS  not-accessible
   STATUS      current
   DESCRIPTION
      ""
   INDEX      { pr1645v2Lan2FGPPPoETableIx,
                pr1645v2Lan2FGPPPoEMCH2PTableIx }
   ::= {pr1645v2Lan2FGPPPoEMCH2P 1}

Pr1645v2Lan2FGPPPoEMCH2PEntry ::=
   SEQUENCE
      {
      pr1645v2Lan2FGPPPoEMCH2PTableIx
         TableIndex,
      pr1645v2Lan2FGPPPoEMCH2PSysUpTime
         TimeTicks,
      pr1645v2Lan2FGPPPoEMCH2PIfUpTime
         TimeTicks,
      pr1645v2Lan2FGPPPoEMCH2PIfStatChanges
         Counter32,
      pr1645v2Lan2FGPPPoEMCH2PIfInOctets
         Counter64,
      pr1645v2Lan2FGPPPoEMCH2PIfInUCPkts
         Counter64,
      pr1645v2Lan2FGPPPoEMCH2PIfInNUCPkts
         Counter64,
      pr1645v2Lan2FGPPPoEMCH2PIfInBCPkts
         Counter64,
      pr1645v2Lan2FGPPPoEMCH2PIfInMCPkts
         Counter64,
      pr1645v2Lan2FGPPPoEMCH2PIfInDiscards
         Counter64,
      pr1645v2Lan2FGPPPoEMCH2PIfInErrors
         Counter64,
      pr1645v2Lan2FGPPPoEMCH2PIfInUnkwn
         Counter64,
      pr1645v2Lan2FGPPPoEMCH2PInDropEx
         Counter64,
      pr1645v2Lan2FGPPPoEMCH2PInDropNoMac
         Counter64,
      pr1645v2Lan2FGPPPoEMCH2PInDropNUCast
         Counter64,
      pr1645v2Lan2FGPPPoEMCH2PInDropFilter
         Counter64,
      pr1645v2Lan2FGPPPoEMCH2PIfInBandwidth
         Integer32,
      pr1645v2Lan2FGPPPoEMCH2PIfOutOctets
         Counter64,
      pr1645v2Lan2FGPPPoEMCH2PIfOutUCPkts
         Counter64,
      pr1645v2Lan2FGPPPoEMCH2PIfOutNUCPkts
         Counter64,
      pr1645v2Lan2FGPPPoEMCH2PIfOutBCPkts
         Counter64,
      pr1645v2Lan2FGPPPoEMCH2PIfOutMCPkts
         Counter64,
      pr1645v2Lan2FGPPPoEMCH2PIfOutDiscards
         Counter64,
      pr1645v2Lan2FGPPPoEMCH2PIfOutErrors
         Counter64,
      pr1645v2Lan2FGPPPoEMCH2POutDropEx
         Counter64,
      pr1645v2Lan2FGPPPoEMCH2POutDropNoArp
         Counter64,
      pr1645v2Lan2FGPPPoEMCH2POutDropFilter
         Counter64,
      pr1645v2Lan2FGPPPoEMCH2PIfOutBandwidth
         Integer32,
      pr1645v2Lan2FGPPPoEMCH2PIfErrSec
         Counter32
      }

pr1645v2Lan2FGPPPoEMCH2PTableIx OBJECT-TYPE
   SYNTAX      TableIndex
   MAX-ACCESS  not-accessible
   STATUS      current
   DESCRIPTION
      ""
   ::= {pr1645v2Lan2FGPPPoEMCH2PEntry 11}

pr1645v2Lan2FGPPPoEMCH2PSysUpTime OBJECT-TYPE
   SYNTAX      TimeTicks
   MAX-ACCESS  read-only
   STATUS      current
   DESCRIPTION
      "Path: ethernet2.performance.pppoEClient.mibCounters.h2Performance.sysUpTime

       Time in centi-second."
   ::= {pr1645v2Lan2FGPPPoEMCH2PEntry 16777216}

pr1645v2Lan2FGPPPoEMCH2PIfUpTime OBJECT-TYPE
   SYNTAX      TimeTicks
   MAX-ACCESS  read-only
   STATUS      current
   DESCRIPTION
      "Path: ethernet2.performance.pppoEClient.mibCounters.h2Performance.ifUpTime

       Time in centi-second."
   ::= {pr1645v2Lan2FGPPPoEMCH2PEntry 33554432}

pr1645v2Lan2FGPPPoEMCH2PIfStatChanges OBJECT-TYPE
   SYNTAX      Counter32
   MAX-ACCESS  read-only
   STATUS      current
   DESCRIPTION
      "Path: ethernet2.performance.pppoEClient.mibCounters.h2Performance.ifStatusChanges

       32 bit unsigned wrappable counter."
   ::= {pr1645v2Lan2FGPPPoEMCH2PEntry 50331648}

pr1645v2Lan2FGPPPoEMCH2PIfInOctets OBJECT-TYPE
   SYNTAX      Counter64
   MAX-ACCESS  read-only
   STATUS      current
   DESCRIPTION
      "Path: ethernet2.performance.pppoEClient.mibCounters.h2Performance.ifInOctets

       64 bit unsigned wrappable counter."
   ::= {pr1645v2Lan2FGPPPoEMCH2PEntry 67108864}

pr1645v2Lan2FGPPPoEMCH2PIfInUCPkts OBJECT-TYPE
   SYNTAX      Counter64
   MAX-ACCESS  read-only
   STATUS      current
   DESCRIPTION
      "Path: ethernet2.performance.pppoEClient.mibCounters.h2Performance.ifInUcastPkts

       64 bit unsigned wrappable counter."
   ::= {pr1645v2Lan2FGPPPoEMCH2PEntry 83886080}

pr1645v2Lan2FGPPPoEMCH2PIfInNUCPkts OBJECT-TYPE
   SYNTAX      Counter64
   MAX-ACCESS  read-only
   STATUS      current
   DESCRIPTION
      "Path: ethernet2.performance.pppoEClient.mibCounters.h2Performance.ifInNUcastPkts

       64 bit unsigned wrappable counter."
   ::= {pr1645v2Lan2FGPPPoEMCH2PEntry 100663296}

pr1645v2Lan2FGPPPoEMCH2PIfInBCPkts OBJECT-TYPE
   SYNTAX      Counter64
   MAX-ACCESS  read-only
   STATUS      current
   DESCRIPTION
      "Path: ethernet2.performance.pppoEClient.mibCounters.h2Performance.ifInBcastPkts

       64 bit unsigned wrappable counter."
   ::= {pr1645v2Lan2FGPPPoEMCH2PEntry 419430400}

pr1645v2Lan2FGPPPoEMCH2PIfInMCPkts OBJECT-TYPE
   SYNTAX      Counter64
   MAX-ACCESS  read-only
   STATUS      current
   DESCRIPTION
      "Path: ethernet2.performance.pppoEClient.mibCounters.h2Performance.ifInMcastPkts

       64 bit unsigned wrappable counter."
   ::= {pr1645v2Lan2FGPPPoEMCH2PEntry 436207616}

pr1645v2Lan2FGPPPoEMCH2PIfInDiscards OBJECT-TYPE
   SYNTAX      Counter64
   MAX-ACCESS  read-only
   STATUS      current
   DESCRIPTION
      "Path: ethernet2.performance.pppoEClient.mibCounters.h2Performance.ifInDiscards

       64 bit unsigned wrappable counter."
   ::= {pr1645v2Lan2FGPPPoEMCH2PEntry 117440512}

pr1645v2Lan2FGPPPoEMCH2PIfInErrors OBJECT-TYPE
   SYNTAX      Counter64
   MAX-ACCESS  read-only
   STATUS      current
   DESCRIPTION
      "Path: ethernet2.performance.pppoEClient.mibCounters.h2Performance.ifInErrors

       64 bit unsigned wrappable counter."
   ::= {pr1645v2Lan2FGPPPoEMCH2PEntry 134217728}

pr1645v2Lan2FGPPPoEMCH2PIfInUnkwn OBJECT-TYPE
   SYNTAX      Counter64
   MAX-ACCESS  read-only
   STATUS      current
   DESCRIPTION
      "Path: ethernet2.performance.pppoEClient.mibCounters.h2Performance.ifInUnknownProtos

       64 bit unsigned wrappable counter."
   ::= {pr1645v2Lan2FGPPPoEMCH2PEntry 150994944}

pr1645v2Lan2FGPPPoEMCH2PInDropEx OBJECT-TYPE
   SYNTAX      Counter64
   MAX-ACCESS  read-only
   STATUS      current
   DESCRIPTION
      "Path: ethernet2.performance.pppoEClient.mibCounters.h2Performance.ifInDropLevelExceeded

       64 bit unsigned wrappable counter."
   ::= {pr1645v2Lan2FGPPPoEMCH2PEntry 335544320}

pr1645v2Lan2FGPPPoEMCH2PInDropNoMac OBJECT-TYPE
   SYNTAX      Counter64
   MAX-ACCESS  read-only
   STATUS      current
   DESCRIPTION
      "Path: ethernet2.performance.pppoEClient.mibCounters.h2Performance.fInDiscardsNoMacFit

       64 bit unsigned wrappable counter."
   ::= {pr1645v2Lan2FGPPPoEMCH2PEntry 301989888}

pr1645v2Lan2FGPPPoEMCH2PInDropNUCast OBJECT-TYPE
   SYNTAX      Counter64
   MAX-ACCESS  read-only
   STATUS      current
   DESCRIPTION
      "Path: ethernet2.performance.pppoEClient.mibCounters.h2Performance.fInDiscardsNUCast

       64 bit unsigned wrappable counter."
   ::= {pr1645v2Lan2FGPPPoEMCH2PEntry 318767104}

pr1645v2Lan2FGPPPoEMCH2PInDropFilter OBJECT-TYPE
   SYNTAX      Counter64
   MAX-ACCESS  read-only
   STATUS      current
   DESCRIPTION
      "Path: ethernet2.performance.pppoEClient.mibCounters.h2Performance.fInDiscardsFilter

       64 bit unsigned wrappable counter."
   ::= {pr1645v2Lan2FGPPPoEMCH2PEntry 385875968}

pr1645v2Lan2FGPPPoEMCH2PIfInBandwidth OBJECT-TYPE
   SYNTAX      Integer32
   MAX-ACCESS  read-only
   STATUS      current
   DESCRIPTION
      "Path: ethernet2.performance.pppoEClient.mibCounters.h2Performance.ifInBandwidth

       unit name = bps
       formula = 8 * ; 8 /"
   ::= {pr1645v2Lan2FGPPPoEMCH2PEntry 268435456}

pr1645v2Lan2FGPPPoEMCH2PIfOutOctets OBJECT-TYPE
   SYNTAX      Counter64
   MAX-ACCESS  read-only
   STATUS      current
   DESCRIPTION
      "Path: ethernet2.performance.pppoEClient.mibCounters.h2Performance.ifOutOctets

       64 bit unsigned wrappable counter."
   ::= {pr1645v2Lan2FGPPPoEMCH2PEntry 167772160}

pr1645v2Lan2FGPPPoEMCH2PIfOutUCPkts OBJECT-TYPE
   SYNTAX      Counter64
   MAX-ACCESS  read-only
   STATUS      current
   DESCRIPTION
      "Path: ethernet2.performance.pppoEClient.mibCounters.h2Performance.ifOutUcastPkts

       64 bit unsigned wrappable counter."
   ::= {pr1645v2Lan2FGPPPoEMCH2PEntry 184549376}

pr1645v2Lan2FGPPPoEMCH2PIfOutNUCPkts OBJECT-TYPE
   SYNTAX      Counter64
   MAX-ACCESS  read-only
   STATUS      current
   DESCRIPTION
      "Path: ethernet2.performance.pppoEClient.mibCounters.h2Performance.ifOutNUcastPkts

       64 bit unsigned wrappable counter."
   ::= {pr1645v2Lan2FGPPPoEMCH2PEntry 201326592}

pr1645v2Lan2FGPPPoEMCH2PIfOutBCPkts OBJECT-TYPE
   SYNTAX      Counter64
   MAX-ACCESS  read-only
   STATUS      current
   DESCRIPTION
      "Path: ethernet2.performance.pppoEClient.mibCounters.h2Performance.ifOutBcastPkts

       64 bit unsigned wrappable counter."
   ::= {pr1645v2Lan2FGPPPoEMCH2PEntry 452984832}

pr1645v2Lan2FGPPPoEMCH2PIfOutMCPkts OBJECT-TYPE
   SYNTAX      Counter64
   MAX-ACCESS  read-only
   STATUS      current
   DESCRIPTION
      "Path: ethernet2.performance.pppoEClient.mibCounters.h2Performance.ifOutMcastPkts

       64 bit unsigned wrappable counter."
   ::= {pr1645v2Lan2FGPPPoEMCH2PEntry 469762048}

pr1645v2Lan2FGPPPoEMCH2PIfOutDiscards OBJECT-TYPE
   SYNTAX      Counter64
   MAX-ACCESS  read-only
   STATUS      current
   DESCRIPTION
      "Path: ethernet2.performance.pppoEClient.mibCounters.h2Performance.ifOutDiscards

       64 bit unsigned wrappable counter."
   ::= {pr1645v2Lan2FGPPPoEMCH2PEntry 218103808}

pr1645v2Lan2FGPPPoEMCH2PIfOutErrors OBJECT-TYPE
   SYNTAX      Counter64
   MAX-ACCESS  read-only
   STATUS      current
   DESCRIPTION
      "Path: ethernet2.performance.pppoEClient.mibCounters.h2Performance.ifOutErrors

       64 bit unsigned wrappable counter."
   ::= {pr1645v2Lan2FGPPPoEMCH2PEntry 234881024}

pr1645v2Lan2FGPPPoEMCH2POutDropEx OBJECT-TYPE
   SYNTAX      Counter64
   MAX-ACCESS  read-only
   STATUS      current
   DESCRIPTION
      "Path: ethernet2.performance.pppoEClient.mibCounters.h2Performance.ifOutDropLevelExceeded

       64 bit unsigned wrappable counter."
   ::= {pr1645v2Lan2FGPPPoEMCH2PEntry 352321536}

pr1645v2Lan2FGPPPoEMCH2POutDropNoArp OBJECT-TYPE
   SYNTAX      Counter64
   MAX-ACCESS  read-only
   STATUS      current
   DESCRIPTION
      "Path: ethernet2.performance.pppoEClient.mibCounters.h2Performance.ifOutDiscardsNoArp

       64 bit unsigned wrappable counter."
   ::= {pr1645v2Lan2FGPPPoEMCH2PEntry 369098752}

pr1645v2Lan2FGPPPoEMCH2POutDropFilter OBJECT-TYPE
   SYNTAX      Counter64
   MAX-ACCESS  read-only
   STATUS      current
   DESCRIPTION
      "Path: ethernet2.performance.pppoEClient.mibCounters.h2Performance.ifOutDiscardsFilter

       64 bit unsigned wrappable counter."
   ::= {pr1645v2Lan2FGPPPoEMCH2PEntry 402653184}

pr1645v2Lan2FGPPPoEMCH2PIfOutBandwidth OBJECT-TYPE
   SYNTAX      Integer32
   MAX-ACCESS  read-only
   STATUS      current
   DESCRIPTION
      "Path: ethernet2.performance.pppoEClient.mibCounters.h2Performance.ifOutBandwidth

       unit name = bps
       formula = 8 * ; 8 /"
   ::= {pr1645v2Lan2FGPPPoEMCH2PEntry 285212672}

pr1645v2Lan2FGPPPoEMCH2PIfErrSec OBJECT-TYPE
   SYNTAX      Counter32
   MAX-ACCESS  read-only
   STATUS      current
   DESCRIPTION
      "Path: ethernet2.performance.pppoEClient.mibCounters.h2Performance.ifErrSec

       32 bit unsigned wrappable counter."
   ::= {pr1645v2Lan2FGPPPoEMCH2PEntry 251658240}

pr1645v2Lan2FGPPPoEMCH24P OBJECT-TYPE
   SYNTAX      SEQUENCE OF Pr1645v2Lan2FGPPPoEMCH24PEntry
   MAX-ACCESS  not-accessible
   STATUS      current
   DESCRIPTION
      ""
   ::= {pr1645v2Lan2FGPPPoE 41615360}

pr1645v2Lan2FGPPPoEMCH24PEntry OBJECT-TYPE
   SYNTAX      Pr1645v2Lan2FGPPPoEMCH24PEntry
   MAX-ACCESS  not-accessible
   STATUS      current
   DESCRIPTION
      ""
   INDEX      { pr1645v2Lan2FGPPPoETableIx,
                pr1645v2Lan2FGPPPoEMCH24PTableIx }
   ::= {pr1645v2Lan2FGPPPoEMCH24P 1}

Pr1645v2Lan2FGPPPoEMCH24PEntry ::=
   SEQUENCE
      {
      pr1645v2Lan2FGPPPoEMCH24PTableIx
         TableIndex,
      pr1645v2Lan2FGPPPoEMCH24PSysUpTime
         TimeTicks,
      pr1645v2Lan2FGPPPoEMCH24PIfUpTime
         TimeTicks,
      pr1645v2Lan2FGPPPoEMCH24PIfStatChanges
         Counter32,
      pr1645v2Lan2FGPPPoEMCH24PIfInOctets
         Counter64,
      pr1645v2Lan2FGPPPoEMCH24PIfInUCPkts
         Counter64,
      pr1645v2Lan2FGPPPoEMCH24PIfInNUCPkts
         Counter64,
      pr1645v2Lan2FGPPPoEMCH24PIfInBCPkts
         Counter64,
      pr1645v2Lan2FGPPPoEMCH24PIfInMCPkts
         Counter64,
      pr1645v2Lan2FGPPPoEMCH24PIfInDiscards
         Counter64,
      pr1645v2Lan2FGPPPoEMCH24PIfInErrors
         Counter64,
      pr1645v2Lan2FGPPPoEMCH24PIfInUnkwn
         Counter64,
      pr1645v2Lan2FGPPPoEMCH24PInDropEx
         Counter64,
      pr1645v2Lan2FGPPPoEMCH24PInDropNoMac
         Counter64,
      pr1645v2Lan2FGPPPoEMCH24PInDropNUCast
         Counter64,
      pr1645v2Lan2FGPPPoEMCH24PInDropFilter
         Counter64,
      pr1645v2Lan2FGPPPoEMCH24PIfInBandwidth
         Integer32,
      pr1645v2Lan2FGPPPoEMCH24PIfOutOctets
         Counter64,
      pr1645v2Lan2FGPPPoEMCH24PIfOutUCPkts
         Counter64,
      pr1645v2Lan2FGPPPoEMCH24PIfOutNUCPkts
         Counter64,
      pr1645v2Lan2FGPPPoEMCH24PIfOutBCPkts
         Counter64,
      pr1645v2Lan2FGPPPoEMCH24PIfOutMCPkts
         Counter64,
      pr1645v2Lan2FGPPPoEMCH24PIfOutDiscards
         Counter64,
      pr1645v2Lan2FGPPPoEMCH24PIfOutErrors
         Counter64,
      pr1645v2Lan2FGPPPoEMCH24POutDropEx
         Counter64,
      pr1645v2Lan2FGPPPoEMCH24POutDropNoArp
         Counter64,
      pr1645v2Lan2FGPPPoEMCH24POutDropFilter
         Counter64,
      pr1645v2Lan2FGPPPoEMCH24PIfOutBandwidth
         Integer32,
      pr1645v2Lan2FGPPPoEMCH24PIfErrSec
         Counter32
      }

pr1645v2Lan2FGPPPoEMCH24PTableIx OBJECT-TYPE
   SYNTAX      TableIndex
   MAX-ACCESS  not-accessible
   STATUS      current
   DESCRIPTION
      ""
   ::= {pr1645v2Lan2FGPPPoEMCH24PEntry 11}

pr1645v2Lan2FGPPPoEMCH24PSysUpTime OBJECT-TYPE
   SYNTAX      TimeTicks
   MAX-ACCESS  read-only
   STATUS      current
   DESCRIPTION
      "Path: ethernet2.performance.pppoEClient.mibCounters.h24Performance.sysUpTime

       Time in centi-second."
   ::= {pr1645v2Lan2FGPPPoEMCH24PEntry 16777216}

pr1645v2Lan2FGPPPoEMCH24PIfUpTime OBJECT-TYPE
   SYNTAX      TimeTicks
   MAX-ACCESS  read-only
   STATUS      current
   DESCRIPTION
      "Path: ethernet2.performance.pppoEClient.mibCounters.h24Performance.ifUpTime

       Time in centi-second."
   ::= {pr1645v2Lan2FGPPPoEMCH24PEntry 33554432}

pr1645v2Lan2FGPPPoEMCH24PIfStatChanges OBJECT-TYPE
   SYNTAX      Counter32
   MAX-ACCESS  read-only
   STATUS      current
   DESCRIPTION
      "Path: ethernet2.performance.pppoEClient.mibCounters.h24Performance.ifStatusChanges

       32 bit unsigned wrappable counter."
   ::= {pr1645v2Lan2FGPPPoEMCH24PEntry 50331648}

pr1645v2Lan2FGPPPoEMCH24PIfInOctets OBJECT-TYPE
   SYNTAX      Counter64
   MAX-ACCESS  read-only
   STATUS      current
   DESCRIPTION
      "Path: ethernet2.performance.pppoEClient.mibCounters.h24Performance.ifInOctets

       64 bit unsigned wrappable counter."
   ::= {pr1645v2Lan2FGPPPoEMCH24PEntry 67108864}

pr1645v2Lan2FGPPPoEMCH24PIfInUCPkts OBJECT-TYPE
   SYNTAX      Counter64
   MAX-ACCESS  read-only
   STATUS      current
   DESCRIPTION
      "Path: ethernet2.performance.pppoEClient.mibCounters.h24Performance.ifInUcastPkts

       64 bit unsigned wrappable counter."
   ::= {pr1645v2Lan2FGPPPoEMCH24PEntry 83886080}

pr1645v2Lan2FGPPPoEMCH24PIfInNUCPkts OBJECT-TYPE
   SYNTAX      Counter64
   MAX-ACCESS  read-only
   STATUS      current
   DESCRIPTION
      "Path: ethernet2.performance.pppoEClient.mibCounters.h24Performance.ifInNUcastPkts

       64 bit unsigned wrappable counter."
   ::= {pr1645v2Lan2FGPPPoEMCH24PEntry 100663296}

pr1645v2Lan2FGPPPoEMCH24PIfInBCPkts OBJECT-TYPE
   SYNTAX      Counter64
   MAX-ACCESS  read-only
   STATUS      current
   DESCRIPTION
      "Path: ethernet2.performance.pppoEClient.mibCounters.h24Performance.ifInBcastPkts

       64 bit unsigned wrappable counter."
   ::= {pr1645v2Lan2FGPPPoEMCH24PEntry 419430400}

pr1645v2Lan2FGPPPoEMCH24PIfInMCPkts OBJECT-TYPE
   SYNTAX      Counter64
   MAX-ACCESS  read-only
   STATUS      current
   DESCRIPTION
      "Path: ethernet2.performance.pppoEClient.mibCounters.h24Performance.ifInMcastPkts

       64 bit unsigned wrappable counter."
   ::= {pr1645v2Lan2FGPPPoEMCH24PEntry 436207616}

pr1645v2Lan2FGPPPoEMCH24PIfInDiscards OBJECT-TYPE
   SYNTAX      Counter64
   MAX-ACCESS  read-only
   STATUS      current
   DESCRIPTION
      "Path: ethernet2.performance.pppoEClient.mibCounters.h24Performance.ifInDiscards

       64 bit unsigned wrappable counter."
   ::= {pr1645v2Lan2FGPPPoEMCH24PEntry 117440512}

pr1645v2Lan2FGPPPoEMCH24PIfInErrors OBJECT-TYPE
   SYNTAX      Counter64
   MAX-ACCESS  read-only
   STATUS      current
   DESCRIPTION
      "Path: ethernet2.performance.pppoEClient.mibCounters.h24Performance.ifInErrors

       64 bit unsigned wrappable counter."
   ::= {pr1645v2Lan2FGPPPoEMCH24PEntry 134217728}

pr1645v2Lan2FGPPPoEMCH24PIfInUnkwn OBJECT-TYPE
   SYNTAX      Counter64
   MAX-ACCESS  read-only
   STATUS      current
   DESCRIPTION
      "Path: ethernet2.performance.pppoEClient.mibCounters.h24Performance.ifInUnknownProtos

       64 bit unsigned wrappable counter."
   ::= {pr1645v2Lan2FGPPPoEMCH24PEntry 150994944}

pr1645v2Lan2FGPPPoEMCH24PInDropEx OBJECT-TYPE
   SYNTAX      Counter64
   MAX-ACCESS  read-only
   STATUS      current
   DESCRIPTION
      "Path: ethernet2.performance.pppoEClient.mibCounters.h24Performance.ifInDropLevelExceeded

       64 bit unsigned wrappable counter."
   ::= {pr1645v2Lan2FGPPPoEMCH24PEntry 335544320}

pr1645v2Lan2FGPPPoEMCH24PInDropNoMac OBJECT-TYPE
   SYNTAX      Counter64
   MAX-ACCESS  read-only
   STATUS      current
   DESCRIPTION
      "Path: ethernet2.performance.pppoEClient.mibCounters.h24Performance.fInDiscardsNoMacFit

       64 bit unsigned wrappable counter."
   ::= {pr1645v2Lan2FGPPPoEMCH24PEntry 301989888}

pr1645v2Lan2FGPPPoEMCH24PInDropNUCast OBJECT-TYPE
   SYNTAX      Counter64
   MAX-ACCESS  read-only
   STATUS      current
   DESCRIPTION
      "Path: ethernet2.performance.pppoEClient.mibCounters.h24Performance.fInDiscardsNUCast

       64 bit unsigned wrappable counter."
   ::= {pr1645v2Lan2FGPPPoEMCH24PEntry 318767104}

pr1645v2Lan2FGPPPoEMCH24PInDropFilter OBJECT-TYPE
   SYNTAX      Counter64
   MAX-ACCESS  read-only
   STATUS      current
   DESCRIPTION
      "Path: ethernet2.performance.pppoEClient.mibCounters.h24Performance.fInDiscardsFilter

       64 bit unsigned wrappable counter."
   ::= {pr1645v2Lan2FGPPPoEMCH24PEntry 385875968}

pr1645v2Lan2FGPPPoEMCH24PIfInBandwidth OBJECT-TYPE
   SYNTAX      Integer32
   MAX-ACCESS  read-only
   STATUS      current
   DESCRIPTION
      "Path: ethernet2.performance.pppoEClient.mibCounters.h24Performance.ifInBandwidth

       unit name = bps
       formula = 8 * ; 8 /"
   ::= {pr1645v2Lan2FGPPPoEMCH24PEntry 268435456}

pr1645v2Lan2FGPPPoEMCH24PIfOutOctets OBJECT-TYPE
   SYNTAX      Counter64
   MAX-ACCESS  read-only
   STATUS      current
   DESCRIPTION
      "Path: ethernet2.performance.pppoEClient.mibCounters.h24Performance.ifOutOctets

       64 bit unsigned wrappable counter."
   ::= {pr1645v2Lan2FGPPPoEMCH24PEntry 167772160}

pr1645v2Lan2FGPPPoEMCH24PIfOutUCPkts OBJECT-TYPE
   SYNTAX      Counter64
   MAX-ACCESS  read-only
   STATUS      current
   DESCRIPTION
      "Path: ethernet2.performance.pppoEClient.mibCounters.h24Performance.ifOutUcastPkts

       64 bit unsigned wrappable counter."
   ::= {pr1645v2Lan2FGPPPoEMCH24PEntry 184549376}

pr1645v2Lan2FGPPPoEMCH24PIfOutNUCPkts OBJECT-TYPE
   SYNTAX      Counter64
   MAX-ACCESS  read-only
   STATUS      current
   DESCRIPTION
      "Path: ethernet2.performance.pppoEClient.mibCounters.h24Performance.ifOutNUcastPkts

       64 bit unsigned wrappable counter."
   ::= {pr1645v2Lan2FGPPPoEMCH24PEntry 201326592}

pr1645v2Lan2FGPPPoEMCH24PIfOutBCPkts OBJECT-TYPE
   SYNTAX      Counter64
   MAX-ACCESS  read-only
   STATUS      current
   DESCRIPTION
      "Path: ethernet2.performance.pppoEClient.mibCounters.h24Performance.ifOutBcastPkts

       64 bit unsigned wrappable counter."
   ::= {pr1645v2Lan2FGPPPoEMCH24PEntry 452984832}

pr1645v2Lan2FGPPPoEMCH24PIfOutMCPkts OBJECT-TYPE
   SYNTAX      Counter64
   MAX-ACCESS  read-only
   STATUS      current
   DESCRIPTION
      "Path: ethernet2.performance.pppoEClient.mibCounters.h24Performance.ifOutMcastPkts

       64 bit unsigned wrappable counter."
   ::= {pr1645v2Lan2FGPPPoEMCH24PEntry 469762048}

pr1645v2Lan2FGPPPoEMCH24PIfOutDiscards OBJECT-TYPE
   SYNTAX      Counter64
   MAX-ACCESS  read-only
   STATUS      current
   DESCRIPTION
      "Path: ethernet2.performance.pppoEClient.mibCounters.h24Performance.ifOutDiscards

       64 bit unsigned wrappable counter."
   ::= {pr1645v2Lan2FGPPPoEMCH24PEntry 218103808}

pr1645v2Lan2FGPPPoEMCH24PIfOutErrors OBJECT-TYPE
   SYNTAX      Counter64
   MAX-ACCESS  read-only
   STATUS      current
   DESCRIPTION
      "Path: ethernet2.performance.pppoEClient.mibCounters.h24Performance.ifOutErrors

       64 bit unsigned wrappable counter."
   ::= {pr1645v2Lan2FGPPPoEMCH24PEntry 234881024}

pr1645v2Lan2FGPPPoEMCH24POutDropEx OBJECT-TYPE
   SYNTAX      Counter64
   MAX-ACCESS  read-only
   STATUS      current
   DESCRIPTION
      "Path: ethernet2.performance.pppoEClient.mibCounters.h24Performance.ifOutDropLevelExceeded

       64 bit unsigned wrappable counter."
   ::= {pr1645v2Lan2FGPPPoEMCH24PEntry 352321536}

pr1645v2Lan2FGPPPoEMCH24POutDropNoArp OBJECT-TYPE
   SYNTAX      Counter64
   MAX-ACCESS  read-only
   STATUS      current
   DESCRIPTION
      "Path: ethernet2.performance.pppoEClient.mibCounters.h24Performance.ifOutDiscardsNoArp

       64 bit unsigned wrappable counter."
   ::= {pr1645v2Lan2FGPPPoEMCH24PEntry 369098752}

pr1645v2Lan2FGPPPoEMCH24POutDropFilter OBJECT-TYPE
   SYNTAX      Counter64
   MAX-ACCESS  read-only
   STATUS      current
   DESCRIPTION
      "Path: ethernet2.performance.pppoEClient.mibCounters.h24Performance.ifOutDiscardsFilter

       64 bit unsigned wrappable counter."
   ::= {pr1645v2Lan2FGPPPoEMCH24PEntry 402653184}

pr1645v2Lan2FGPPPoEMCH24PIfOutBandwidth OBJECT-TYPE
   SYNTAX      Integer32
   MAX-ACCESS  read-only
   STATUS      current
   DESCRIPTION
      "Path: ethernet2.performance.pppoEClient.mibCounters.h24Performance.ifOutBandwidth

       unit name = bps
       formula = 8 * ; 8 /"
   ::= {pr1645v2Lan2FGPPPoEMCH24PEntry 285212672}

pr1645v2Lan2FGPPPoEMCH24PIfErrSec OBJECT-TYPE
   SYNTAX      Counter32
   MAX-ACCESS  read-only
   STATUS      current
   DESCRIPTION
      "Path: ethernet2.performance.pppoEClient.mibCounters.h24Performance.ifErrSec

       32 bit unsigned wrappable counter."
   ::= {pr1645v2Lan2FGPPPoEMCH24PEntry 251658240}

pr1645v2Lan2FGPPPoEMCD7P OBJECT-TYPE
   SYNTAX      SEQUENCE OF Pr1645v2Lan2FGPPPoEMCD7PEntry
   MAX-ACCESS  not-accessible
   STATUS      current
   DESCRIPTION
      ""
   ::= {pr1645v2Lan2FGPPPoE 41680896}

pr1645v2Lan2FGPPPoEMCD7PEntry OBJECT-TYPE
   SYNTAX      Pr1645v2Lan2FGPPPoEMCD7PEntry
   MAX-ACCESS  not-accessible
   STATUS      current
   DESCRIPTION
      ""
   INDEX      { pr1645v2Lan2FGPPPoETableIx,
                pr1645v2Lan2FGPPPoEMCD7PTableIx }
   ::= {pr1645v2Lan2FGPPPoEMCD7P 1}

Pr1645v2Lan2FGPPPoEMCD7PEntry ::=
   SEQUENCE
      {
      pr1645v2Lan2FGPPPoEMCD7PTableIx
         TableIndex,
      pr1645v2Lan2FGPPPoEMCD7PSysUpTime
         TimeTicks,
      pr1645v2Lan2FGPPPoEMCD7PIfUpTime
         TimeTicks,
      pr1645v2Lan2FGPPPoEMCD7PIfStatChanges
         Counter32,
      pr1645v2Lan2FGPPPoEMCD7PIfInOctets
         Counter64,
      pr1645v2Lan2FGPPPoEMCD7PIfInUCPkts
         Counter64,
      pr1645v2Lan2FGPPPoEMCD7PIfInNUCPkts
         Counter64,
      pr1645v2Lan2FGPPPoEMCD7PIfInBCPkts
         Counter64,
      pr1645v2Lan2FGPPPoEMCD7PIfInMCPkts
         Counter64,
      pr1645v2Lan2FGPPPoEMCD7PIfInDiscards
         Counter64,
      pr1645v2Lan2FGPPPoEMCD7PIfInErrors
         Counter64,
      pr1645v2Lan2FGPPPoEMCD7PIfInUnkwn
         Counter64,
      pr1645v2Lan2FGPPPoEMCD7PInDropEx
         Counter64,
      pr1645v2Lan2FGPPPoEMCD7PInDropNoMac
         Counter64,
      pr1645v2Lan2FGPPPoEMCD7PInDropNUCast
         Counter64,
      pr1645v2Lan2FGPPPoEMCD7PInDropFilter
         Counter64,
      pr1645v2Lan2FGPPPoEMCD7PIfInBandwidth
         Integer32,
      pr1645v2Lan2FGPPPoEMCD7PIfOutOctets
         Counter64,
      pr1645v2Lan2FGPPPoEMCD7PIfOutUCPkts
         Counter64,
      pr1645v2Lan2FGPPPoEMCD7PIfOutNUCPkts
         Counter64,
      pr1645v2Lan2FGPPPoEMCD7PIfOutBCPkts
         Counter64,
      pr1645v2Lan2FGPPPoEMCD7PIfOutMCPkts
         Counter64,
      pr1645v2Lan2FGPPPoEMCD7PIfOutDiscards
         Counter64,
      pr1645v2Lan2FGPPPoEMCD7PIfOutErrors
         Counter64,
      pr1645v2Lan2FGPPPoEMCD7POutDropEx
         Counter64,
      pr1645v2Lan2FGPPPoEMCD7POutDropNoArp
         Counter64,
      pr1645v2Lan2FGPPPoEMCD7POutDropFilter
         Counter64,
      pr1645v2Lan2FGPPPoEMCD7PIfOutBandwidth
         Integer32,
      pr1645v2Lan2FGPPPoEMCD7PIfErrSec
         Counter32
      }

pr1645v2Lan2FGPPPoEMCD7PTableIx OBJECT-TYPE
   SYNTAX      TableIndex
   MAX-ACCESS  not-accessible
   STATUS      current
   DESCRIPTION
      ""
   ::= {pr1645v2Lan2FGPPPoEMCD7PEntry 11}

pr1645v2Lan2FGPPPoEMCD7PSysUpTime OBJECT-TYPE
   SYNTAX      TimeTicks
   MAX-ACCESS  read-only
   STATUS      current
   DESCRIPTION
      "Path: ethernet2.performance.pppoEClient.mibCounters.d7Performance.sysUpTime

       Time in centi-second."
   ::= {pr1645v2Lan2FGPPPoEMCD7PEntry 16777216}

pr1645v2Lan2FGPPPoEMCD7PIfUpTime OBJECT-TYPE
   SYNTAX      TimeTicks
   MAX-ACCESS  read-only
   STATUS      current
   DESCRIPTION
      "Path: ethernet2.performance.pppoEClient.mibCounters.d7Performance.ifUpTime

       Time in centi-second."
   ::= {pr1645v2Lan2FGPPPoEMCD7PEntry 33554432}

pr1645v2Lan2FGPPPoEMCD7PIfStatChanges OBJECT-TYPE
   SYNTAX      Counter32
   MAX-ACCESS  read-only
   STATUS      current
   DESCRIPTION
      "Path: ethernet2.performance.pppoEClient.mibCounters.d7Performance.ifStatusChanges

       32 bit unsigned wrappable counter."
   ::= {pr1645v2Lan2FGPPPoEMCD7PEntry 50331648}

pr1645v2Lan2FGPPPoEMCD7PIfInOctets OBJECT-TYPE
   SYNTAX      Counter64
   MAX-ACCESS  read-only
   STATUS      current
   DESCRIPTION
      "Path: ethernet2.performance.pppoEClient.mibCounters.d7Performance.ifInOctets

       64 bit unsigned wrappable counter."
   ::= {pr1645v2Lan2FGPPPoEMCD7PEntry 67108864}

pr1645v2Lan2FGPPPoEMCD7PIfInUCPkts OBJECT-TYPE
   SYNTAX      Counter64
   MAX-ACCESS  read-only
   STATUS      current
   DESCRIPTION
      "Path: ethernet2.performance.pppoEClient.mibCounters.d7Performance.ifInUcastPkts

       64 bit unsigned wrappable counter."
   ::= {pr1645v2Lan2FGPPPoEMCD7PEntry 83886080}

pr1645v2Lan2FGPPPoEMCD7PIfInNUCPkts OBJECT-TYPE
   SYNTAX      Counter64
   MAX-ACCESS  read-only
   STATUS      current
   DESCRIPTION
      "Path: ethernet2.performance.pppoEClient.mibCounters.d7Performance.ifInNUcastPkts

       64 bit unsigned wrappable counter."
   ::= {pr1645v2Lan2FGPPPoEMCD7PEntry 100663296}

pr1645v2Lan2FGPPPoEMCD7PIfInBCPkts OBJECT-TYPE
   SYNTAX      Counter64
   MAX-ACCESS  read-only
   STATUS      current
   DESCRIPTION
      "Path: ethernet2.performance.pppoEClient.mibCounters.d7Performance.ifInBcastPkts

       64 bit unsigned wrappable counter."
   ::= {pr1645v2Lan2FGPPPoEMCD7PEntry 419430400}

pr1645v2Lan2FGPPPoEMCD7PIfInMCPkts OBJECT-TYPE
   SYNTAX      Counter64
   MAX-ACCESS  read-only
   STATUS      current
   DESCRIPTION
      "Path: ethernet2.performance.pppoEClient.mibCounters.d7Performance.ifInMcastPkts

       64 bit unsigned wrappable counter."
   ::= {pr1645v2Lan2FGPPPoEMCD7PEntry 436207616}

pr1645v2Lan2FGPPPoEMCD7PIfInDiscards OBJECT-TYPE
   SYNTAX      Counter64
   MAX-ACCESS  read-only
   STATUS      current
   DESCRIPTION
      "Path: ethernet2.performance.pppoEClient.mibCounters.d7Performance.ifInDiscards

       64 bit unsigned wrappable counter."
   ::= {pr1645v2Lan2FGPPPoEMCD7PEntry 117440512}

pr1645v2Lan2FGPPPoEMCD7PIfInErrors OBJECT-TYPE
   SYNTAX      Counter64
   MAX-ACCESS  read-only
   STATUS      current
   DESCRIPTION
      "Path: ethernet2.performance.pppoEClient.mibCounters.d7Performance.ifInErrors

       64 bit unsigned wrappable counter."
   ::= {pr1645v2Lan2FGPPPoEMCD7PEntry 134217728}

pr1645v2Lan2FGPPPoEMCD7PIfInUnkwn OBJECT-TYPE
   SYNTAX      Counter64
   MAX-ACCESS  read-only
   STATUS      current
   DESCRIPTION
      "Path: ethernet2.performance.pppoEClient.mibCounters.d7Performance.ifInUnknownProtos

       64 bit unsigned wrappable counter."
   ::= {pr1645v2Lan2FGPPPoEMCD7PEntry 150994944}

pr1645v2Lan2FGPPPoEMCD7PInDropEx OBJECT-TYPE
   SYNTAX      Counter64
   MAX-ACCESS  read-only
   STATUS      current
   DESCRIPTION
      "Path: ethernet2.performance.pppoEClient.mibCounters.d7Performance.ifInDropLevelExceeded

       64 bit unsigned wrappable counter."
   ::= {pr1645v2Lan2FGPPPoEMCD7PEntry 335544320}

pr1645v2Lan2FGPPPoEMCD7PInDropNoMac OBJECT-TYPE
   SYNTAX      Counter64
   MAX-ACCESS  read-only
   STATUS      current
   DESCRIPTION
      "Path: ethernet2.performance.pppoEClient.mibCounters.d7Performance.fInDiscardsNoMacFit

       64 bit unsigned wrappable counter."
   ::= {pr1645v2Lan2FGPPPoEMCD7PEntry 301989888}

pr1645v2Lan2FGPPPoEMCD7PInDropNUCast OBJECT-TYPE
   SYNTAX      Counter64
   MAX-ACCESS  read-only
   STATUS      current
   DESCRIPTION
      "Path: ethernet2.performance.pppoEClient.mibCounters.d7Performance.fInDiscardsNUCast

       64 bit unsigned wrappable counter."
   ::= {pr1645v2Lan2FGPPPoEMCD7PEntry 318767104}

pr1645v2Lan2FGPPPoEMCD7PInDropFilter OBJECT-TYPE
   SYNTAX      Counter64
   MAX-ACCESS  read-only
   STATUS      current
   DESCRIPTION
      "Path: ethernet2.performance.pppoEClient.mibCounters.d7Performance.fInDiscardsFilter

       64 bit unsigned wrappable counter."
   ::= {pr1645v2Lan2FGPPPoEMCD7PEntry 385875968}

pr1645v2Lan2FGPPPoEMCD7PIfInBandwidth OBJECT-TYPE
   SYNTAX      Integer32
   MAX-ACCESS  read-only
   STATUS      current
   DESCRIPTION
      "Path: ethernet2.performance.pppoEClient.mibCounters.d7Performance.ifInBandwidth

       unit name = bps
       formula = 8 * ; 8 /"
   ::= {pr1645v2Lan2FGPPPoEMCD7PEntry 268435456}

pr1645v2Lan2FGPPPoEMCD7PIfOutOctets OBJECT-TYPE
   SYNTAX      Counter64
   MAX-ACCESS  read-only
   STATUS      current
   DESCRIPTION
      "Path: ethernet2.performance.pppoEClient.mibCounters.d7Performance.ifOutOctets

       64 bit unsigned wrappable counter."
   ::= {pr1645v2Lan2FGPPPoEMCD7PEntry 167772160}

pr1645v2Lan2FGPPPoEMCD7PIfOutUCPkts OBJECT-TYPE
   SYNTAX      Counter64
   MAX-ACCESS  read-only
   STATUS      current
   DESCRIPTION
      "Path: ethernet2.performance.pppoEClient.mibCounters.d7Performance.ifOutUcastPkts

       64 bit unsigned wrappable counter."
   ::= {pr1645v2Lan2FGPPPoEMCD7PEntry 184549376}

pr1645v2Lan2FGPPPoEMCD7PIfOutNUCPkts OBJECT-TYPE
   SYNTAX      Counter64
   MAX-ACCESS  read-only
   STATUS      current
   DESCRIPTION
      "Path: ethernet2.performance.pppoEClient.mibCounters.d7Performance.ifOutNUcastPkts

       64 bit unsigned wrappable counter."
   ::= {pr1645v2Lan2FGPPPoEMCD7PEntry 201326592}

pr1645v2Lan2FGPPPoEMCD7PIfOutBCPkts OBJECT-TYPE
   SYNTAX      Counter64
   MAX-ACCESS  read-only
   STATUS      current
   DESCRIPTION
      "Path: ethernet2.performance.pppoEClient.mibCounters.d7Performance.ifOutBcastPkts

       64 bit unsigned wrappable counter."
   ::= {pr1645v2Lan2FGPPPoEMCD7PEntry 452984832}

pr1645v2Lan2FGPPPoEMCD7PIfOutMCPkts OBJECT-TYPE
   SYNTAX      Counter64
   MAX-ACCESS  read-only
   STATUS      current
   DESCRIPTION
      "Path: ethernet2.performance.pppoEClient.mibCounters.d7Performance.ifOutMcastPkts

       64 bit unsigned wrappable counter."
   ::= {pr1645v2Lan2FGPPPoEMCD7PEntry 469762048}

pr1645v2Lan2FGPPPoEMCD7PIfOutDiscards OBJECT-TYPE
   SYNTAX      Counter64
   MAX-ACCESS  read-only
   STATUS      current
   DESCRIPTION
      "Path: ethernet2.performance.pppoEClient.mibCounters.d7Performance.ifOutDiscards

       64 bit unsigned wrappable counter."
   ::= {pr1645v2Lan2FGPPPoEMCD7PEntry 218103808}

pr1645v2Lan2FGPPPoEMCD7PIfOutErrors OBJECT-TYPE
   SYNTAX      Counter64
   MAX-ACCESS  read-only
   STATUS      current
   DESCRIPTION
      "Path: ethernet2.performance.pppoEClient.mibCounters.d7Performance.ifOutErrors

       64 bit unsigned wrappable counter."
   ::= {pr1645v2Lan2FGPPPoEMCD7PEntry 234881024}

pr1645v2Lan2FGPPPoEMCD7POutDropEx OBJECT-TYPE
   SYNTAX      Counter64
   MAX-ACCESS  read-only
   STATUS      current
   DESCRIPTION
      "Path: ethernet2.performance.pppoEClient.mibCounters.d7Performance.ifOutDropLevelExceeded

       64 bit unsigned wrappable counter."
   ::= {pr1645v2Lan2FGPPPoEMCD7PEntry 352321536}

pr1645v2Lan2FGPPPoEMCD7POutDropNoArp OBJECT-TYPE
   SYNTAX      Counter64
   MAX-ACCESS  read-only
   STATUS      current
   DESCRIPTION
      "Path: ethernet2.performance.pppoEClient.mibCounters.d7Performance.ifOutDiscardsNoArp

       64 bit unsigned wrappable counter."
   ::= {pr1645v2Lan2FGPPPoEMCD7PEntry 369098752}

pr1645v2Lan2FGPPPoEMCD7POutDropFilter OBJECT-TYPE
   SYNTAX      Counter64
   MAX-ACCESS  read-only
   STATUS      current
   DESCRIPTION
      "Path: ethernet2.performance.pppoEClient.mibCounters.d7Performance.ifOutDiscardsFilter

       64 bit unsigned wrappable counter."
   ::= {pr1645v2Lan2FGPPPoEMCD7PEntry 402653184}

pr1645v2Lan2FGPPPoEMCD7PIfOutBandwidth OBJECT-TYPE
   SYNTAX      Integer32
   MAX-ACCESS  read-only
   STATUS      current
   DESCRIPTION
      "Path: ethernet2.performance.pppoEClient.mibCounters.d7Performance.ifOutBandwidth

       unit name = bps
       formula = 8 * ; 8 /"
   ::= {pr1645v2Lan2FGPPPoEMCD7PEntry 285212672}

pr1645v2Lan2FGPPPoEMCD7PIfErrSec OBJECT-TYPE
   SYNTAX      Counter32
   MAX-ACCESS  read-only
   STATUS      current
   DESCRIPTION
      "Path: ethernet2.performance.pppoEClient.mibCounters.d7Performance.ifErrSec

       32 bit unsigned wrappable counter."
   ::= {pr1645v2Lan2FGPPPoEMCD7PEntry 251658240}


pr1645v2Lan2FGIfInHwPriorityQueues OBJECT IDENTIFIER ::= {pr1645v2Lan2FG 132}

pr1645v2Lan2FGIfInHwPriorityQueuesSSCTable OBJECT-TYPE
   SYNTAX      SEQUENCE OF Pr1645v2Lan2FGIfInHwPriorityQueuesEntry
   MAX-ACCESS  not-accessible
   STATUS      current
   DESCRIPTION
      "hwPriorityQueues"
   ::= {pr1645v2Lan2FGIfInHwPriorityQueues 1}

pr1645v2Lan2FGIfInHwPriorityQueuesEntry OBJECT-TYPE
   SYNTAX      Pr1645v2Lan2FGIfInHwPriorityQueuesEntry
   MAX-ACCESS  not-accessible
   STATUS      current
   DESCRIPTION
      ""
   INDEX      { pr1645v2Lan2FGIfInHwPriorityQueuesTableIx }
   ::= {pr1645v2Lan2FGIfInHwPriorityQueuesSSCTable 1}

Pr1645v2Lan2FGIfInHwPriorityQueuesEntry ::=
   SEQUENCE
      {
      pr1645v2Lan2FGIfInHwPriorityQueuesTableIx
         TableIndex,
      pr1645v2Lan2FGIfInHwPriorityQueuesName
         INTEGER,
      pr1645v2Lan2FGIfInHwPriorityQueuesLength
         Integer32,
      pr1645v2Lan2FGIfInHwPriorityQueuesPacketsTotal
         Counter64,
      pr1645v2Lan2FGIfInHwPriorityQueuesOctetsTotal
         Counter64,
      pr1645v2Lan2FGIfInHwPriorityQueuesOctetsBandwidth15sec
         Integer32,
      pr1645v2Lan2FGIfInHwPriorityQueuesOctetsBandwidth30sec
         Integer32,
      pr1645v2Lan2FGIfInHwPriorityQueuesOctetsBandwidth1min
         Integer32,
      pr1645v2Lan2FGIfInHwPriorityQueuesOctetsBandwidth2min
         Integer32,
      pr1645v2Lan2FGIfInHwPriorityQueuesOctetsBandwidth5min
         Integer32
      }

pr1645v2Lan2FGIfInHwPriorityQueuesTableIx OBJECT-TYPE
   SYNTAX      TableIndex
   MAX-ACCESS  not-accessible
   STATUS      current
   DESCRIPTION
      ""
   ::= {pr1645v2Lan2FGIfInHwPriorityQueuesEntry 11}

pr1645v2Lan2FGIfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2FGIfInHwPriorityQueuesEntry 16777216}

pr1645v2Lan2FGIfInHwPriorityQueuesLength OBJECT-TYPE
   SYNTAX      Integer32
   MAX-ACCESS  read-only
   STATUS      current
   DESCRIPTION
      "Path: ethernet2.performance.ifInHwPriorityQueues.length"
   ::= {pr1645v2Lan2FGIfInHwPriorityQueuesEntry 33554432}

pr1645v2Lan2FGIfInHwPriorityQueuesPacketsTotal OBJECT-TYPE
   SYNTAX      Counter64
   MAX-ACCESS  read-only
   STATUS      current
   DESCRIPTION
      "Path: ethernet2.performance.ifInHwPriorityQueues.packets.total

       64 bit unsigned wrappable counter."
   ::= {pr1645v2Lan2FGIfInHwPriorityQueuesEntry 50790400}

pr1645v2Lan2FGIfInHwPriorityQueuesOctetsTotal OBJECT-TYPE
   SYNTAX      Counter64
   MAX-ACCESS  read-only
   STATUS      current
   DESCRIPTION
      "Path: ethernet2.performance.ifInHwPriorityQueues.octets.total

       64 bit unsigned wrappable counter."
   ::= {pr1645v2Lan2FGIfInHwPriorityQueuesEntry 67567616}

pr1645v2Lan2FGIfInHwPriorityQueuesOctetsBandwidth15sec OBJECT-TYPE
   SYNTAX      Integer32
   MAX-ACCESS  read-only
   STATUS      current
   DESCRIPTION
      "Path: ethernet2.performance.ifInHwPriorityQueues.octets.bandwidth.15sec

       unit name = bps
       formula = 8 * ; 8 /"
   ::= {pr1645v2Lan2FGIfInHwPriorityQueuesEntry 70386944}

pr1645v2Lan2FGIfInHwPriorityQueuesOctetsBandwidth30sec OBJECT-TYPE
   SYNTAX      Integer32
   MAX-ACCESS  read-only
   STATUS      current
   DESCRIPTION
      "Path: ethernet2.performance.ifInHwPriorityQueues.octets.bandwidth.30sec

       unit name = bps
       formula = 8 * ; 8 /"
   ::= {pr1645v2Lan2FGIfInHwPriorityQueuesEntry 70388224}

pr1645v2Lan2FGIfInHwPriorityQueuesOctetsBandwidth1min OBJECT-TYPE
   SYNTAX      Integer32
   MAX-ACCESS  read-only
   STATUS      current
   DESCRIPTION
      "Path: ethernet2.performance.ifInHwPriorityQueues.octets.bandwidth.1min

       unit name = bps
       formula = 8 * ; 8 /"
   ::= {pr1645v2Lan2FGIfInHwPriorityQueuesEntry 70390784}

pr1645v2Lan2FGIfInHwPriorityQueuesOctetsBandwidth2min OBJECT-TYPE
   SYNTAX      Integer32
   MAX-ACCESS  read-only
   STATUS      current
   DESCRIPTION
      "Path: ethernet2.performance.ifInHwPriorityQueues.octets.bandwidth.2min

       unit name = bps
       formula = 8 * ; 8 /"
   ::= {pr1645v2Lan2FGIfInHwPriorityQueuesEntry 70395904}

pr1645v2Lan2FGIfInHwPriorityQueuesOctetsBandwidth5min OBJECT-TYPE
   SYNTAX      Integer32
   MAX-ACCESS  read-only
   STATUS      current
   DESCRIPTION
      "Path: ethernet2.performance.ifInHwPriorityQueues.octets.bandwidth.5min

       unit name = bps
       formula = 8 * ; 8 /"
   ::= {pr1645v2Lan2FGIfInHwPriorityQueuesEntry 70411264}

pr1645v2Lan2FGIfInHwPriorityQueuesH2Performance OBJECT-TYPE
   SYNTAX      SEQUENCE OF Pr1645v2Lan2FGIfInHwPriorityQueuesH2PerformanceEntry
   MAX-ACCESS  not-accessible
   STATUS      current
   DESCRIPTION
      ""
   ::= {pr1645v2Lan2FGIfInHwPriorityQueues 83886080}

pr1645v2Lan2FGIfInHwPriorityQueuesH2PerformanceEntry OBJECT-TYPE
   SYNTAX      Pr1645v2Lan2FGIfInHwPriorityQueuesH2PerformanceEntry
   MAX-ACCESS  not-accessible
   STATUS      current
   DESCRIPTION
      ""
   INDEX      { pr1645v2Lan2FGIfInHwPriorityQueuesTableIx,
                pr1645v2Lan2FGIfInHwPriorityQueuesH2PerformanceTableIx }
   ::= {pr1645v2Lan2FGIfInHwPriorityQueuesH2Performance 1}

Pr1645v2Lan2FGIfInHwPriorityQueuesH2PerformanceEntry ::=
   SEQUENCE
      {
      pr1645v2Lan2FGIfInHwPriorityQueuesH2PerformanceTableIx
         TableIndex,
      pr1645v2Lan2FGIfInHwPriorityQueuesH2PerformanceSysUpTime
         TimeTicks,
      pr1645v2Lan2FGIfInHwPriorityQueuesH2PerformanceTotPkts
         Counter64,
      pr1645v2Lan2FGIfInHwPriorityQueuesH2PerformanceTotOcts
         Counter64,
      pr1645v2Lan2FGIfInHwPriorityQueuesH2PerformanceBandwidth
         Integer32
      }

pr1645v2Lan2FGIfInHwPriorityQueuesH2PerformanceTableIx OBJECT-TYPE
   SYNTAX      TableIndex
   MAX-ACCESS  not-accessible
   STATUS      current
   DESCRIPTION
      ""
   ::= {pr1645v2Lan2FGIfInHwPriorityQueuesH2PerformanceEntry 11}

pr1645v2Lan2FGIfInHwPriorityQueuesH2PerformanceSysUpTime OBJECT-TYPE
   SYNTAX      TimeTicks
   MAX-ACCESS  read-only
   STATUS      current
   DESCRIPTION
      "Path: ethernet2.performance.ifInHwPriorityQueues.h2Performance.sysUpTime

       Time in centi-second."
   ::= {pr1645v2Lan2FGIfInHwPriorityQueuesH2PerformanceEntry 16777216}

pr1645v2Lan2FGIfInHwPriorityQueuesH2PerformanceTotPkts OBJECT-TYPE
   SYNTAX      Counter64
   MAX-ACCESS  read-only
   STATUS      current
   DESCRIPTION
      "Path: ethernet2.performance.ifInHwPriorityQueues.h2Performance.totalPkts

       64 bit unsigned wrappable counter."
   ::= {pr1645v2Lan2FGIfInHwPriorityQueuesH2PerformanceEntry 234881024}

pr1645v2Lan2FGIfInHwPriorityQueuesH2PerformanceTotOcts OBJECT-TYPE
   SYNTAX      Counter64
   MAX-ACCESS  read-only
   STATUS      current
   DESCRIPTION
      "Path: ethernet2.performance.ifInHwPriorityQueues.h2Performance.totalOctets

       64 bit unsigned wrappable counter."
   ::= {pr1645v2Lan2FGIfInHwPriorityQueuesH2PerformanceEntry 251658240}

pr1645v2Lan2FGIfInHwPriorityQueuesH2PerformanceBandwidth OBJECT-TYPE
   SYNTAX      Integer32
   MAX-ACCESS  read-only
   STATUS      current
   DESCRIPTION
      "Path: ethernet2.performance.ifInHwPriorityQueues.h2Performance.bandwidth

       unit name = bps
       formula = 8 * ; 8 /"
   ::= {pr1645v2Lan2FGIfInHwPriorityQueuesH2PerformanceEntry 268435456}

pr1645v2Lan2FGIfInHwPriorityQueuesH24Performance OBJECT-TYPE
   SYNTAX      SEQUENCE OF Pr1645v2Lan2FGIfInHwPriorityQueuesH24PerformanceEntry
   MAX-ACCESS  not-accessible
   STATUS      current
   DESCRIPTION
      ""
   ::= {pr1645v2Lan2FGIfInHwPriorityQueues 100663296}

pr1645v2Lan2FGIfInHwPriorityQueuesH24PerformanceEntry OBJECT-TYPE
   SYNTAX      Pr1645v2Lan2FGIfInHwPriorityQueuesH24PerformanceEntry
   MAX-ACCESS  not-accessible
   STATUS      current
   DESCRIPTION
      ""
   INDEX      { pr1645v2Lan2FGIfInHwPriorityQueuesTableIx,
                pr1645v2Lan2FGIfInHwPriorityQueuesH24PerformanceTableIx }
   ::= {pr1645v2Lan2FGIfInHwPriorityQueuesH24Performance 1}

Pr1645v2Lan2FGIfInHwPriorityQueuesH24PerformanceEntry ::=
   SEQUENCE
      {
      pr1645v2Lan2FGIfInHwPriorityQueuesH24PerformanceTableIx
         TableIndex,
      pr1645v2Lan2FGIfInHwPriorityQueuesH24PerformanceSysUpTime
         TimeTicks,
      pr1645v2Lan2FGIfInHwPriorityQueuesH24PerformanceTotPkts
         Counter64,
      pr1645v2Lan2FGIfInHwPriorityQueuesH24PerformanceTotOcts
         Counter64,
      pr1645v2Lan2FGIfInHwPriorityQueuesH24PerformanceBandwidth
         Integer32
      }

pr1645v2Lan2FGIfInHwPriorityQueuesH24PerformanceTableIx OBJECT-TYPE
   SYNTAX      TableIndex
   MAX-ACCESS  not-accessible
   STATUS      current
   DESCRIPTION
      ""
   ::= {pr1645v2Lan2FGIfInHwPriorityQueuesH24PerformanceEntry 11}

pr1645v2Lan2FGIfInHwPriorityQueuesH24PerformanceSysUpTime OBJECT-TYPE
   SYNTAX      TimeTicks
   MAX-ACCESS  read-only
   STATUS      current
   DESCRIPTION
      "Path: ethernet2.performance.ifInHwPriorityQueues.h24Performance.sysUpTime

       Time in centi-second."
   ::= {pr1645v2Lan2FGIfInHwPriorityQueuesH24PerformanceEntry 16777216}

pr1645v2Lan2FGIfInHwPriorityQueuesH24PerformanceTotPkts OBJECT-TYPE
   SYNTAX      Counter64
   MAX-ACCESS  read-only
   STATUS      current
   DESCRIPTION
      "Path: ethernet2.performance.ifInHwPriorityQueues.h24Performance.totalPkts

       64 bit unsigned wrappable counter."
   ::= {pr1645v2Lan2FGIfInHwPriorityQueuesH24PerformanceEntry 234881024}

pr1645v2Lan2FGIfInHwPriorityQueuesH24PerformanceTotOcts OBJECT-TYPE
   SYNTAX      Counter64
   MAX-ACCESS  read-only
   STATUS      current
   DESCRIPTION
      "Path: ethernet2.performance.ifInHwPriorityQueues.h24Performance.totalOctets

       64 bit unsigned wrappable counter."
   ::= {pr1645v2Lan2FGIfInHwPriorityQueuesH24PerformanceEntry 251658240}

pr1645v2Lan2FGIfInHwPriorityQueuesH24PerformanceBandwidth OBJECT-TYPE
   SYNTAX      Integer32
   MAX-ACCESS  read-only
   STATUS      current
   DESCRIPTION
      "Path: ethernet2.performance.ifInHwPriorityQueues.h24Performance.bandwidth

       unit name = bps
       formula = 8 * ; 8 /"
   ::= {pr1645v2Lan2FGIfInHwPriorityQueuesH24PerformanceEntry 268435456}

pr1645v2Lan2FGIfInHwPriorityQueuesD7Performance OBJECT-TYPE
   SYNTAX      SEQUENCE OF Pr1645v2Lan2FGIfInHwPriorityQueuesD7PerformanceEntry
   MAX-ACCESS  not-accessible
   STATUS      current
   DESCRIPTION
      ""
   ::= {pr1645v2Lan2FGIfInHwPriorityQueues 117440512}

pr1645v2Lan2FGIfInHwPriorityQueuesD7PerformanceEntry OBJECT-TYPE
   SYNTAX      Pr1645v2Lan2FGIfInHwPriorityQueuesD7PerformanceEntry
   MAX-ACCESS  not-accessible
   STATUS      current
   DESCRIPTION
      ""
   INDEX      { pr1645v2Lan2FGIfInHwPriorityQueuesTableIx,
                pr1645v2Lan2FGIfInHwPriorityQueuesD7PerformanceTableIx }
   ::= {pr1645v2Lan2FGIfInHwPriorityQueuesD7Performance 1}

Pr1645v2Lan2FGIfInHwPriorityQueuesD7PerformanceEntry ::=
   SEQUENCE
      {
      pr1645v2Lan2FGIfInHwPriorityQueuesD7PerformanceTableIx
         TableIndex,
      pr1645v2Lan2FGIfInHwPriorityQueuesD7PerformanceSysUpTime
         TimeTicks,
      pr1645v2Lan2FGIfInHwPriorityQueuesD7PerformanceTotPkts
         Counter64,
      pr1645v2Lan2FGIfInHwPriorityQueuesD7PerformanceTotOcts
         Counter64,
      pr1645v2Lan2FGIfInHwPriorityQueuesD7PerformanceBandwidth
         Integer32
      }

pr1645v2Lan2FGIfInHwPriorityQueuesD7PerformanceTableIx OBJECT-TYPE
   SYNTAX      TableIndex
   MAX-ACCESS  not-accessible
   STATUS      current
   DESCRIPTION
      ""
   ::= {pr1645v2Lan2FGIfInHwPriorityQueuesD7PerformanceEntry 11}

pr1645v2Lan2FGIfInHwPriorityQueuesD7PerformanceSysUpTime OBJECT-TYPE
   SYNTAX      TimeTicks
   MAX-ACCESS  read-only
   STATUS      current
   DESCRIPTION
      "Path: ethernet2.performance.ifInHwPriorityQueues.d7Performance.sysUpTime

       Time in centi-second."
   ::= {pr1645v2Lan2FGIfInHwPriorityQueuesD7PerformanceEntry 16777216}

pr1645v2Lan2FGIfInHwPriorityQueuesD7PerformanceTotPkts OBJECT-TYPE
   SYNTAX      Counter64
   MAX-ACCESS  read-only
   STATUS      current
   DESCRIPTION
      "Path: ethernet2.performance.ifInHwPriorityQueues.d7Performance.totalPkts

       64 bit unsigned wrappable counter."
   ::= {pr1645v2Lan2FGIfInHwPriorityQueuesD7PerformanceEntry 234881024}

pr1645v2Lan2FGIfInHwPriorityQueuesD7PerformanceTotOcts OBJECT-TYPE
   SYNTAX      Counter64
   MAX-ACCESS  read-only
   STATUS      current
   DESCRIPTION
      "Path: ethernet2.performance.ifInHwPriorityQueues.d7Performance.totalOctets

       64 bit unsigned wrappable counter."
   ::= {pr1645v2Lan2FGIfInHwPriorityQueuesD7PerformanceEntry 251658240}

pr1645v2Lan2FGIfInHwPriorityQueuesD7PerformanceBandwidth OBJECT-TYPE
   SYNTAX      Integer32
   MAX-ACCESS  read-only
   STATUS      current
   DESCRIPTION
      "Path: ethernet2.performance.ifInHwPriorityQueues.d7Performance.bandwidth

       unit name = bps
       formula = 8 * ; 8 /"
   ::= {pr1645v2Lan2FGIfInHwPriorityQueuesD7PerformanceEntry 268435456}



ar1645v2Lan2FG OBJECT IDENTIFIER ::= {r1645v2Lan2FG 16}


ar1645v2Lan2FGClearCounters OBJECT-TYPE
   SYNTAX      Integer32
   MAX-ACCESS  read-write
   STATUS      current
   DESCRIPTION
      "Path: ethernet2.actions.clearCounters
       Info: reset counters"
   ::= {ar1645v2Lan2FG 263}


ar1645v2Lan2FGPowerToggle OBJECT-TYPE
   SYNTAX      Integer32
   MAX-ACCESS  read-write
   STATUS      current
   DESCRIPTION
      "Path: ethernet2.actions.powerToggle
       Info: action in the debug group"
   ::= {ar1645v2Lan2FG 68}


ar1645v2Lan2FGRestartIntf OBJECT-TYPE
   SYNTAX      Integer32
   MAX-ACCESS  read-write
   STATUS      current
   DESCRIPTION
      "Path: ethernet2.actions.restartIntf
       Info: action in the debug group"
   ::= {ar1645v2Lan2FG 67}


ar1645v2Lan2FGClearOamEventLog OBJECT-TYPE
   SYNTAX      Integer32
   MAX-ACCESS  read-write
   STATUS      current
   DESCRIPTION
      "Path: ethernet2.actions.clearOamEventLog
       Info: clear the OAM event log"
   ::= {ar1645v2Lan2FG 916}


ar1645v2Lan2FGLoopback OBJECT-TYPE
   SYNTAX      Integer32
   MAX-ACCESS  read-write
   STATUS      current
   DESCRIPTION
      "Path: ethernet2.actions.loopback
       Info: ethernet loopback"
   ::= {ar1645v2Lan2FG 914}


ar1645v2Lan2FGLoop OBJECT IDENTIFIER ::= {ar1645v2Lan2FG 915}

ar1645v2Lan2FGLoopSSC OBJECT IDENTIFIER ::= {ar1645v2Lan2FGLoop 1}

ar1645v2Lan2FGLoopEntry OBJECT IDENTIFIER ::= {ar1645v2Lan2FGLoopSSC 1}

ar1645v2Lan2FGLoopAction OBJECT-TYPE
   SYNTAX      INTEGER
               {
               start (1),
               stop (2)
               }
   MAX-ACCESS  read-write
   STATUS      current
   DESCRIPTION
      "Path: ethernet2.actions.loop.action

       Possibilities:
               start   (1)
               stop   (2)"
   ::= {ar1645v2Lan2FGLoopEntry 16777216}

ar1645v2Lan2FGLoopTime OBJECT-TYPE
   SYNTAX      TimeTicks
   MAX-ACCESS  read-write
   STATUS      current
   DESCRIPTION
      "Path: ethernet2.actions.loop.time

       Time in centi-second."
   ::= {ar1645v2Lan2FGLoopEntry 50331648}

ar1645v2Lan2FGLoopIntfName OBJECT-TYPE
   SYNTAX      DisplayString
   MAX-ACCESS  read-write
   STATUS      current
   DESCRIPTION
      "Path: ethernet2.actions.loop.intfName"
   ::= {ar1645v2Lan2FGLoopEntry 67108864}


ar1645v2Lan2FGOamRemLoopback OBJECT-TYPE
   SYNTAX      Integer32
   MAX-ACCESS  read-write
   STATUS      current
   DESCRIPTION
      "Path: ethernet2.actions.oamRemLoopback
       Info: OAM Remote Loopback"
   ::= {ar1645v2Lan2FG 912}


ar1645v2Lan2FGType OBJECT-TYPE
   SYNTAX      INTEGER
               {
               start (0),
               stop (1)
               }
   MAX-ACCESS  read-write
   STATUS      current
   DESCRIPTION
      "Path: ethernet2.actions.type
       Info: OAM Remote Loopback type

       Possibilities:
               start   (0)
               stop   (1)"
   ::= {ar1645v2Lan2FG 913}


ar1645v2Lan2FGSendWOL OBJECT-TYPE
   SYNTAX      Integer32
   MAX-ACCESS  read-write
   STATUS      current
   DESCRIPTION
      "Path: ethernet2.actions.sendWOL
       Info: send a WakeOnLan message on this interface"
   ::= {ar1645v2Lan2FG 333}


ar1645v2Lan2FGWolInfo OBJECT IDENTIFIER ::= {ar1645v2Lan2FG 332}

ar1645v2Lan2FGWolInfoSSC OBJECT IDENTIFIER ::= {ar1645v2Lan2FGWolInfo 1}

ar1645v2Lan2FGWolInfoEntry OBJECT IDENTIFIER ::= {ar1645v2Lan2FGWolInfoSSC 1}

ar1645v2Lan2FGWolInfoTargetMAC OBJECT-TYPE
   SYNTAX      OCTET STRING
   MAX-ACCESS  read-write
   STATUS      current
   DESCRIPTION
      "Path: ethernet2.actions.wolInfo.targetMAC

       MAC address."
   ::= {ar1645v2Lan2FGWolInfoEntry 16777216}

ar1645v2Lan2FGWolInfoPassword OBJECT-TYPE
   SYNTAX      OCTET STRING
   MAX-ACCESS  read-write
   STATUS      current
   DESCRIPTION
      "Path: ethernet2.actions.wolInfo.password"
   ::= {ar1645v2Lan2FGWolInfoEntry 33554432}


ar1645v2Lan2FGClearArpCache OBJECT-TYPE
   SYNTAX      Integer32
   MAX-ACCESS  read-write
   STATUS      current
   DESCRIPTION
      "Path: ethernet2.actions.clearArpCache
       Info: clear all dynamic enties in ARP cache table"
   ::= {ar1645v2Lan2FG 25}


ar1645v2Lan2FGClearDebugCounters OBJECT-TYPE
   SYNTAX      Integer32
   MAX-ACCESS  read-write
   STATUS      current
   DESCRIPTION
      "Path: ethernet2.actions.clearDebugCounters
       Info: action in the debug group"
   ::= {ar1645v2Lan2FG 76}


ar1645v2Lan2FGEnableRds OBJECT-TYPE
   SYNTAX      Integer32
   MAX-ACCESS  read-write
   STATUS      current
   DESCRIPTION
      "Path: ethernet2.actions.enableRds
       Info: action in the debug group"
   ::= {ar1645v2Lan2FG 367}


ar1645v2Lan2FGDisableRds OBJECT-TYPE
   SYNTAX      Integer32
   MAX-ACCESS  read-write
   STATUS      current
   DESCRIPTION
      "Path: ethernet2.actions.disableRds
       Info: action in the debug group"
   ::= {ar1645v2Lan2FG 366}


ar1645v2Lan2FGEnableTds OBJECT-TYPE
   SYNTAX      Integer32
   MAX-ACCESS  read-write
   STATUS      current
   DESCRIPTION
      "Path: ethernet2.actions.enableTds
       Info: action in the debug group"
   ::= {ar1645v2Lan2FG 365}


ar1645v2Lan2FGDisableTds OBJECT-TYPE
   SYNTAX      Integer32
   MAX-ACCESS  read-write
   STATUS      current
   DESCRIPTION
      "Path: ethernet2.actions.disableTds
       Info: action in the debug group"
   ::= {ar1645v2Lan2FG 364}


ar1645v2Lan2FGClearTsecStats OBJECT-TYPE
   SYNTAX      Integer32
   MAX-ACCESS  read-write
   STATUS      current
   DESCRIPTION
      "Path: ethernet2.actions.clearTsecStats
       Info: action in the debug group"
   ::= {ar1645v2Lan2FG 363}


ar1645v2Lan2FGStopTsecStats OBJECT-TYPE
   SYNTAX      Integer32
   MAX-ACCESS  read-write
   STATUS      current
   DESCRIPTION
      "Path: ethernet2.actions.stopTsecStats
       Info: action in the debug group"
   ::= {ar1645v2Lan2FG 362}


ar1645v2Lan2FGStartTsecStats OBJECT-TYPE
   SYNTAX      Integer32
   MAX-ACCESS  read-write
   STATUS      current
   DESCRIPTION
      "Path: ethernet2.actions.startTsecStats
       Info: action in the debug group"
   ::= {ar1645v2Lan2FG 361}


ar1645v2Lan2FGPhyAction OBJECT-TYPE
   SYNTAX      Integer32
   MAX-ACCESS  read-write
   STATUS      current
   DESCRIPTION
      "Path: ethernet2.actions.phyAction
       Info: action in the debug group"
   ::= {ar1645v2Lan2FG 90}



fr1645v2Lan2FG OBJECT IDENTIFIER ::= {r1645v2Lan2FG 13}


fr1645v2Lan2FGAlarm OBJECT IDENTIFIER ::= {fr1645v2Lan2FG 207}

fr1645v2Lan2FGAlarmSSC OBJECT IDENTIFIER ::= {fr1645v2Lan2FGAlarm 1}

fr1645v2Lan2FGAlarmEntry OBJECT IDENTIFIER ::= {fr1645v2Lan2FGAlarmSSC 1}

fr1645v2Lan2FGAlarmDiscriminator OBJECT-TYPE
   SYNTAX      Integer32
   MAX-ACCESS  read-only
   STATUS      current
   DESCRIPTION
      "Path: ethernet2.alarms.alarmInfo.discriminator"
   ::= {fr1645v2Lan2FGAlarmEntry 16777216}

fr1645v2Lan2FGAlarmCurrent OBJECT-TYPE
   SYNTAX      Integer32
   MAX-ACCESS  read-only
   STATUS      current
   DESCRIPTION
      "Path: ethernet2.alarms.alarmInfo.currentAlarms

       Bit meanings:
               bit 0 = linkDown,
               bit 9 = pppoEDown"
   ::= {fr1645v2Lan2FGAlarmEntry 33554432}

fr1645v2Lan2FGAlarmPrevious OBJECT-TYPE
   SYNTAX      Integer32
   MAX-ACCESS  read-only
   STATUS      current
   DESCRIPTION
      "Path: ethernet2.alarms.alarmInfo.previousAlarms

       Bit meanings:
               bit 0 = linkDown,
               bit 9 = pppoEDown"
   ::= {fr1645v2Lan2FGAlarmEntry 50331648}

fr1645v2Lan2FGAlarmMask OBJECT-TYPE
   SYNTAX      Integer32
   MAX-ACCESS  read-only
   STATUS      current
   DESCRIPTION
      "Path: ethernet2.alarms.alarmInfo.alarmMask

       Bit meanings:
               bit 0 = linkDown,
               bit 9 = pppoEDown"
   ::= {fr1645v2Lan2FGAlarmEntry 67108864}

fr1645v2Lan2FGAlarmLevLinkDown OBJECT-TYPE
   SYNTAX      Integer32
   MAX-ACCESS  read-only
   STATUS      current
   DESCRIPTION
      "Path: ethernet2.alarms.alarmInfo.alarmLevel.linkDown"
   ::= {fr1645v2Lan2FGAlarmEntry 83951616}

fr1645v2Lan2FGAlarmLevPppoEDown OBJECT-TYPE
   SYNTAX      Integer32
   MAX-ACCESS  read-only
   STATUS      current
   DESCRIPTION
      "Path: ethernet2.alarms.alarmInfo.alarmLevel.pppoEDown"
   ::= {fr1645v2Lan2FGAlarmEntry 84541440}


fr1645v2Lan2FGAlarmE2 OBJECT IDENTIFIER ::= {fr1645v2Lan2FGAlarm 2}

fr1645v2Lan2FGAlarmE2Entry OBJECT IDENTIFIER ::= {fr1645v2Lan2FGAlarmE2 1}

fr1645v2Lan2FGAlarmE2LinkDown OBJECT IDENTIFIER ::= {fr1645v2Lan2FGAlarmE2Entry 10}

fr1645v2Lan2FGAlarmE2LinkDownPfx OBJECT IDENTIFIER ::= {fr1645v2Lan2FGAlarmE2LinkDown 0}

fr1645v2Lan2FGAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lanCfg2Giga'
                (root='router1645') has changed from the ON to the OFF state."
   ::= {fr1645v2Lan2FGAlarmE2LinkDownPfx 1}

fr1645v2Lan2FGAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lanCfg2Giga'
                (root='router1645') has changed from the OFF to the ON state."
   ::= {fr1645v2Lan2FGAlarmE2LinkDownPfx 2}

fr1645v2Lan2FGAlarmE2PppoEDown OBJECT IDENTIFIER ::= {fr1645v2Lan2FGAlarmE2Entry 19}

fr1645v2Lan2FGAlarmE2PppoEDownPfx OBJECT IDENTIFIER ::= {fr1645v2Lan2FGAlarmE2PppoEDown 0}

fr1645v2Lan2FGAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lanCfg2Giga'
                (root='router1645') has changed from the ON to the OFF state."
   ::= {fr1645v2Lan2FGAlarmE2PppoEDownPfx 1}

fr1645v2Lan2FGAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lanCfg2Giga'
                (root='router1645') has changed from the OFF to the ON state."
   ::= {fr1645v2Lan2FGAlarmE2PppoEDownPfx 2}



END
