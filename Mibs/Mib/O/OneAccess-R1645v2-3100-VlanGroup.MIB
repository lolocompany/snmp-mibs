OneAccess-R1645v2-3100-VlanGroup DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2VlanGroup OBJECT IDENTIFIER ::= {r1645Rootv2 3100}

r1645v2VlanGroupMOProp OBJECT-TYPE
   SYNTAX      SEQUENCE OF R1645v2VlanGroupMOPropEntry
   MAX-ACCESS  not-accessible
   STATUS      current
   DESCRIPTION
      ""
   ::= {r1645v2VlanGroup 1}

r1645v2VlanGroupMOPropEntry OBJECT-TYPE
   SYNTAX      R1645v2VlanGroupMOPropEntry
   MAX-ACCESS  not-accessible
   STATUS      current
   DESCRIPTION
      ""
   INDEX      { r1645v2VlanGroupMOPropGlobalIx }
   ::= {r1645v2VlanGroupMOProp 1}

R1645v2VlanGroupMOPropEntry ::=
   SEQUENCE
      {
      r1645v2VlanGroupMOPropPath
         ContainmentPath,
      r1645v2VlanGroupMOPropRev
         ObjectRevision,
      r1645v2VlanGroupMOPropGlobalIx
         GlobalIndex
      }

r1645v2VlanGroupMOPropPath OBJECT-TYPE
   SYNTAX      ContainmentPath
   MAX-ACCESS  read-only
   STATUS      current
   DESCRIPTION
      "Textual description of the containment tree from the instance of
       the root object down to the instance of the current object."
   ::= {r1645v2VlanGroupMOPropEntry 3}

r1645v2VlanGroupMOPropRev OBJECT-TYPE
   SYNTAX      ObjectRevision
   MAX-ACCESS  read-only
   STATUS      current
   DESCRIPTION
      "This value corresponds with the revision of the MANAGED OBJECT."
   ::= {r1645v2VlanGroupMOPropEntry 4}

r1645v2VlanGroupMOPropGlobalIx OBJECT-TYPE
   SYNTAX      GlobalIndex
   MAX-ACCESS  read-only
   STATUS      current
   DESCRIPTION
      "The value of the tlsCntTreeGlobalIndex of the MANAGED OBJECT."
   ::= {r1645v2VlanGroupMOPropEntry 10}



er1645v2VlanGroup OBJECT IDENTIFIER ::= {r1645v2VlanGroup 11}


er1645v2VlanGroupSnmpIndexOffset OBJECT IDENTIFIER ::= {er1645v2VlanGroup 268}

er1645v2VlanGroupSnmpIndexOffsetTable OBJECT-TYPE
   SYNTAX      SEQUENCE OF Er1645v2VlanGroupSnmpIndexOffsetEntry
   MAX-ACCESS  not-accessible
   STATUS      current
   DESCRIPTION
      "Preferred offset in the range of SNMP indices for this SWinst, 0 means automatic"
   ::= {er1645v2VlanGroupSnmpIndexOffset 1}

er1645v2VlanGroupSnmpIndexOffsetEntry OBJECT-TYPE
   SYNTAX      Er1645v2VlanGroupSnmpIndexOffsetEntry
   MAX-ACCESS  not-accessible
   STATUS      current
   DESCRIPTION
      ""
   INDEX      { er1645v2VlanGroupSnmpIndexOffsetGlobalIx }
   ::= {er1645v2VlanGroupSnmpIndexOffsetTable 1}

Er1645v2VlanGroupSnmpIndexOffsetEntry ::=
   SEQUENCE
      {
      er1645v2VlanGroupSnmpIndexOffsetGlobalIx
         GlobalIndex,
      er1645v2VlanGroupSnmpIndexOffsetValue
         Integer32
      }

er1645v2VlanGroupSnmpIndexOffsetGlobalIx OBJECT-TYPE
   SYNTAX      GlobalIndex
   MAX-ACCESS  not-accessible
   STATUS      current
   DESCRIPTION
      "The value of the tlsCntTreeGlobalIndex of the MANAGED OBJECT."
   ::= {er1645v2VlanGroupSnmpIndexOffsetEntry 10}

er1645v2VlanGroupSnmpIndexOffsetValue OBJECT-TYPE
   SYNTAX      Integer32
   MAX-ACCESS  read-write
   STATUS      current
   DESCRIPTION
      "Path: vlanGroup.editConf.snmpIndexOffset"
   ::= {er1645v2VlanGroupSnmpIndexOffsetEntry 2147483648}


er1645v2VlanGroupFilteringId OBJECT IDENTIFIER ::= {er1645v2VlanGroup 2}

er1645v2VlanGroupFilteringIdTable OBJECT-TYPE
   SYNTAX      SEQUENCE OF Er1645v2VlanGroupFilteringIdEntry
   MAX-ACCESS  not-accessible
   STATUS      current
   DESCRIPTION
      ""
   ::= {er1645v2VlanGroupFilteringId 1}

er1645v2VlanGroupFilteringIdEntry OBJECT-TYPE
   SYNTAX      Er1645v2VlanGroupFilteringIdEntry
   MAX-ACCESS  not-accessible
   STATUS      current
   DESCRIPTION
      ""
   INDEX      { er1645v2VlanGroupFilteringIdGlobalIx }
   ::= {er1645v2VlanGroupFilteringIdTable 1}

Er1645v2VlanGroupFilteringIdEntry ::=
   SEQUENCE
      {
      er1645v2VlanGroupFilteringIdGlobalIx
         GlobalIndex,
      er1645v2VlanGroupFilteringIdValue
         Integer32
      }

er1645v2VlanGroupFilteringIdGlobalIx OBJECT-TYPE
   SYNTAX      GlobalIndex
   MAX-ACCESS  not-accessible
   STATUS      current
   DESCRIPTION
      "The value of the tlsCntTreeGlobalIndex of the MANAGED OBJECT."
   ::= {er1645v2VlanGroupFilteringIdEntry 10}

er1645v2VlanGroupFilteringIdValue OBJECT-TYPE
   SYNTAX      Integer32
   MAX-ACCESS  read-write
   STATUS      current
   DESCRIPTION
      "Path: vlanGroup.editConf.filteringId"
   ::= {er1645v2VlanGroupFilteringIdEntry 2147483648}


er1645v2VlanGroupVlanMembers OBJECT IDENTIFIER ::= {er1645v2VlanGroup 3}

er1645v2VlanGroupVlanMembersSSCTable OBJECT-TYPE
   SYNTAX      SEQUENCE OF Er1645v2VlanGroupVlanMembersEntry
   MAX-ACCESS  not-accessible
   STATUS      current
   DESCRIPTION
      ""
   ::= {er1645v2VlanGroupVlanMembers 1}

er1645v2VlanGroupVlanMembersEntry OBJECT-TYPE
   SYNTAX      Er1645v2VlanGroupVlanMembersEntry
   MAX-ACCESS  not-accessible
   STATUS      current
   DESCRIPTION
      ""
   INDEX      { er1645v2VlanGroupVlanMembersGlobalIx,
                er1645v2VlanGroupVlanMembersTableIx }
   ::= {er1645v2VlanGroupVlanMembersSSCTable 1}

Er1645v2VlanGroupVlanMembersEntry ::=
   SEQUENCE
      {
      er1645v2VlanGroupVlanMembersActions
         VariableLengthTableActions,
      er1645v2VlanGroupVlanMembersGlobalIx
         GlobalIndex,
      er1645v2VlanGroupVlanMembersTableIx
         TableIndex,
      er1645v2VlanGroupVlanMembersSingle
         Integer32,
      er1645v2VlanGroupVlanMembersRangeFrom
         Integer32,
      er1645v2VlanGroupVlanMembersRangeTo
         Integer32
      }

er1645v2VlanGroupVlanMembersActions OBJECT-TYPE
   SYNTAX      VariableLengthTableActions
   MAX-ACCESS  read-write
   STATUS      current
   DESCRIPTION
      "By way of this field, some manipulations
       on this table may be performed."
   ::= {er1645v2VlanGroupVlanMembersEntry 2}

er1645v2VlanGroupVlanMembersGlobalIx OBJECT-TYPE
   SYNTAX      GlobalIndex
   MAX-ACCESS  not-accessible
   STATUS      current
   DESCRIPTION
      "The value of the tlsCntTreeGlobalIndex of the MANAGED OBJECT."
   ::= {er1645v2VlanGroupVlanMembersEntry 10}

er1645v2VlanGroupVlanMembersTableIx OBJECT-TYPE
   SYNTAX      TableIndex
   MAX-ACCESS  not-accessible
   STATUS      current
   DESCRIPTION
      ""
   ::= {er1645v2VlanGroupVlanMembersEntry 11}

er1645v2VlanGroupVlanMembersSingle OBJECT-TYPE
   SYNTAX      Integer32
   MAX-ACCESS  read-write
   STATUS      current
   DESCRIPTION
      "Path: vlanGroup.editConf.vlanMembers.single"
   ::= {er1645v2VlanGroupVlanMembersEntry 16777216}

er1645v2VlanGroupVlanMembersRangeFrom OBJECT-TYPE
   SYNTAX      Integer32
   MAX-ACCESS  read-write
   STATUS      current
   DESCRIPTION
      "Path: vlanGroup.editConf.vlanMembers.range.from"
   ::= {er1645v2VlanGroupVlanMembersEntry 33619968}

er1645v2VlanGroupVlanMembersRangeTo OBJECT-TYPE
   SYNTAX      Integer32
   MAX-ACCESS  read-write
   STATUS      current
   DESCRIPTION
      "Path: vlanGroup.editConf.vlanMembers.range.to"
   ::= {er1645v2VlanGroupVlanMembersEntry 33685504}


er1645v2VlanGroupImportBridgePorts OBJECT IDENTIFIER ::= {er1645v2VlanGroup 5}

er1645v2VlanGroupImportBridgePortsTable OBJECT-TYPE
   SYNTAX      SEQUENCE OF Er1645v2VlanGroupImportBridgePortsEntry
   MAX-ACCESS  not-accessible
   STATUS      current
   DESCRIPTION
      ""
   ::= {er1645v2VlanGroupImportBridgePorts 1}

er1645v2VlanGroupImportBridgePortsEntry OBJECT-TYPE
   SYNTAX      Er1645v2VlanGroupImportBridgePortsEntry
   MAX-ACCESS  not-accessible
   STATUS      current
   DESCRIPTION
      ""
   INDEX      { er1645v2VlanGroupImportBridgePortsGlobalIx }
   ::= {er1645v2VlanGroupImportBridgePortsTable 1}

Er1645v2VlanGroupImportBridgePortsEntry ::=
   SEQUENCE
      {
      er1645v2VlanGroupImportBridgePortsGlobalIx
         GlobalIndex,
      er1645v2VlanGroupImportBridgePortsValue
         INTEGER
      }

er1645v2VlanGroupImportBridgePortsGlobalIx OBJECT-TYPE
   SYNTAX      GlobalIndex
   MAX-ACCESS  not-accessible
   STATUS      current
   DESCRIPTION
      "The value of the tlsCntTreeGlobalIndex of the MANAGED OBJECT."
   ::= {er1645v2VlanGroupImportBridgePortsEntry 10}

er1645v2VlanGroupImportBridgePortsValue OBJECT-TYPE
   SYNTAX      INTEGER
               {
               disabled (0),
               enabled (1)
               }
   MAX-ACCESS  read-write
   STATUS      current
   DESCRIPTION
      "Path: vlanGroup.editConf.importBridgePorts

       Possibilities:
               disabled   (0)
               enabled   (1)"
   ::= {er1645v2VlanGroupImportBridgePortsEntry 2147483648}


er1645v2VlanGroupPorts OBJECT IDENTIFIER ::= {er1645v2VlanGroup 6}

er1645v2VlanGroupPortsSSCTable OBJECT-TYPE
   SYNTAX      SEQUENCE OF Er1645v2VlanGroupPortsEntry
   MAX-ACCESS  not-accessible
   STATUS      current
   DESCRIPTION
      "mst ports"
   ::= {er1645v2VlanGroupPorts 1}

er1645v2VlanGroupPortsEntry OBJECT-TYPE
   SYNTAX      Er1645v2VlanGroupPortsEntry
   MAX-ACCESS  not-accessible
   STATUS      current
   DESCRIPTION
      ""
   INDEX      { er1645v2VlanGroupPortsGlobalIx,
                er1645v2VlanGroupPortsTableIx }
   ::= {er1645v2VlanGroupPortsSSCTable 1}

Er1645v2VlanGroupPortsEntry ::=
   SEQUENCE
      {
      er1645v2VlanGroupPortsActions
         VariableLengthTableActions,
      er1645v2VlanGroupPortsGlobalIx
         GlobalIndex,
      er1645v2VlanGroupPortsTableIx
         TableIndex,
      er1645v2VlanGroupPortsName
         DisplayString,
      er1645v2VlanGroupPortsPriority
         Integer32,
      er1645v2VlanGroupPortsInternalPathCost
         Integer32
      }

er1645v2VlanGroupPortsActions OBJECT-TYPE
   SYNTAX      VariableLengthTableActions
   MAX-ACCESS  read-write
   STATUS      current
   DESCRIPTION
      "By way of this field, some manipulations
       on this table may be performed."
   ::= {er1645v2VlanGroupPortsEntry 2}

er1645v2VlanGroupPortsGlobalIx OBJECT-TYPE
   SYNTAX      GlobalIndex
   MAX-ACCESS  not-accessible
   STATUS      current
   DESCRIPTION
      "The value of the tlsCntTreeGlobalIndex of the MANAGED OBJECT."
   ::= {er1645v2VlanGroupPortsEntry 10}

er1645v2VlanGroupPortsTableIx OBJECT-TYPE
   SYNTAX      TableIndex
   MAX-ACCESS  not-accessible
   STATUS      current
   DESCRIPTION
      ""
   ::= {er1645v2VlanGroupPortsEntry 11}

er1645v2VlanGroupPortsName OBJECT-TYPE
   SYNTAX      DisplayString
   MAX-ACCESS  read-write
   STATUS      current
   DESCRIPTION
      "Path: vlanGroup.editConf.ports.name"
   ::= {er1645v2VlanGroupPortsEntry 16777216}

er1645v2VlanGroupPortsPriority OBJECT-TYPE
   SYNTAX      Integer32
   MAX-ACCESS  read-write
   STATUS      current
   DESCRIPTION
      "Path: vlanGroup.editConf.ports.priority"
   ::= {er1645v2VlanGroupPortsEntry 33554432}

er1645v2VlanGroupPortsInternalPathCost OBJECT-TYPE
   SYNTAX      Integer32
   MAX-ACCESS  read-write
   STATUS      current
   DESCRIPTION
      "Path: vlanGroup.editConf.ports.internalPathCost"
   ::= {er1645v2VlanGroupPortsEntry 50331648}


er1645v2VlanGroupMst OBJECT IDENTIFIER ::= {er1645v2VlanGroup 4}

er1645v2VlanGroupMstSSCTable OBJECT-TYPE
   SYNTAX      SEQUENCE OF Er1645v2VlanGroupMstEntry
   MAX-ACCESS  not-accessible
   STATUS      current
   DESCRIPTION
      "Spanning tree parameters for mst instance"
   ::= {er1645v2VlanGroupMst 1}

er1645v2VlanGroupMstEntry OBJECT-TYPE
   SYNTAX      Er1645v2VlanGroupMstEntry
   MAX-ACCESS  not-accessible
   STATUS      current
   DESCRIPTION
      ""
   INDEX      { er1645v2VlanGroupMstGlobalIx }
   ::= {er1645v2VlanGroupMstSSCTable 1}

Er1645v2VlanGroupMstEntry ::=
   SEQUENCE
      {
      er1645v2VlanGroupMstGlobalIx
         GlobalIndex,
      er1645v2VlanGroupMstBrPrio
         Integer32
      }

er1645v2VlanGroupMstGlobalIx OBJECT-TYPE
   SYNTAX      GlobalIndex
   MAX-ACCESS  not-accessible
   STATUS      current
   DESCRIPTION
      "The value of the tlsCntTreeGlobalIndex of the MANAGED OBJECT."
   ::= {er1645v2VlanGroupMstEntry 10}

er1645v2VlanGroupMstBrPrio OBJECT-TYPE
   SYNTAX      Integer32
   MAX-ACCESS  read-write
   STATUS      current
   DESCRIPTION
      "Path: vlanGroup.editConf.mst.bridgePriority"
   ::= {er1645v2VlanGroupMstEntry 16777216}



sr1645v2VlanGroup OBJECT IDENTIFIER ::= {r1645v2VlanGroup 14}


sr1645v2VlanGroupSnmpIndex OBJECT IDENTIFIER ::= {sr1645v2VlanGroup 269}

sr1645v2VlanGroupSnmpIndexTable OBJECT-TYPE
   SYNTAX      SEQUENCE OF Sr1645v2VlanGroupSnmpIndexEntry
   MAX-ACCESS  not-accessible
   STATUS      current
   DESCRIPTION
      "SNMP index assigned to this object"
   ::= {sr1645v2VlanGroupSnmpIndex 1}

sr1645v2VlanGroupSnmpIndexEntry OBJECT-TYPE
   SYNTAX      Sr1645v2VlanGroupSnmpIndexEntry
   MAX-ACCESS  not-accessible
   STATUS      current
   DESCRIPTION
      ""
   INDEX      { sr1645v2VlanGroupSnmpIndexGlobalIx }
   ::= {sr1645v2VlanGroupSnmpIndexTable 1}

Sr1645v2VlanGroupSnmpIndexEntry ::=
   SEQUENCE
      {
      sr1645v2VlanGroupSnmpIndexGlobalIx
         GlobalIndex,
      sr1645v2VlanGroupSnmpIndexValue
         Integer32
      }

sr1645v2VlanGroupSnmpIndexGlobalIx OBJECT-TYPE
   SYNTAX      GlobalIndex
   MAX-ACCESS  not-accessible
   STATUS      current
   DESCRIPTION
      "The value of the tlsCntTreeGlobalIndex of the MANAGED OBJECT."
   ::= {sr1645v2VlanGroupSnmpIndexEntry 10}

sr1645v2VlanGroupSnmpIndexValue OBJECT-TYPE
   SYNTAX      Integer32
   MAX-ACCESS  read-only
   STATUS      current
   DESCRIPTION
      "Path: vlanGroup.status.snmpIndex"
   ::= {sr1645v2VlanGroupSnmpIndexEntry 2147483648}


sr1645v2VlanGroupVlanMembers OBJECT IDENTIFIER ::= {sr1645v2VlanGroup 40}

sr1645v2VlanGroupVlanMembersSSCTable OBJECT-TYPE
   SYNTAX      SEQUENCE OF Sr1645v2VlanGroupVlanMembersEntry
   MAX-ACCESS  not-accessible
   STATUS      current
   DESCRIPTION
      ""
   ::= {sr1645v2VlanGroupVlanMembers 1}

sr1645v2VlanGroupVlanMembersEntry OBJECT-TYPE
   SYNTAX      Sr1645v2VlanGroupVlanMembersEntry
   MAX-ACCESS  not-accessible
   STATUS      current
   DESCRIPTION
      ""
   INDEX      { sr1645v2VlanGroupVlanMembersGlobalIx,
                sr1645v2VlanGroupVlanMembersTableIx }
   ::= {sr1645v2VlanGroupVlanMembersSSCTable 1}

Sr1645v2VlanGroupVlanMembersEntry ::=
   SEQUENCE
      {
      sr1645v2VlanGroupVlanMembersGlobalIx
         GlobalIndex,
      sr1645v2VlanGroupVlanMembersTableIx
         TableIndex,
      sr1645v2VlanGroupVlanMembersVlanId
         Integer32
      }

sr1645v2VlanGroupVlanMembersGlobalIx OBJECT-TYPE
   SYNTAX      GlobalIndex
   MAX-ACCESS  not-accessible
   STATUS      current
   DESCRIPTION
      "The value of the tlsCntTreeGlobalIndex of the MANAGED OBJECT."
   ::= {sr1645v2VlanGroupVlanMembersEntry 10}

sr1645v2VlanGroupVlanMembersTableIx OBJECT-TYPE
   SYNTAX      TableIndex
   MAX-ACCESS  not-accessible
   STATUS      current
   DESCRIPTION
      ""
   ::= {sr1645v2VlanGroupVlanMembersEntry 11}

sr1645v2VlanGroupVlanMembersVlanId OBJECT-TYPE
   SYNTAX      Integer32
   MAX-ACCESS  read-only
   STATUS      current
   DESCRIPTION
      "Path: vlanGroup.status.vlanMembers.vlanId"
   ::= {sr1645v2VlanGroupVlanMembersEntry 16777216}


sr1645v2VlanGroupBrCache OBJECT IDENTIFIER ::= {sr1645v2VlanGroup 41}

sr1645v2VlanGroupBrCacheSSCTable OBJECT-TYPE
   SYNTAX      SEQUENCE OF Sr1645v2VlanGroupBrCacheEntry
   MAX-ACCESS  not-accessible
   STATUS      current
   DESCRIPTION
      "bridge cache"
   ::= {sr1645v2VlanGroupBrCache 1}

sr1645v2VlanGroupBrCacheEntry OBJECT-TYPE
   SYNTAX      Sr1645v2VlanGroupBrCacheEntry
   MAX-ACCESS  not-accessible
   STATUS      current
   DESCRIPTION
      ""
   INDEX      { sr1645v2VlanGroupBrCacheGlobalIx,
                sr1645v2VlanGroupBrCacheTableIx }
   ::= {sr1645v2VlanGroupBrCacheSSCTable 1}

Sr1645v2VlanGroupBrCacheEntry ::=
   SEQUENCE
      {
      sr1645v2VlanGroupBrCacheGlobalIx
         GlobalIndex,
      sr1645v2VlanGroupBrCacheTableIx
         TableIndex,
      sr1645v2VlanGroupBrCacheIf
         DisplayString,
      sr1645v2VlanGroupBrCacheMacAddress
         OCTET STRING,
      sr1645v2VlanGroupBrCacheTpid
         INTEGER,
      sr1645v2VlanGroupBrCacheVlanId
         INTEGER,
      sr1645v2VlanGroupBrCacheTpid2
         INTEGER,
      sr1645v2VlanGroupBrCacheVlanId2
         INTEGER,
      sr1645v2VlanGroupBrCacheType
         INTEGER,
      sr1645v2VlanGroupBrCacheAge
         TimeTicks
      }

sr1645v2VlanGroupBrCacheGlobalIx OBJECT-TYPE
   SYNTAX      GlobalIndex
   MAX-ACCESS  not-accessible
   STATUS      current
   DESCRIPTION
      "The value of the tlsCntTreeGlobalIndex of the MANAGED OBJECT."
   ::= {sr1645v2VlanGroupBrCacheEntry 10}

sr1645v2VlanGroupBrCacheTableIx OBJECT-TYPE
   SYNTAX      TableIndex
   MAX-ACCESS  not-accessible
   STATUS      current
   DESCRIPTION
      ""
   ::= {sr1645v2VlanGroupBrCacheEntry 11}

sr1645v2VlanGroupBrCacheIf OBJECT-TYPE
   SYNTAX      DisplayString
   MAX-ACCESS  read-only
   STATUS      current
   DESCRIPTION
      "Path: vlanGroup.status.bridgeCache.interface"
   ::= {sr1645v2VlanGroupBrCacheEntry 16777216}

sr1645v2VlanGroupBrCacheMacAddress OBJECT-TYPE
   SYNTAX      OCTET STRING
   MAX-ACCESS  read-only
   STATUS      current
   DESCRIPTION
      "Path: vlanGroup.status.bridgeCache.macAddress

       MAC address."
   ::= {sr1645v2VlanGroupBrCacheEntry 33554432}

sr1645v2VlanGroupBrCacheTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vlanGroup.status.bridgeCache.tpid

       Possibilities:
               untagged   (0)
               dot1q   (33024)
               dot1ad   (34984)
               group   (65534)
               notUsed   (65535)
               dot1qOrDot1ad   (65536)"
   ::= {sr1645v2VlanGroupBrCacheEntry 150994944}

sr1645v2VlanGroupBrCacheVlanId OBJECT-TYPE
   SYNTAX      INTEGER
               {
               undefined (-1)
               }
   MAX-ACCESS  read-only
   STATUS      current
   DESCRIPTION
      "Path: vlanGroup.status.bridgeCache.vlanId

       Possibilities:
               undefined   (-1)"
   ::= {sr1645v2VlanGroupBrCacheEntry 83886080}

sr1645v2VlanGroupBrCacheTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: vlanGroup.status.bridgeCache.tpid2

       Possibilities:
               untagged   (0)
               dot1q   (33024)
               dot1ad   (34984)
               group   (65534)
               notUsed   (65535)
               dot1qOrDot1ad   (65536)"
   ::= {sr1645v2VlanGroupBrCacheEntry 369098752}

sr1645v2VlanGroupBrCacheVlanId2 OBJECT-TYPE
   SYNTAX      INTEGER
               {
               undefined (-1)
               }
   MAX-ACCESS  read-only
   STATUS      current
   DESCRIPTION
      "Path: vlanGroup.status.bridgeCache.vlanId2

       Possibilities:
               undefined   (-1)"
   ::= {sr1645v2VlanGroupBrCacheEntry 385875968}

sr1645v2VlanGroupBrCacheType OBJECT-TYPE
   SYNTAX      INTEGER
               {
               static (0),
               dynamic (1),
               tester (2),
               fastFlood (3)
               }
   MAX-ACCESS  read-only
   STATUS      current
   DESCRIPTION
      "Path: vlanGroup.status.bridgeCache.type

       Possibilities:
               static   (0)
               dynamic   (1)
               tester   (2)
               fastFlood   (3)"
   ::= {sr1645v2VlanGroupBrCacheEntry 50331648}

sr1645v2VlanGroupBrCacheAge OBJECT-TYPE
   SYNTAX      TimeTicks
   MAX-ACCESS  read-only
   STATUS      current
   DESCRIPTION
      "Path: vlanGroup.status.bridgeCache.age

       Time in centi-second."
   ::= {sr1645v2VlanGroupBrCacheEntry 67108864}


sr1645v2VlanGroupPorts OBJECT IDENTIFIER ::= {sr1645v2VlanGroup 42}

sr1645v2VlanGroupPortsSSCTable OBJECT-TYPE
   SYNTAX      SEQUENCE OF Sr1645v2VlanGroupPortsEntry
   MAX-ACCESS  not-accessible
   STATUS      current
   DESCRIPTION
      "vlan group ports"
   ::= {sr1645v2VlanGroupPorts 1}

sr1645v2VlanGroupPortsEntry OBJECT-TYPE
   SYNTAX      Sr1645v2VlanGroupPortsEntry
   MAX-ACCESS  not-accessible
   STATUS      current
   DESCRIPTION
      ""
   INDEX      { sr1645v2VlanGroupPortsGlobalIx,
                sr1645v2VlanGroupPortsTableIx }
   ::= {sr1645v2VlanGroupPortsSSCTable 1}

Sr1645v2VlanGroupPortsEntry ::=
   SEQUENCE
      {
      sr1645v2VlanGroupPortsGlobalIx
         GlobalIndex,
      sr1645v2VlanGroupPortsTableIx
         TableIndex,
      sr1645v2VlanGroupPortsName
         DisplayString,
      sr1645v2VlanGroupPortsPortRole
         INTEGER,
      sr1645v2VlanGroupPortsPortId
         Integer32,
      sr1645v2VlanGroupPortsPriority
         Integer32,
      sr1645v2VlanGroupPortsIntPCost
         Integer32,
      sr1645v2VlanGroupPortsIntRpCost
         Integer32,
      sr1645v2VlanGroupPortsDesBrIdPriority
         Integer32,
      sr1645v2VlanGroupPortsDesBrIdMacAddress
         OCTET STRING,
      sr1645v2VlanGroupPortsDesPrtId
         Integer32
      }

sr1645v2VlanGroupPortsGlobalIx OBJECT-TYPE
   SYNTAX      GlobalIndex
   MAX-ACCESS  not-accessible
   STATUS      current
   DESCRIPTION
      "The value of the tlsCntTreeGlobalIndex of the MANAGED OBJECT."
   ::= {sr1645v2VlanGroupPortsEntry 10}

sr1645v2VlanGroupPortsTableIx OBJECT-TYPE
   SYNTAX      TableIndex
   MAX-ACCESS  not-accessible
   STATUS      current
   DESCRIPTION
      ""
   ::= {sr1645v2VlanGroupPortsEntry 11}

sr1645v2VlanGroupPortsName OBJECT-TYPE
   SYNTAX      DisplayString
   MAX-ACCESS  read-only
   STATUS      current
   DESCRIPTION
      "Path: vlanGroup.status.ports.name"
   ::= {sr1645v2VlanGroupPortsEntry 16777216}

sr1645v2VlanGroupPortsPortRole OBJECT-TYPE
   SYNTAX      INTEGER
               {
               none (0),
               root (1),
               designated (2),
               alternate (3),
               backup (4),
               disabled (5),
               master (6)
               }
   MAX-ACCESS  read-only
   STATUS      current
   DESCRIPTION
      "Path: vlanGroup.status.ports.portRole

       Possibilities:
               none   (0)
               root   (1)
               designated   (2)
               alternate   (3)
               backup   (4)
               disabled   (5)
               master   (6)"
   ::= {sr1645v2VlanGroupPortsEntry 33554432}

sr1645v2VlanGroupPortsPortId OBJECT-TYPE
   SYNTAX      Integer32
   MAX-ACCESS  read-only
   STATUS      current
   DESCRIPTION
      "Path: vlanGroup.status.ports.portId"
   ::= {sr1645v2VlanGroupPortsEntry 50331648}

sr1645v2VlanGroupPortsPriority OBJECT-TYPE
   SYNTAX      Integer32
   MAX-ACCESS  read-only
   STATUS      current
   DESCRIPTION
      "Path: vlanGroup.status.ports.priority"
   ::= {sr1645v2VlanGroupPortsEntry 67108864}

sr1645v2VlanGroupPortsIntPCost OBJECT-TYPE
   SYNTAX      Integer32
   MAX-ACCESS  read-only
   STATUS      current
   DESCRIPTION
      "Path: vlanGroup.status.ports.internalPathCost"
   ::= {sr1645v2VlanGroupPortsEntry 83886080}

sr1645v2VlanGroupPortsIntRpCost OBJECT-TYPE
   SYNTAX      Integer32
   MAX-ACCESS  read-only
   STATUS      current
   DESCRIPTION
      "Path: vlanGroup.status.ports.intRootPathCost"
   ::= {sr1645v2VlanGroupPortsEntry 100663296}

sr1645v2VlanGroupPortsDesBrIdPriority OBJECT-TYPE
   SYNTAX      Integer32
   MAX-ACCESS  read-only
   STATUS      current
   DESCRIPTION
      "Path: vlanGroup.status.ports.designatedBridgeId.priority"
   ::= {sr1645v2VlanGroupPortsEntry 117506048}

sr1645v2VlanGroupPortsDesBrIdMacAddress OBJECT-TYPE
   SYNTAX      OCTET STRING
   MAX-ACCESS  read-only
   STATUS      current
   DESCRIPTION
      "Path: vlanGroup.status.ports.designatedBridgeId.macAddress

       MAC address."
   ::= {sr1645v2VlanGroupPortsEntry 117571584}

sr1645v2VlanGroupPortsDesPrtId OBJECT-TYPE
   SYNTAX      Integer32
   MAX-ACCESS  read-only
   STATUS      current
   DESCRIPTION
      "Path: vlanGroup.status.ports.designatedPortId"
   ::= {sr1645v2VlanGroupPortsEntry 134217728}


sr1645v2VlanGroupMst OBJECT IDENTIFIER ::= {sr1645v2VlanGroup 43}

sr1645v2VlanGroupMstSSCTable OBJECT-TYPE
   SYNTAX      SEQUENCE OF Sr1645v2VlanGroupMstEntry
   MAX-ACCESS  not-accessible
   STATUS      current
   DESCRIPTION
      ""
   ::= {sr1645v2VlanGroupMst 1}

sr1645v2VlanGroupMstEntry OBJECT-TYPE
   SYNTAX      Sr1645v2VlanGroupMstEntry
   MAX-ACCESS  not-accessible
   STATUS      current
   DESCRIPTION
      ""
   INDEX      { sr1645v2VlanGroupMstGlobalIx }
   ::= {sr1645v2VlanGroupMstSSCTable 1}

Sr1645v2VlanGroupMstEntry ::=
   SEQUENCE
      {
      sr1645v2VlanGroupMstGlobalIx
         GlobalIndex,
      sr1645v2VlanGroupMstBridgePriority
         Integer32,
      sr1645v2VlanGroupMstBridgeMacAddress
         OCTET STRING,
      sr1645v2VlanGroupMstMaxHops
         Integer32,
      sr1645v2VlanGroupMstRegionalRootIdPriority
         Integer32,
      sr1645v2VlanGroupMstRegionalRootIdMacAddress
         OCTET STRING,
      sr1645v2VlanGroupMstRootPortId
         Integer32,
      sr1645v2VlanGroupMstIntRootPathCost
         Integer32
      }

sr1645v2VlanGroupMstGlobalIx OBJECT-TYPE
   SYNTAX      GlobalIndex
   MAX-ACCESS  not-accessible
   STATUS      current
   DESCRIPTION
      "The value of the tlsCntTreeGlobalIndex of the MANAGED OBJECT."
   ::= {sr1645v2VlanGroupMstEntry 10}

sr1645v2VlanGroupMstBridgePriority OBJECT-TYPE
   SYNTAX      Integer32
   MAX-ACCESS  read-only
   STATUS      current
   DESCRIPTION
      "Path: vlanGroup.status.mst.bridgePriority"
   ::= {sr1645v2VlanGroupMstEntry 16777216}

sr1645v2VlanGroupMstBridgeMacAddress OBJECT-TYPE
   SYNTAX      OCTET STRING
   MAX-ACCESS  read-only
   STATUS      current
   DESCRIPTION
      "Path: vlanGroup.status.mst.bridgeMacAddress

       MAC address."
   ::= {sr1645v2VlanGroupMstEntry 33554432}

sr1645v2VlanGroupMstMaxHops OBJECT-TYPE
   SYNTAX      Integer32
   MAX-ACCESS  read-only
   STATUS      current
   DESCRIPTION
      "Path: vlanGroup.status.mst.maxHops"
   ::= {sr1645v2VlanGroupMstEntry 50331648}

sr1645v2VlanGroupMstRegionalRootIdPriority OBJECT-TYPE
   SYNTAX      Integer32
   MAX-ACCESS  read-only
   STATUS      current
   DESCRIPTION
      "Path: vlanGroup.status.mst.regionalRootId.priority"
   ::= {sr1645v2VlanGroupMstEntry 67174400}

sr1645v2VlanGroupMstRegionalRootIdMacAddress OBJECT-TYPE
   SYNTAX      OCTET STRING
   MAX-ACCESS  read-only
   STATUS      current
   DESCRIPTION
      "Path: vlanGroup.status.mst.regionalRootId.macAddress

       MAC address."
   ::= {sr1645v2VlanGroupMstEntry 67239936}

sr1645v2VlanGroupMstRootPortId OBJECT-TYPE
   SYNTAX      Integer32
   MAX-ACCESS  read-only
   STATUS      current
   DESCRIPTION
      "Path: vlanGroup.status.mst.rootPortId"
   ::= {sr1645v2VlanGroupMstEntry 83886080}

sr1645v2VlanGroupMstIntRootPathCost OBJECT-TYPE
   SYNTAX      Integer32
   MAX-ACCESS  read-only
   STATUS      current
   DESCRIPTION
      "Path: vlanGroup.status.mst.intRootPathCost"
   ::= {sr1645v2VlanGroupMstEntry 100663296}



END
