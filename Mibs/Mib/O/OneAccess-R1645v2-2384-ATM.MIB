OneAccess-R1645v2-2384-ATM DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2ATM OBJECT IDENTIFIER ::= {r1645Rootv2 2384}

r1645v2ATMMOProp OBJECT IDENTIFIER ::= {r1645v2ATM 1}

r1645v2ATMMOPropEntry OBJECT IDENTIFIER ::= {r1645v2ATMMOProp 1}

r1645v2ATMMOPropPath OBJECT-TYPE
   SYNTAX      ContainmentPath
   MAX-ACCESS  read-only
   STATUS      current
   DESCRIPTION
      "Textual description of the containment tree from the instance of
       the root object down to the instance of the current object."
   ::= {r1645v2ATMMOPropEntry 3}

r1645v2ATMMOPropRev OBJECT-TYPE
   SYNTAX      ObjectRevision
   MAX-ACCESS  read-only
   STATUS      current
   DESCRIPTION
      "This value corresponds with the revision of the MANAGED OBJECT."
   ::= {r1645v2ATMMOPropEntry 4}



er1645v2ATM OBJECT IDENTIFIER ::= {r1645v2ATM 11}


er1645v2ATMCfg OBJECT IDENTIFIER ::= {er1645v2ATM 1}

er1645v2ATMCfgSSCTable OBJECT-TYPE
   SYNTAX      SEQUENCE OF Er1645v2ATMCfgEntry
   MAX-ACCESS  not-accessible
   STATUS      current
   DESCRIPTION
      ""
   ::= {er1645v2ATMCfg 1}

er1645v2ATMCfgEntry OBJECT-TYPE
   SYNTAX      Er1645v2ATMCfgEntry
   MAX-ACCESS  not-accessible
   STATUS      current
   DESCRIPTION
      ""
   INDEX      { er1645v2ATMCfgTableIx }
   ::= {er1645v2ATMCfgSSCTable 1}

Er1645v2ATMCfgEntry ::=
   SEQUENCE
      {
      er1645v2ATMCfgActions
         VariableLengthTableActions,
      er1645v2ATMCfgTableIx
         TableIndex,
      er1645v2ATMCfgName
         DisplayString,
      er1645v2ATMCfgRemark
         DisplayString,
      er1645v2ATMCfgAdminStatus
         INTEGER,
      er1645v2ATMCfgMode
         INTEGER,
      er1645v2ATMCfgPriorityPolicy
         DisplayString,
      er1645v2ATMCfgDelayOptimisation
         INTEGER,
      er1645v2ATMCfgIpVrfRouter
         DisplayString,
      er1645v2ATMCfgIpAdr
         IpAddress,
      er1645v2ATMCfgIpNetm
         IpAddress,
      er1645v2ATMCfgIpSNetName
         INTEGER,
      er1645v2ATMCfgIpSNetCust
         DisplayString,
      er1645v2ATMCfgIpRem
         IpAddress,
      er1645v2ATMCfgIpUnnumbered
         DisplayString,
      er1645v2ATMCfgIpGwPref
         Integer32,
      er1645v2ATMCfgIpRsn
         INTEGER,
      er1645v2ATMCfgIpMtu
         Integer32,
      er1645v2ATMCfgIpMssAdjust
         INTEGER,
      er1645v2ATMCfgIpRipMetric
         Integer32,
      er1645v2ATMCfgIpRipMetricOut
         Integer32,
      er1645v2ATMCfgIpRipMode
         INTEGER,
      er1645v2ATMCfgIpRipTxVer
         INTEGER,
      er1645v2ATMCfgIpRipRxVer
         INTEGER,
      er1645v2ATMCfgIpRipSplitH
         INTEGER,
      er1645v2ATMCfgIpRipAuth
         INTEGER,
      er1645v2ATMCfgIpRipFilter
         DisplayString,
      er1645v2ATMCfgIpRipFilterIn
         DisplayString,
      er1645v2ATMCfgIpRipClearNextHop
         INTEGER,
      er1645v2ATMCfgIpAccPol
         DisplayString,
      er1645v2ATMCfgIpAB
         DisplayString,
      er1645v2ATMCfgIpMA
         INTEGER,
      er1645v2ATMCfgIpMF
         Integer32,
      er1645v2ATMCfgIpDB
         INTEGER,
      er1645v2ATMCfgIpIR
         INTEGER,
      er1645v2ATMCfgIpIgmp
         INTEGER,
      er1645v2ATMCfgIpNN
         DisplayString,
      er1645v2ATMCfgIpPimMode
         INTEGER,
      er1645v2ATMCfgIpPimDrPriority
         Counter32,
      er1645v2ATMCfgIpPimHelloTime
         TimeTicks,
      er1645v2ATMCfgIpPimPropagationDelay
         TimeTicks,
      er1645v2ATMCfgIpPimOverrideInterval
         TimeTicks,
      er1645v2ATMCfgIpPimBsrBorder
         INTEGER,
      er1645v2ATMCfgIpPimTtlThreshold
         Integer32,
      er1645v2ATMCfgIpIMNetworkUnreachable
         INTEGER,
      er1645v2ATMCfgIpIMHostUnreachable
         INTEGER,
      er1645v2ATMCfgIpIMProtocolUnreachable
         INTEGER,
      er1645v2ATMCfgIpIMPortUnreachable
         INTEGER,
      er1645v2ATMCfgIpIMMtuExceeded
         INTEGER,
      er1645v2ATMCfgIpIMAdminProhibited
         INTEGER,
      er1645v2ATMCfgIpIMTtlExceeded
         INTEGER,
      er1645v2ATMCfgIpIMRedirect
         INTEGER,
      er1645v2ATMCfgIpV6VrfRouter
         DisplayString,
      er1645v2ATMCfgIpV6AddrAutoConfigNrDupAddrDetects
         Integer32,
      er1645v2ATMCfgIpV6AddrAutoConfigAcceptRa
         INTEGER,
      er1645v2ATMCfgIpV6AddrAutoConfigAcceptRaRdnss
         INTEGER,
      er1645v2ATMCfgIpV6AddrAutoConfigAcceptRaDnssl
         INTEGER,
      er1645v2ATMCfgIpV6DefaultRoute
         INTEGER,
      er1645v2ATMCfgIpV6RaSend
         INTEGER,
      er1645v2ATMCfgIpV6RaMinInterval
         TimeTicks,
      er1645v2ATMCfgIpV6RaMaxInterval
         TimeTicks,
      er1645v2ATMCfgIpV6RaManagedFlag
         INTEGER,
      er1645v2ATMCfgIpV6RaOtherConfFlag
         INTEGER,
      er1645v2ATMCfgIpV6RaLinkMtu
         Integer32,
      er1645v2ATMCfgIpV6RaReachableTime
         TimeTicks,
      er1645v2ATMCfgIpV6RaRetransmitTime
         TimeTicks,
      er1645v2ATMCfgIpV6RaHopLimit
         Integer32,
      er1645v2ATMCfgIpV6RaDefaultLifeTime
         TimeTicks,
      er1645v2ATMCfgIpV6RaDnsOptionsRdnssLifeTime
         TimeTicks,
      er1645v2ATMCfgIpV6RaDnsOptionsRdnssImportServers
         INTEGER,
      er1645v2ATMCfgIpV6RaDnsOptionsDnsslLifeTime
         TimeTicks,
      er1645v2ATMCfgIpV6RaDnsOptionsDnsslImportDomains
         INTEGER,
      er1645v2ATMCfgIpV6RsSend
         INTEGER,
      er1645v2ATMCfgIpV6RsMaxRandomDelay
         TimeTicks,
      er1645v2ATMCfgIpV6RsInterval
         TimeTicks,
      er1645v2ATMCfgIpV6RsMaxSolicitations
         Integer32,
      er1645v2ATMCfgIpV6TrafficPolicyInbound
         DisplayString,
      er1645v2ATMCfgIpV6TrafficPolicyOutbound
         DisplayString,
      er1645v2ATMCfgIpV6FirewallZone
         DisplayString,
      er1645v2ATMCfgIpV6DhcpClientAddrAC
         INTEGER,
      er1645v2ATMCfgIpV6DhcpClientPrDelMode
         INTEGER,
      er1645v2ATMCfgIpV6DhcpClientPrDelPool
         DisplayString,
      er1645v2ATMCfgIpV6DhcpClientPrDelPdExclOpt
         INTEGER,
      er1645v2ATMCfgIpV6DhcpClientDnsServerPref
         Integer32,
      er1645v2ATMCfgIpV6DhcpClientRapidCommit
         INTEGER,
      er1645v2ATMCfgIpV6DhcpClientTimersSolTimeOut
         TimeTicks,
      er1645v2ATMCfgIpV6DhcpClientTimersSolMaxRt
         TimeTicks,
      er1645v2ATMCfgIpV6DhcpClientTimersInfoRefresh
         TimeTicks,
      er1645v2ATMCfgIpV6DhcpServerMode
         INTEGER,
      er1645v2ATMCfgIpV6DhcpServerPreference
         Integer32,
      er1645v2ATMCfgIpV6DhcpServerPool
         DisplayString,
      er1645v2ATMCfgIpV6DhcpServerRapidCommit
         INTEGER,
      er1645v2ATMCfgIpV6DhcpServerTimersInfoRefresh
         TimeTicks,
      er1645v2ATMCfgIpV6DhcpRelayMode
         INTEGER,
      er1645v2ATMCfgIpV6SendRedirect
         INTEGER,
      er1645v2ATMCfgIpV6LinkMtu
         Integer32,
      er1645v2ATMCfgIpV6InterfaceId
         OCTET STRING,
      er1645v2ATMCfgIpV6MF
         Integer32,
      er1645v2ATMCfgIpV6IcmpMessagesNoRoute
         INTEGER,
      er1645v2ATMCfgIpV6IcmpMessagesBeyondScope
         INTEGER,
      er1645v2ATMCfgIpV6IcmpMessagesAddressUnreachable
         INTEGER,
      er1645v2ATMCfgIpV6IcmpMessagesPortUnreachable
         INTEGER,
      er1645v2ATMCfgIpV6IcmpMessagesPacketTooBig
         INTEGER,
      er1645v2ATMCfgIpV6IcmpMessagesHopLimitExceeded
         INTEGER,
      er1645v2ATMCfgIpV6IcmpMessagesFragTimeExceeded
         INTEGER,
      er1645v2ATMCfgIpV6IcmpMessagesHeaderFieldErr
         INTEGER,
      er1645v2ATMCfgIpV6IcmpMessagesOptionUnrecognized
         INTEGER,
      er1645v2ATMCfgIpV6IcmpMessagesRedirect
         INTEGER,
      er1645v2ATMCfgBridgingAccList
         DisplayString,
      er1645v2ATMCfgBridgingInACL
         DisplayString,
      er1645v2ATMCfgBridgingTp
         DisplayString,
      er1645v2ATMCfgBridgingBrGrp
         DisplayString,
      er1645v2ATMCfgBridgingLimBC
         INTEGER,
      er1645v2ATMCfgBridgingPrivateMode
         INTEGER,
      er1645v2ATMCfgBridgingLearning
         INTEGER,
      er1645v2ATMCfgBridgingMaxCacheSize
         INTEGER,
      er1645v2ATMCfgBridgingRelearnDropOnRelearn
         INTEGER,
      er1645v2ATMCfgBridgingRelearnShutdownThreshold
         Integer32,
      er1645v2ATMCfgBridgingRelearnShutdownTime
         TimeTicks,
      er1645v2ATMCfgBridgingRelearnLoopDetection
         INTEGER,
      er1645v2ATMCfgBridgingRelearnLoopDetectionInterval
         TimeTicks,
      er1645v2ATMCfgBridgingVlanMemberShip
         INTEGER,
      er1645v2ATMCfgBridgingVlTUntaggedAction
         INTEGER,
      er1645v2ATMCfgBridgingVlTUntaggedTagInfoTpid
         INTEGER,
      er1645v2ATMCfgBridgingVlTUntaggedTagInfoVid
         Integer32,
      er1645v2ATMCfgBridgingVlTUnknownVlansAction
         INTEGER,
      er1645v2ATMCfgBridgingVlTUnknownVlansTagInfoTpid
         INTEGER,
      er1645v2ATMCfgBridgingVlTUnknownVlansTagInfoVid
         Integer32,
      er1645v2ATMCfgBridgingDot1adType
         INTEGER,
      er1645v2ATMCfgBridgingPriority
         Integer32,
      er1645v2ATMCfgBridgingPathCost
         Integer32,
      er1645v2ATMCfgBridgingInternalPathCost
         Integer32,
      er1645v2ATMCfgBridgingTCD
         INTEGER,
      er1645v2ATMCfgBridgingRestrictedRole
         INTEGER,
      er1645v2ATMCfgBridgingAdminEdge
         INTEGER,
      er1645v2ATMCfgBridgingOamMacDeviceMac
         DisplayString,
      er1645v2ATMCfgBridgingOamMacUserMac
         OCTET STRING,
      er1645v2ATMCfgBridgingOamMacBridgeMac
         DisplayString,
      er1645v2ATMCfgBridgingMgmtInline
         INTEGER,
      er1645v2ATMCfgBridgingL2ptMode
         INTEGER,
      er1645v2ATMCfgBridgingL2ptProtocols
         Integer32,
      er1645v2ATMCfgBridgingL2ptDestMac
         OCTET STRING,
      er1645v2ATMCfgBridgingL2ptCos
         INTEGER,
      er1645v2ATMCfgBridgingL2ptDropThrStp
         INTEGER,
      er1645v2ATMCfgBridgingL2ptDropThrLldp
         INTEGER,
      er1645v2ATMCfgBridgingL2ptDropThrOam
         INTEGER,
      er1645v2ATMCfgBridgingL2ptDropThrCdp
         INTEGER,
      er1645v2ATMCfgBridgingL2ptDropThrVtp
         INTEGER,
      er1645v2ATMCfgBridgingL2ptDropThrLacp
         INTEGER,
      er1645v2ATMCfgBridgingL2ptDropThrEfmOam
         INTEGER,
      er1645v2ATMCfgBridgingL2ptDropThrPvst
         INTEGER,
      er1645v2ATMCfgBridgingL2ptDropThrMmrp
         INTEGER,
      er1645v2ATMCfgBridgingL2ptDropThrMvrp
         INTEGER,
      er1645v2ATMCfgBridgingL2ptDropThrGvrp
         INTEGER,
      er1645v2ATMCfgBridgingL2ptDropThrGmrp
         INTEGER,
      er1645v2ATMCfgBridgingL2ptDropThrDtp
         INTEGER,
      er1645v2ATMCfgBridgingL2ptDropThrPagp
         INTEGER,
      er1645v2ATMCfgBridgingL2ptDropThrUdld
         INTEGER,
      er1645v2ATMCfgVirtEthernetVirtualEthernet
         DisplayString,
      er1645v2ATMCfgAtmVpi
         Integer32,
      er1645v2ATMCfgAtmVci
         Integer32,
      er1645v2ATMCfgAtmHighLayProt
         INTEGER,
      er1645v2ATMCfgAtmMultiProt
         INTEGER,
      er1645v2ATMCfgAtmServCat
         INTEGER,
      er1645v2ATMCfgAtmPeakCellRate
         INTEGER,
      er1645v2ATMCfgAtmSustCellRate
         INTEGER,
      er1645v2ATMCfgAtmMaxBurstSize
         Integer32,
      er1645v2ATMCfgAtmInArpTimeOut
         TimeTicks,
      er1645v2ATMCfgAtmF5LbOper
         INTEGER,
      er1645v2ATMCfgAtmF5LbInterval
         TimeTicks,
      er1645v2ATMCfgAtmF5LbFailsPerm
         Integer32,
      er1645v2ATMCfgAtmF5LbTar
         INTEGER,
      er1645v2ATMCfgAtmF5ccDir
         INTEGER,
      er1645v2ATMCfgAtmF5ccTar
         INTEGER,
      er1645v2ATMCfgAtmF5ccTxMode
         INTEGER,
      er1645v2ATMCfgAtmF5ccTxTxPer
         TimeTicks,
      er1645v2ATMCfgAtmF5ccRxRcvTim
         TimeTicks,
      er1645v2ATMCfgAtmF5ccActProc
         INTEGER,
      er1645v2ATMCfgAtmF5ccActTim
         TimeTicks,
      er1645v2ATMCfgAtmF5ccActCnt
         Integer32,
      er1645v2ATMCfgAtmCpt
         INTEGER,
      er1645v2ATMCfgPppLnkMOperation
         INTEGER,
      er1645v2ATMCfgPppLnkMInterval
         TimeTicks,
      er1645v2ATMCfgPppLnkMRepTimeOut
         TimeTicks,
      er1645v2ATMCfgPppLnkMFailsPrmt
         Integer32,
      er1645v2ATMCfgPppAuthentication
         INTEGER,
      er1645v2ATMCfgPppAuthenPeriod
         TimeTicks,
      er1645v2ATMCfgPppCompression
         INTEGER,
      er1645v2ATMCfgPppSessionName
         DisplayString,
      er1645v2ATMCfgPppSessionSecret
         DisplayString,
      er1645v2ATMCfgPppEncModeSessionSecret
         INTEGER,
      er1645v2ATMCfgPppEncSessionSecret
         DisplayString,
      er1645v2ATMCfgPppServiceName
         DisplayString,
      er1645v2ATMCfgInbBwCir
         Integer32,
      er1645v2ATMCfgInbBwTc
         INTEGER,
      er1645v2ATMCfgInbBwCorrType
         INTEGER,
      er1645v2ATMCfgInbBwCorrPredefEncapsFrameRelay
         DisplayString,
      er1645v2ATMCfgInbBwCorrPredefEncapsPpp
         DisplayString,
      er1645v2ATMCfgInbBwCorrPredefEncapsAtmHl
         INTEGER,
      er1645v2ATMCfgInbBwCorrPredefEncapsAtmMp
         INTEGER,
      er1645v2ATMCfgInbBwCorrPredefEncapsHdlc
         DisplayString,
      er1645v2ATMCfgInbBwCorrPredefEncapsEfmFs
         Integer32,
      er1645v2ATMCfgInbBwCorrPredefEncapsEfmIb
         Integer32,
      er1645v2ATMCfgInbBwCorrPredefMode
         INTEGER,
      er1645v2ATMCfgInbBwCorrManualOverhead
         Integer32,
      er1645v2ATMCfgInbBwCorrManualFrameData
         Counter32,
      er1645v2ATMCfgInbBwCorrManualFrameHeader
         Counter32,
      er1645v2ATMCfgInbBwMaxFifoQLen
         Integer32,
      er1645v2ATMCfgInbBwPriorityPolicy
         DisplayString
      }

er1645v2ATMCfgActions OBJECT-TYPE
   SYNTAX      VariableLengthTableActions
   MAX-ACCESS  read-write
   STATUS      current
   DESCRIPTION
      "By way of this field, some manipulations
       on this table may be performed."
   ::= {er1645v2ATMCfgEntry 2}

er1645v2ATMCfgTableIx OBJECT-TYPE
   SYNTAX      TableIndex
   MAX-ACCESS  not-accessible
   STATUS      current
   DESCRIPTION
      ""
   ::= {er1645v2ATMCfgEntry 11}

er1645v2ATMCfgName OBJECT-TYPE
   SYNTAX      DisplayString
   MAX-ACCESS  read-write
   STATUS      current
   DESCRIPTION
      "Path: atm.editConf.pvcTable.name"
   ::= {er1645v2ATMCfgEntry 16777216}

er1645v2ATMCfgRemark OBJECT-TYPE
   SYNTAX      DisplayString
   MAX-ACCESS  read-write
   STATUS      current
   DESCRIPTION
      "Path: atm.editConf.pvcTable.remark"
   ::= {er1645v2ATMCfgEntry 1157627904}

er1645v2ATMCfgAdminStatus OBJECT-TYPE
   SYNTAX      INTEGER
               {
               up (1),
               down (2)
               }
   MAX-ACCESS  read-write
   STATUS      current
   DESCRIPTION
      "Path: atm.editConf.pvcTable.adminStatus

       Possibilities:
               up   (1)
               down   (2)"
   ::= {er1645v2ATMCfgEntry 33554432}

er1645v2ATMCfgMode OBJECT-TYPE
   SYNTAX      INTEGER
               {
               routing (1),
               bridging (2),
               routingAndBridging (3),
               multiLink (8),
               ipV6 (16),
               virtEthernet (32)
               }
   MAX-ACCESS  read-write
   STATUS      current
   DESCRIPTION
      "Path: atm.editConf.pvcTable.mode

       Possibilities:
               routing   (1)
               bridging   (2)
               routingAndBridging   (3)
               multiLink   (8)
               ipV6   (16)
               virtEthernet   (32)"
   ::= {er1645v2ATMCfgEntry 67108864}

er1645v2ATMCfgPriorityPolicy OBJECT-TYPE
   SYNTAX      DisplayString
   MAX-ACCESS  read-write
   STATUS      current
   DESCRIPTION
      "Path: atm.editConf.pvcTable.priorityPolicy"
   ::= {er1645v2ATMCfgEntry 83886080}

er1645v2ATMCfgDelayOptimisation OBJECT-TYPE
   SYNTAX      INTEGER
               {
               disabled (0),
               enabled (1)
               }
   MAX-ACCESS  read-write
   STATUS      current
   DESCRIPTION
      "Path: atm.editConf.pvcTable.delayOptimisation

       Possibilities:
               disabled   (0)
               enabled   (1)"
   ::= {er1645v2ATMCfgEntry 553648128}

er1645v2ATMCfgIpVrfRouter OBJECT-TYPE
   SYNTAX      DisplayString
   MAX-ACCESS  read-write
   STATUS      current
   DESCRIPTION
      "Path: atm.editConf.pvcTable.ip.vrfRouter"
   ::= {er1645v2ATMCfgEntry 53215232}

er1645v2ATMCfgIpAdr OBJECT-TYPE
   SYNTAX      IpAddress
   MAX-ACCESS  read-write
   STATUS      current
   DESCRIPTION
      "Path: atm.editConf.pvcTable.ip.address"
   ::= {er1645v2ATMCfgEntry 58261504}

er1645v2ATMCfgIpNetm OBJECT-TYPE
   SYNTAX      IpAddress
   MAX-ACCESS  read-write
   STATUS      current
   DESCRIPTION
      "Path: atm.editConf.pvcTable.ip.netMask"
   ::= {er1645v2ATMCfgEntry 58392576}

er1645v2ATMCfgIpSNetName OBJECT-TYPE
   SYNTAX      INTEGER
               {
               slOPTg (0),
               corp (2),
               dmz (3),
               internet (1)
               }
   MAX-ACCESS  read-write
   STATUS      current
   DESCRIPTION
      "Path: atm.editConf.pvcTable.ip.sNet.name

       Possibilities:
               <OPT>   (0)
               corp   (2)
               dmz   (3)
               internet   (1)"
   ::= {er1645v2ATMCfgEntry 53674240}

er1645v2ATMCfgIpSNetCust OBJECT-TYPE
   SYNTAX      DisplayString
   MAX-ACCESS  read-write
   STATUS      current
   DESCRIPTION
      "Path: atm.editConf.pvcTable.ip.sNet.custom"
   ::= {er1645v2ATMCfgEntry 53674496}

er1645v2ATMCfgIpRem OBJECT-TYPE
   SYNTAX      IpAddress
   MAX-ACCESS  read-write
   STATUS      current
   DESCRIPTION
      "Path: atm.editConf.pvcTable.ip.remote"
   ::= {er1645v2ATMCfgEntry 58458112}

er1645v2ATMCfgIpUnnumbered OBJECT-TYPE
   SYNTAX      DisplayString
   MAX-ACCESS  read-write
   STATUS      current
   DESCRIPTION
      "Path: atm.editConf.pvcTable.ip.unnumbered"
   ::= {er1645v2ATMCfgEntry 52625408}

er1645v2ATMCfgIpGwPref OBJECT-TYPE
   SYNTAX      Integer32
   MAX-ACCESS  read-write
   STATUS      current
   DESCRIPTION
      "Path: atm.editConf.pvcTable.ip.gatewayPreference"
   ::= {er1645v2ATMCfgEntry 52690944}

er1645v2ATMCfgIpRsn OBJECT-TYPE
   SYNTAX      INTEGER
               {
               disabled (0),
               enabled (1)
               }
   MAX-ACCESS  read-write
   STATUS      current
   DESCRIPTION
      "Path: atm.editConf.pvcTable.ip.requestSubnet

       Possibilities:
               disabled   (0)
               enabled   (1)"
   ::= {er1645v2ATMCfgEntry 56688640}

er1645v2ATMCfgIpMtu OBJECT-TYPE
   SYNTAX      Integer32
   MAX-ACCESS  read-write
   STATUS      current
   DESCRIPTION
      "Path: atm.editConf.pvcTable.ip.mtu"
   ::= {er1645v2ATMCfgEntry 52953088}

er1645v2ATMCfgIpMssAdjust OBJECT-TYPE
   SYNTAX      INTEGER
               {
               disabled (0),
               auto (65536)
               }
   MAX-ACCESS  read-write
   STATUS      current
   DESCRIPTION
      "Path: atm.editConf.pvcTable.ip.mssAdjust

       Possibilities:
               disabled   (0)
               auto   (65536)"
   ::= {er1645v2ATMCfgEntry 53280768}

er1645v2ATMCfgIpRipMetric OBJECT-TYPE
   SYNTAX      Integer32
   MAX-ACCESS  read-write
   STATUS      current
   DESCRIPTION
      "Path: atm.editConf.pvcTable.ip.rip.metric"
   ::= {er1645v2ATMCfgEntry 51712768}

er1645v2ATMCfgIpRipMetricOut OBJECT-TYPE
   SYNTAX      Integer32
   MAX-ACCESS  read-write
   STATUS      current
   DESCRIPTION
      "Path: atm.editConf.pvcTable.ip.rip.metricOut"
   ::= {er1645v2ATMCfgEntry 51713024}

er1645v2ATMCfgIpRipMode OBJECT-TYPE
   SYNTAX      INTEGER
               {
               disabled (0),
               passive (1),
               active (2)
               }
   MAX-ACCESS  read-write
   STATUS      current
   DESCRIPTION
      "Path: atm.editConf.pvcTable.ip.rip.mode

       Possibilities:
               disabled   (0)
               passive   (1)
               active   (2)"
   ::= {er1645v2ATMCfgEntry 51713280}

er1645v2ATMCfgIpRipTxVer OBJECT-TYPE
   SYNTAX      INTEGER
               {
               rip1 (0),
               rip2 (1),
               rip1mcompatible (2)
               }
   MAX-ACCESS  read-write
   STATUS      current
   DESCRIPTION
      "Path: atm.editConf.pvcTable.ip.rip.txVersion

       Possibilities:
               rip1   (0)
               rip2   (1)
               rip1-compatible   (2)"
   ::= {er1645v2ATMCfgEntry 51716864}

er1645v2ATMCfgIpRipRxVer OBJECT-TYPE
   SYNTAX      INTEGER
               {
               rip1only (0),
               rip2only (1),
               rip12 (2)
               }
   MAX-ACCESS  read-write
   STATUS      current
   DESCRIPTION
      "Path: atm.editConf.pvcTable.ip.rip.rxVersion

       Possibilities:
               rip1only   (0)
               rip2only   (1)
               rip1&2   (2)"
   ::= {er1645v2ATMCfgEntry 51717120}

er1645v2ATMCfgIpRipSplitH OBJECT-TYPE
   SYNTAX      INTEGER
               {
               disabled (0),
               enabled (1),
               poisonedReverse (2)
               }
   MAX-ACCESS  read-write
   STATUS      current
   DESCRIPTION
      "Path: atm.editConf.pvcTable.ip.rip.splitHorizon

       Possibilities:
               disabled   (0)
               enabled   (1)
               poisonedReverse   (2)"
   ::= {er1645v2ATMCfgEntry 51713792}

er1645v2ATMCfgIpRipAuth OBJECT-TYPE
   SYNTAX      INTEGER
               {
               disabled (0),
               texts (1),
               md5 (2)
               }
   MAX-ACCESS  read-write
   STATUS      current
   DESCRIPTION
      "Path: atm.editConf.pvcTable.ip.rip.authentication

       Possibilities:
               disabled   (0)
               text    (1)
               md5   (2)"
   ::= {er1645v2ATMCfgEntry 51712512}

er1645v2ATMCfgIpRipFilter OBJECT-TYPE
   SYNTAX      DisplayString
   MAX-ACCESS  read-write
   STATUS      current
   DESCRIPTION
      "Path: atm.editConf.pvcTable.ip.rip.filter"
   ::= {er1645v2ATMCfgEntry 51716096}

er1645v2ATMCfgIpRipFilterIn OBJECT-TYPE
   SYNTAX      DisplayString
   MAX-ACCESS  read-write
   STATUS      current
   DESCRIPTION
      "Path: atm.editConf.pvcTable.ip.rip.filterIn"
   ::= {er1645v2ATMCfgEntry 51716352}

er1645v2ATMCfgIpRipClearNextHop OBJECT-TYPE
   SYNTAX      INTEGER
               {
               disabled (0),
               enabled (1)
               }
   MAX-ACCESS  read-write
   STATUS      current
   DESCRIPTION
      "Path: atm.editConf.pvcTable.ip.rip.clearNextHop

       Possibilities:
               disabled   (0)
               enabled   (1)"
   ::= {er1645v2ATMCfgEntry 51708416}

er1645v2ATMCfgIpAccPol OBJECT-TYPE
   SYNTAX      DisplayString
   MAX-ACCESS  read-write
   STATUS      current
   DESCRIPTION
      "Path: atm.editConf.pvcTable.ip.accessPolicy"
   ::= {er1645v2ATMCfgEntry 53084160}

er1645v2ATMCfgIpAB OBJECT-TYPE
   SYNTAX      DisplayString
   MAX-ACCESS  read-write
   STATUS      current
   DESCRIPTION
      "Path: atm.editConf.pvcTable.ip.trafficPolicy"
   ::= {er1645v2ATMCfgEntry 51249152}

er1645v2ATMCfgIpMA OBJECT-TYPE
   SYNTAX      INTEGER
               {
               disabled (0),
               enabled (1)
               }
   MAX-ACCESS  read-write
   STATUS      current
   DESCRIPTION
      "Path: atm.editConf.pvcTable.ip.mgmtAccess

       Possibilities:
               disabled   (0)
               enabled   (1)"
   ::= {er1645v2ATMCfgEntry 51380224}

er1645v2ATMCfgIpMF OBJECT-TYPE
   SYNTAX      Integer32
   MAX-ACCESS  read-write
   STATUS      current
   DESCRIPTION
      "Path: atm.editConf.pvcTable.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2ATMCfgEntry 51445760}

er1645v2ATMCfgIpDB OBJECT-TYPE
   SYNTAX      INTEGER
               {
               disabled (0),
               enabled (1)
               }
   MAX-ACCESS  read-write
   STATUS      current
   DESCRIPTION
      "Path: atm.editConf.pvcTable.ip.directedBroadcasts

       Possibilities:
               disabled   (0)
               enabled   (1)"
   ::= {er1645v2ATMCfgEntry 51773440}

er1645v2ATMCfgIpIR OBJECT-TYPE
   SYNTAX      INTEGER
               {
               disabled (0),
               enabled (1)
               }
   MAX-ACCESS  read-write
   STATUS      current
   DESCRIPTION
      "Path: atm.editConf.pvcTable.ip.icmpRedirects

       Possibilities:
               disabled   (0)
               enabled   (1)"
   ::= {er1645v2ATMCfgEntry 52035584}

er1645v2ATMCfgIpIgmp OBJECT-TYPE
   SYNTAX      INTEGER
               {
               disabled (0),
               proxy (1),
               router (2),
               v3Router (5)
               }
   MAX-ACCESS  read-write
   STATUS      current
   DESCRIPTION
      "Path: atm.editConf.pvcTable.ip.igmp

       Possibilities:
               disabled   (0)
               proxy   (1)
               router   (2)
               v3Router   (5)"
   ::= {er1645v2ATMCfgEntry 52428800}

er1645v2ATMCfgIpNN OBJECT-TYPE
   SYNTAX      DisplayString
   MAX-ACCESS  read-write
   STATUS      current
   DESCRIPTION
      "Path: atm.editConf.pvcTable.ip.nat"
   ::= {er1645v2ATMCfgEntry 52101120}

er1645v2ATMCfgIpPimMode OBJECT-TYPE
   SYNTAX      INTEGER
               {
               disabled (0),
               sparse (1),
               passive (2)
               }
   MAX-ACCESS  read-write
   STATUS      current
   DESCRIPTION
      "Path: atm.editConf.pvcTable.ip.pim.mode

       Possibilities:
               disabled   (0)
               sparse   (1)
               passive   (2)"
   ::= {er1645v2ATMCfgEntry 53346560}

er1645v2ATMCfgIpPimDrPriority OBJECT-TYPE
   SYNTAX      Counter32
   MAX-ACCESS  read-write
   STATUS      current
   DESCRIPTION
      "Path: atm.editConf.pvcTable.ip.pim.drPriority

       32 bit unsigned wrappable counter."
   ::= {er1645v2ATMCfgEntry 53346816}

er1645v2ATMCfgIpPimHelloTime OBJECT-TYPE
   SYNTAX      TimeTicks
   MAX-ACCESS  read-write
   STATUS      current
   DESCRIPTION
      "Path: atm.editConf.pvcTable.ip.pim.helloTime

       Time in centi-second."
   ::= {er1645v2ATMCfgEntry 53347072}

er1645v2ATMCfgIpPimPropagationDelay OBJECT-TYPE
   SYNTAX      TimeTicks
   MAX-ACCESS  read-write
   STATUS      current
   DESCRIPTION
      "Path: atm.editConf.pvcTable.ip.pim.propagationDelay

       Time in centi-second."
   ::= {er1645v2ATMCfgEntry 53347328}

er1645v2ATMCfgIpPimOverrideInterval OBJECT-TYPE
   SYNTAX      TimeTicks
   MAX-ACCESS  read-write
   STATUS      current
   DESCRIPTION
      "Path: atm.editConf.pvcTable.ip.pim.overrideInterval

       Time in centi-second."
   ::= {er1645v2ATMCfgEntry 53347584}

er1645v2ATMCfgIpPimBsrBorder OBJECT-TYPE
   SYNTAX      INTEGER
               {
               disabled (0),
               enabled (1)
               }
   MAX-ACCESS  read-write
   STATUS      current
   DESCRIPTION
      "Path: atm.editConf.pvcTable.ip.pim.bsrBorder

       Possibilities:
               disabled   (0)
               enabled   (1)"
   ::= {er1645v2ATMCfgEntry 53347840}

er1645v2ATMCfgIpPimTtlThreshold OBJECT-TYPE
   SYNTAX      Integer32
   MAX-ACCESS  read-write
   STATUS      current
   DESCRIPTION
      "Path: atm.editConf.pvcTable.ip.pim.ttlThreshold"
   ::= {er1645v2ATMCfgEntry 53348096}

er1645v2ATMCfgIpIMNetworkUnreachable OBJECT-TYPE
   SYNTAX      INTEGER
               {
               disabled (0),
               enabled (1)
               }
   MAX-ACCESS  read-write
   STATUS      current
   DESCRIPTION
      "Path: atm.editConf.pvcTable.ip.icmpMessages.networkUnreachable

       Possibilities:
               disabled   (0)
               enabled   (1)"
   ::= {er1645v2ATMCfgEntry 53412096}

er1645v2ATMCfgIpIMHostUnreachable OBJECT-TYPE
   SYNTAX      INTEGER
               {
               disabled (0),
               enabled (1)
               }
   MAX-ACCESS  read-write
   STATUS      current
   DESCRIPTION
      "Path: atm.editConf.pvcTable.ip.icmpMessages.hostUnreachable

       Possibilities:
               disabled   (0)
               enabled   (1)"
   ::= {er1645v2ATMCfgEntry 53412352}

er1645v2ATMCfgIpIMProtocolUnreachable OBJECT-TYPE
   SYNTAX      INTEGER
               {
               disabled (0),
               enabled (1)
               }
   MAX-ACCESS  read-write
   STATUS      current
   DESCRIPTION
      "Path: atm.editConf.pvcTable.ip.icmpMessages.protocolUnreachable

       Possibilities:
               disabled   (0)
               enabled   (1)"
   ::= {er1645v2ATMCfgEntry 53412608}

er1645v2ATMCfgIpIMPortUnreachable OBJECT-TYPE
   SYNTAX      INTEGER
               {
               disabled (0),
               enabled (1)
               }
   MAX-ACCESS  read-write
   STATUS      current
   DESCRIPTION
      "Path: atm.editConf.pvcTable.ip.icmpMessages.portUnreachable

       Possibilities:
               disabled   (0)
               enabled   (1)"
   ::= {er1645v2ATMCfgEntry 53412864}

er1645v2ATMCfgIpIMMtuExceeded OBJECT-TYPE
   SYNTAX      INTEGER
               {
               disabled (0),
               enabled (1)
               }
   MAX-ACCESS  read-write
   STATUS      current
   DESCRIPTION
      "Path: atm.editConf.pvcTable.ip.icmpMessages.mtuExceeded

       Possibilities:
               disabled   (0)
               enabled   (1)"
   ::= {er1645v2ATMCfgEntry 53413120}

er1645v2ATMCfgIpIMAdminProhibited OBJECT-TYPE
   SYNTAX      INTEGER
               {
               disabled (0),
               enabled (1)
               }
   MAX-ACCESS  read-write
   STATUS      current
   DESCRIPTION
      "Path: atm.editConf.pvcTable.ip.icmpMessages.adminProhibited

       Possibilities:
               disabled   (0)
               enabled   (1)"
   ::= {er1645v2ATMCfgEntry 53413376}

er1645v2ATMCfgIpIMTtlExceeded OBJECT-TYPE
   SYNTAX      INTEGER
               {
               disabled (0),
               enabled (1)
               }
   MAX-ACCESS  read-write
   STATUS      current
   DESCRIPTION
      "Path: atm.editConf.pvcTable.ip.icmpMessages.ttlExceeded

       Possibilities:
               disabled   (0)
               enabled   (1)"
   ::= {er1645v2ATMCfgEntry 53413632}

er1645v2ATMCfgIpIMRedirect OBJECT-TYPE
   SYNTAX      INTEGER
               {
               disabled (0),
               enabled (1)
               }
   MAX-ACCESS  read-write
   STATUS      current
   DESCRIPTION
      "Path: atm.editConf.pvcTable.ip.icmpMessages.redirect

       Possibilities:
               disabled   (0)
               enabled   (1)"
   ::= {er1645v2ATMCfgEntry 53413888}

er1645v2ATMCfgIpV6VrfRouter OBJECT-TYPE
   SYNTAX      DisplayString
   MAX-ACCESS  read-write
   STATUS      current
   DESCRIPTION
      "Path: atm.editConf.pvcTable.ipV6.vrfRouter"
   ::= {er1645v2ATMCfgEntry 704708608}

er1645v2ATMCfgIpV6AddrAutoConfigNrDupAddrDetects OBJECT-TYPE
   SYNTAX      Integer32
   MAX-ACCESS  read-write
   STATUS      current
   DESCRIPTION
      "Path: atm.editConf.pvcTable.ipV6.addrAutoConfig.nrDupAddrDetects"
   ::= {er1645v2ATMCfgEntry 704905472}

er1645v2ATMCfgIpV6AddrAutoConfigAcceptRa OBJECT-TYPE
   SYNTAX      INTEGER
               {
               disabled (0),
               enabled (1)
               }
   MAX-ACCESS  read-write
   STATUS      current
   DESCRIPTION
      "Path: atm.editConf.pvcTable.ipV6.addrAutoConfig.acceptRa

       Possibilities:
               disabled   (0)
               enabled   (1)"
   ::= {er1645v2ATMCfgEntry 704905728}

er1645v2ATMCfgIpV6AddrAutoConfigAcceptRaRdnss OBJECT-TYPE
   SYNTAX      INTEGER
               {
               disabled (0),
               enabled (1)
               }
   MAX-ACCESS  read-write
   STATUS      current
   DESCRIPTION
      "Path: atm.editConf.pvcTable.ipV6.addrAutoConfig.acceptRaRdnss

       Possibilities:
               disabled   (0)
               enabled   (1)"
   ::= {er1645v2ATMCfgEntry 704905984}

er1645v2ATMCfgIpV6AddrAutoConfigAcceptRaDnssl OBJECT-TYPE
   SYNTAX      INTEGER
               {
               disabled (0),
               enabled (1)
               }
   MAX-ACCESS  read-write
   STATUS      current
   DESCRIPTION
      "Path: atm.editConf.pvcTable.ipV6.addrAutoConfig.acceptRaDnssl

       Possibilities:
               disabled   (0)
               enabled   (1)"
   ::= {er1645v2ATMCfgEntry 704906240}

er1645v2ATMCfgIpV6DefaultRoute OBJECT-TYPE
   SYNTAX      INTEGER
               {
               disabled (0),
               enabled (1)
               }
   MAX-ACCESS  read-write
   STATUS      current
   DESCRIPTION
      "Path: atm.editConf.pvcTable.ipV6.defaultRoute

       Possibilities:
               disabled   (0)
               enabled   (1)"
   ::= {er1645v2ATMCfgEntry 704970752}

er1645v2ATMCfgIpV6RaSend OBJECT-TYPE
   SYNTAX      INTEGER
               {
               disabled (0),
               enabled (1)
               }
   MAX-ACCESS  read-write
   STATUS      current
   DESCRIPTION
      "Path: atm.editConf.pvcTable.ipV6.ra.send

       Possibilities:
               disabled   (0)
               enabled   (1)"
   ::= {er1645v2ATMCfgEntry 705036544}

er1645v2ATMCfgIpV6RaMinInterval OBJECT-TYPE
   SYNTAX      TimeTicks
   MAX-ACCESS  read-write
   STATUS      current
   DESCRIPTION
      "Path: atm.editConf.pvcTable.ipV6.ra.minInterval

       Time in centi-second."
   ::= {er1645v2ATMCfgEntry 705036800}

er1645v2ATMCfgIpV6RaMaxInterval OBJECT-TYPE
   SYNTAX      TimeTicks
   MAX-ACCESS  read-write
   STATUS      current
   DESCRIPTION
      "Path: atm.editConf.pvcTable.ipV6.ra.maxInterval

       Time in centi-second."
   ::= {er1645v2ATMCfgEntry 705037056}

er1645v2ATMCfgIpV6RaManagedFlag OBJECT-TYPE
   SYNTAX      INTEGER
               {
               disabled (0),
               enabled (1)
               }
   MAX-ACCESS  read-write
   STATUS      current
   DESCRIPTION
      "Path: atm.editConf.pvcTable.ipV6.ra.managedFlag

       Possibilities:
               disabled   (0)
               enabled   (1)"
   ::= {er1645v2ATMCfgEntry 705037312}

er1645v2ATMCfgIpV6RaOtherConfFlag OBJECT-TYPE
   SYNTAX      INTEGER
               {
               disabled (0),
               enabled (1)
               }
   MAX-ACCESS  read-write
   STATUS      current
   DESCRIPTION
      "Path: atm.editConf.pvcTable.ipV6.ra.otherConfFlag

       Possibilities:
               disabled   (0)
               enabled   (1)"
   ::= {er1645v2ATMCfgEntry 705037568}

er1645v2ATMCfgIpV6RaLinkMtu OBJECT-TYPE
   SYNTAX      Integer32
   MAX-ACCESS  read-write
   STATUS      current
   DESCRIPTION
      "Path: atm.editConf.pvcTable.ipV6.ra.linkMtu"
   ::= {er1645v2ATMCfgEntry 705037824}

er1645v2ATMCfgIpV6RaReachableTime OBJECT-TYPE
   SYNTAX      TimeTicks
   MAX-ACCESS  read-write
   STATUS      current
   DESCRIPTION
      "Path: atm.editConf.pvcTable.ipV6.ra.reachableTime

       Time in centi-second."
   ::= {er1645v2ATMCfgEntry 705038080}

er1645v2ATMCfgIpV6RaRetransmitTime OBJECT-TYPE
   SYNTAX      TimeTicks
   MAX-ACCESS  read-write
   STATUS      current
   DESCRIPTION
      "Path: atm.editConf.pvcTable.ipV6.ra.retransmitTime

       Time in centi-second."
   ::= {er1645v2ATMCfgEntry 705038336}

er1645v2ATMCfgIpV6RaHopLimit OBJECT-TYPE
   SYNTAX      Integer32
   MAX-ACCESS  read-write
   STATUS      current
   DESCRIPTION
      "Path: atm.editConf.pvcTable.ipV6.ra.hopLimit"
   ::= {er1645v2ATMCfgEntry 705038592}

er1645v2ATMCfgIpV6RaDefaultLifeTime OBJECT-TYPE
   SYNTAX      TimeTicks
   MAX-ACCESS  read-write
   STATUS      current
   DESCRIPTION
      "Path: atm.editConf.pvcTable.ipV6.ra.defaultLifeTime

       Time in centi-second."
   ::= {er1645v2ATMCfgEntry 705038848}

er1645v2ATMCfgIpV6RaDnsOptionsRdnssLifeTime OBJECT-TYPE
   SYNTAX      TimeTicks
   MAX-ACCESS  read-write
   STATUS      current
   DESCRIPTION
      "Path: atm.editConf.pvcTable.ipV6.ra.dnsOptions.rdnss.lifeTime

       Time in centi-second."
   ::= {er1645v2ATMCfgEntry 705039140}

er1645v2ATMCfgIpV6RaDnsOptionsRdnssImportServers OBJECT-TYPE
   SYNTAX      INTEGER
               {
               disabled (0),
               enabled (1)
               }
   MAX-ACCESS  read-write
   STATUS      current
   DESCRIPTION
      "Path: atm.editConf.pvcTable.ipV6.ra.dnsOptions.rdnss.importServers

       Possibilities:
               disabled   (0)
               enabled   (1)"
   ::= {er1645v2ATMCfgEntry 705039148}

er1645v2ATMCfgIpV6RaDnsOptionsDnsslLifeTime OBJECT-TYPE
   SYNTAX      TimeTicks
   MAX-ACCESS  read-write
   STATUS      current
   DESCRIPTION
      "Path: atm.editConf.pvcTable.ipV6.ra.dnsOptions.dnssl.lifeTime

       Time in centi-second."
   ::= {er1645v2ATMCfgEntry 705039172}

er1645v2ATMCfgIpV6RaDnsOptionsDnsslImportDomains OBJECT-TYPE
   SYNTAX      INTEGER
               {
               disabled (0),
               enabled (1)
               }
   MAX-ACCESS  read-write
   STATUS      current
   DESCRIPTION
      "Path: atm.editConf.pvcTable.ipV6.ra.dnsOptions.dnssl.importDomains

       Possibilities:
               disabled   (0)
               enabled   (1)"
   ::= {er1645v2ATMCfgEntry 705039180}

er1645v2ATMCfgIpV6RsSend OBJECT-TYPE
   SYNTAX      INTEGER
               {
               disabled (0),
               enabled (1)
               }
   MAX-ACCESS  read-write
   STATUS      current
   DESCRIPTION
      "Path: atm.editConf.pvcTable.ipV6.rs.send

       Possibilities:
               disabled   (0)
               enabled   (1)"
   ::= {er1645v2ATMCfgEntry 705954048}

er1645v2ATMCfgIpV6RsMaxRandomDelay OBJECT-TYPE
   SYNTAX      TimeTicks
   MAX-ACCESS  read-write
   STATUS      current
   DESCRIPTION
      "Path: atm.editConf.pvcTable.ipV6.rs.maxRandomDelay

       Time in centi-second."
   ::= {er1645v2ATMCfgEntry 705954304}

er1645v2ATMCfgIpV6RsInterval OBJECT-TYPE
   SYNTAX      TimeTicks
   MAX-ACCESS  read-write
   STATUS      current
   DESCRIPTION
      "Path: atm.editConf.pvcTable.ipV6.rs.interval

       Time in centi-second."
   ::= {er1645v2ATMCfgEntry 705954560}

er1645v2ATMCfgIpV6RsMaxSolicitations OBJECT-TYPE
   SYNTAX      Integer32
   MAX-ACCESS  read-write
   STATUS      current
   DESCRIPTION
      "Path: atm.editConf.pvcTable.ipV6.rs.maxSolicitations"
   ::= {er1645v2ATMCfgEntry 705954816}

er1645v2ATMCfgIpV6TrafficPolicyInbound OBJECT-TYPE
   SYNTAX      DisplayString
   MAX-ACCESS  read-write
   STATUS      current
   DESCRIPTION
      "Path: atm.editConf.pvcTable.ipV6.trafficPolicy.inbound"
   ::= {er1645v2ATMCfgEntry 705364224}

er1645v2ATMCfgIpV6TrafficPolicyOutbound OBJECT-TYPE
   SYNTAX      DisplayString
   MAX-ACCESS  read-write
   STATUS      current
   DESCRIPTION
      "Path: atm.editConf.pvcTable.ipV6.trafficPolicy.outbound"
   ::= {er1645v2ATMCfgEntry 705364480}

er1645v2ATMCfgIpV6FirewallZone OBJECT-TYPE
   SYNTAX      DisplayString
   MAX-ACCESS  read-write
   STATUS      current
   DESCRIPTION
      "Path: atm.editConf.pvcTable.ipV6.firewall.zone"
   ::= {er1645v2ATMCfgEntry 705429760}

er1645v2ATMCfgIpV6DhcpClientAddrAC OBJECT-TYPE
   SYNTAX      INTEGER
               {
               disabled (0),
               enabled (1)
               }
   MAX-ACCESS  read-write
   STATUS      current
   DESCRIPTION
      "Path: atm.editConf.pvcTable.ipV6.dhcp.client.addrAutoConfig

       Possibilities:
               disabled   (0)
               enabled   (1)"
   ::= {er1645v2ATMCfgEntry 705307648}

er1645v2ATMCfgIpV6DhcpClientPrDelMode OBJECT-TYPE
   SYNTAX      INTEGER
               {
               disabled (0),
               enabled (1)
               }
   MAX-ACCESS  read-write
   STATUS      current
   DESCRIPTION
      "Path: atm.editConf.pvcTable.ipV6.dhcp.client.pd.mode

       Possibilities:
               disabled   (0)
               enabled   (1)"
   ::= {er1645v2ATMCfgEntry 705308676}

er1645v2ATMCfgIpV6DhcpClientPrDelPool OBJECT-TYPE
   SYNTAX      DisplayString
   MAX-ACCESS  read-write
   STATUS      current
   DESCRIPTION
      "Path: atm.editConf.pvcTable.ipV6.dhcp.client.pd.pool"
   ::= {er1645v2ATMCfgEntry 705308680}

er1645v2ATMCfgIpV6DhcpClientPrDelPdExclOpt OBJECT-TYPE
   SYNTAX      INTEGER
               {
               disabled (0),
               enabled (1)
               }
   MAX-ACCESS  read-write
   STATUS      current
   DESCRIPTION
      "Path: atm.editConf.pvcTable.ipV6.dhcp.client.pd.pdExclOpt

       Possibilities:
               disabled   (0)
               enabled   (1)"
   ::= {er1645v2ATMCfgEntry 705308684}

er1645v2ATMCfgIpV6DhcpClientDnsServerPref OBJECT-TYPE
   SYNTAX      Integer32
   MAX-ACCESS  read-write
   STATUS      current
   DESCRIPTION
      "Path: atm.editConf.pvcTable.ipV6.dhcp.client.dns.serverPref"
   ::= {er1645v2ATMCfgEntry 705310724}

er1645v2ATMCfgIpV6DhcpClientRapidCommit OBJECT-TYPE
   SYNTAX      INTEGER
               {
               disabled (0),
               enabled (1)
               }
   MAX-ACCESS  read-write
   STATUS      current
   DESCRIPTION
      "Path: atm.editConf.pvcTable.ipV6.dhcp.client.rapidCommit

       Possibilities:
               disabled   (0)
               enabled   (1)"
   ::= {er1645v2ATMCfgEntry 705309696}

er1645v2ATMCfgIpV6DhcpClientTimersSolTimeOut OBJECT-TYPE
   SYNTAX      TimeTicks
   MAX-ACCESS  read-write
   STATUS      current
   DESCRIPTION
      "Path: atm.editConf.pvcTable.ipV6.dhcp.client.timers.solTimeOut

       Time in centi-second."
   ::= {er1645v2ATMCfgEntry 705311748}

er1645v2ATMCfgIpV6DhcpClientTimersSolMaxRt OBJECT-TYPE
   SYNTAX      TimeTicks
   MAX-ACCESS  read-write
   STATUS      current
   DESCRIPTION
      "Path: atm.editConf.pvcTable.ipV6.dhcp.client.timers.solMaxRt

       Time in centi-second."
   ::= {er1645v2ATMCfgEntry 705311752}

er1645v2ATMCfgIpV6DhcpClientTimersInfoRefresh OBJECT-TYPE
   SYNTAX      TimeTicks
   MAX-ACCESS  read-write
   STATUS      current
   DESCRIPTION
      "Path: atm.editConf.pvcTable.ipV6.dhcp.client.timers.infoRefresh

       Time in centi-second."
   ::= {er1645v2ATMCfgEntry 705311756}

er1645v2ATMCfgIpV6DhcpServerMode OBJECT-TYPE
   SYNTAX      INTEGER
               {
               disabled (0),
               enabled (1)
               }
   MAX-ACCESS  read-write
   STATUS      current
   DESCRIPTION
      "Path: atm.editConf.pvcTable.ipV6.dhcp.server.mode

       Possibilities:
               disabled   (0)
               enabled   (1)"
   ::= {er1645v2ATMCfgEntry 705315840}

er1645v2ATMCfgIpV6DhcpServerPreference OBJECT-TYPE
   SYNTAX      Integer32
   MAX-ACCESS  read-write
   STATUS      current
   DESCRIPTION
      "Path: atm.editConf.pvcTable.ipV6.dhcp.server.preference"
   ::= {er1645v2ATMCfgEntry 705316864}

er1645v2ATMCfgIpV6DhcpServerPool OBJECT-TYPE
   SYNTAX      DisplayString
   MAX-ACCESS  read-write
   STATUS      current
   DESCRIPTION
      "Path: atm.editConf.pvcTable.ipV6.dhcp.server.pool"
   ::= {er1645v2ATMCfgEntry 705317888}

er1645v2ATMCfgIpV6DhcpServerRapidCommit OBJECT-TYPE
   SYNTAX      INTEGER
               {
               disabled (0),
               enabled (1)
               }
   MAX-ACCESS  read-write
   STATUS      current
   DESCRIPTION
      "Path: atm.editConf.pvcTable.ipV6.dhcp.server.rapidCommit

       Possibilities:
               disabled   (0)
               enabled   (1)"
   ::= {er1645v2ATMCfgEntry 705318912}

er1645v2ATMCfgIpV6DhcpServerTimersInfoRefresh OBJECT-TYPE
   SYNTAX      TimeTicks
   MAX-ACCESS  read-write
   STATUS      current
   DESCRIPTION
      "Path: atm.editConf.pvcTable.ipV6.dhcp.server.timers.infoRefresh

       Time in centi-second."
   ::= {er1645v2ATMCfgEntry 705319940}

er1645v2ATMCfgIpV6DhcpRelayMode OBJECT-TYPE
   SYNTAX      INTEGER
               {
               disabled (0),
               enabled (1)
               }
   MAX-ACCESS  read-write
   STATUS      current
   DESCRIPTION
      "Path: atm.editConf.pvcTable.ipV6.dhcp.relay.mode

       Possibilities:
               disabled   (0)
               enabled   (1)"
   ::= {er1645v2ATMCfgEntry 705323040}

er1645v2ATMCfgIpV6SendRedirect OBJECT-TYPE
   SYNTAX      INTEGER
               {
               disabled (0),
               enabled (1)
               }
   MAX-ACCESS  read-write
   STATUS      current
   DESCRIPTION
      "Path: atm.editConf.pvcTable.ipV6.sendRedirect

       Possibilities:
               disabled   (0)
               enabled   (1)"
   ::= {er1645v2ATMCfgEntry 705101824}

er1645v2ATMCfgIpV6LinkMtu OBJECT-TYPE
   SYNTAX      Integer32
   MAX-ACCESS  read-write
   STATUS      current
   DESCRIPTION
      "Path: atm.editConf.pvcTable.ipV6.linkMtu"
   ::= {er1645v2ATMCfgEntry 705167360}

er1645v2ATMCfgIpV6InterfaceId OBJECT-TYPE
   SYNTAX      OCTET STRING
   MAX-ACCESS  read-write
   STATUS      current
   DESCRIPTION
      "Path: atm.editConf.pvcTable.ipV6.interfaceId"
   ::= {er1645v2ATMCfgEntry 705232896}

er1645v2ATMCfgIpV6MF OBJECT-TYPE
   SYNTAX      Integer32
   MAX-ACCESS  read-write
   STATUS      current
   DESCRIPTION
      "Path: atm.editConf.pvcTable.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2ATMCfgEntry 705757184}

er1645v2ATMCfgIpV6IcmpMessagesNoRoute OBJECT-TYPE
   SYNTAX      INTEGER
               {
               disabled (0),
               enabled (1)
               }
   MAX-ACCESS  read-write
   STATUS      current
   DESCRIPTION
      "Path: atm.editConf.pvcTable.ipV6.icmpMessages.noRoute

       Possibilities:
               disabled   (0)
               enabled   (1)"
   ::= {er1645v2ATMCfgEntry 705822976}

er1645v2ATMCfgIpV6IcmpMessagesBeyondScope OBJECT-TYPE
   SYNTAX      INTEGER
               {
               disabled (0),
               enabled (1)
               }
   MAX-ACCESS  read-write
   STATUS      current
   DESCRIPTION
      "Path: atm.editConf.pvcTable.ipV6.icmpMessages.beyondScope

       Possibilities:
               disabled   (0)
               enabled   (1)"
   ::= {er1645v2ATMCfgEntry 705823488}

er1645v2ATMCfgIpV6IcmpMessagesAddressUnreachable OBJECT-TYPE
   SYNTAX      INTEGER
               {
               disabled (0),
               enabled (1)
               }
   MAX-ACCESS  read-write
   STATUS      current
   DESCRIPTION
      "Path: atm.editConf.pvcTable.ipV6.icmpMessages.addressUnreachable

       Possibilities:
               disabled   (0)
               enabled   (1)"
   ::= {er1645v2ATMCfgEntry 705823744}

er1645v2ATMCfgIpV6IcmpMessagesPortUnreachable OBJECT-TYPE
   SYNTAX      INTEGER
               {
               disabled (0),
               enabled (1)
               }
   MAX-ACCESS  read-write
   STATUS      current
   DESCRIPTION
      "Path: atm.editConf.pvcTable.ipV6.icmpMessages.portUnreachable

       Possibilities:
               disabled   (0)
               enabled   (1)"
   ::= {er1645v2ATMCfgEntry 705824000}

er1645v2ATMCfgIpV6IcmpMessagesPacketTooBig OBJECT-TYPE
   SYNTAX      INTEGER
               {
               disabled (0),
               enabled (1)
               }
   MAX-ACCESS  read-write
   STATUS      current
   DESCRIPTION
      "Path: atm.editConf.pvcTable.ipV6.icmpMessages.packetTooBig

       Possibilities:
               disabled   (0)
               enabled   (1)"
   ::= {er1645v2ATMCfgEntry 705825280}

er1645v2ATMCfgIpV6IcmpMessagesHopLimitExceeded OBJECT-TYPE
   SYNTAX      INTEGER
               {
               disabled (0),
               enabled (1)
               }
   MAX-ACCESS  read-write
   STATUS      current
   DESCRIPTION
      "Path: atm.editConf.pvcTable.ipV6.icmpMessages.hopLimitExceeded

       Possibilities:
               disabled   (0)
               enabled   (1)"
   ::= {er1645v2ATMCfgEntry 705827840}

er1645v2ATMCfgIpV6IcmpMessagesFragTimeExceeded OBJECT-TYPE
   SYNTAX      INTEGER
               {
               disabled (0),
               enabled (1)
               }
   MAX-ACCESS  read-write
   STATUS      current
   DESCRIPTION
      "Path: atm.editConf.pvcTable.ipV6.icmpMessages.fragTimeExceeded

       Possibilities:
               disabled   (0)
               enabled   (1)"
   ::= {er1645v2ATMCfgEntry 705828096}

er1645v2ATMCfgIpV6IcmpMessagesHeaderFieldErr OBJECT-TYPE
   SYNTAX      INTEGER
               {
               disabled (0),
               enabled (1)
               }
   MAX-ACCESS  read-write
   STATUS      current
   DESCRIPTION
      "Path: atm.editConf.pvcTable.ipV6.icmpMessages.headerFieldErr

       Possibilities:
               disabled   (0)
               enabled   (1)"
   ::= {er1645v2ATMCfgEntry 705830400}

er1645v2ATMCfgIpV6IcmpMessagesOptionUnrecognized OBJECT-TYPE
   SYNTAX      INTEGER
               {
               disabled (0),
               enabled (1)
               }
   MAX-ACCESS  read-write
   STATUS      current
   DESCRIPTION
      "Path: atm.editConf.pvcTable.ipV6.icmpMessages.optionUnrecognized

       Possibilities:
               disabled   (0)
               enabled   (1)"
   ::= {er1645v2ATMCfgEntry 705830912}

er1645v2ATMCfgIpV6IcmpMessagesRedirect OBJECT-TYPE
   SYNTAX      INTEGER
               {
               disabled (0),
               enabled (1)
               }
   MAX-ACCESS  read-write
   STATUS      current
   DESCRIPTION
      "Path: atm.editConf.pvcTable.ipV6.icmpMessages.redirect

       Possibilities:
               disabled   (0)
               enabled   (1)"
   ::= {er1645v2ATMCfgEntry 705832960}

er1645v2ATMCfgBridgingAccList OBJECT-TYPE
   SYNTAX      DisplayString
   MAX-ACCESS  read-write
   STATUS      current
   DESCRIPTION
      "Path: atm.editConf.pvcTable.bridging.accessList"
   ::= {er1645v2ATMCfgEntry 453246976}

er1645v2ATMCfgBridgingInACL OBJECT-TYPE
   SYNTAX      DisplayString
   MAX-ACCESS  read-write
   STATUS      current
   DESCRIPTION
      "Path: atm.editConf.pvcTable.bridging.inAccessList"
   ::= {er1645v2ATMCfgEntry 456916992}

er1645v2ATMCfgBridgingTp OBJECT-TYPE
   SYNTAX      DisplayString
   MAX-ACCESS  read-write
   STATUS      current
   DESCRIPTION
      "Path: atm.editConf.pvcTable.bridging.trafficPolicy"
   ::= {er1645v2ATMCfgEntry 454295552}

er1645v2ATMCfgBridgingBrGrp OBJECT-TYPE
   SYNTAX      DisplayString
   MAX-ACCESS  read-write
   STATUS      current
   DESCRIPTION
      "Path: atm.editConf.pvcTable.bridging.bridgeGroup"
   ::= {er1645v2ATMCfgEntry 454819840}

er1645v2ATMCfgBridgingLimBC OBJECT-TYPE
   SYNTAX      INTEGER
               {
               disabled (0),
               enabled (1)
               }
   MAX-ACCESS  read-write
   STATUS      current
   DESCRIPTION
      "Path: atm.editConf.pvcTable.bridging.limitBroadcasts

       Possibilities:
               disabled   (0)
               enabled   (1)"
   ::= {er1645v2ATMCfgEntry 455081984}

er1645v2ATMCfgBridgingPrivateMode OBJECT-TYPE
   SYNTAX      INTEGER
               {
               disabled (0),
               enabled (1)
               }
   MAX-ACCESS  read-write
   STATUS      current
   DESCRIPTION
      "Path: atm.editConf.pvcTable.bridging.privateMode

       Possibilities:
               disabled   (0)
               enabled   (1)"
   ::= {er1645v2ATMCfgEntry 459538432}

er1645v2ATMCfgBridgingLearning OBJECT-TYPE
   SYNTAX      INTEGER
               {
               disabled (0),
               enabled (1)
               }
   MAX-ACCESS  read-write
   STATUS      current
   DESCRIPTION
      "Path: atm.editConf.pvcTable.bridging.learning

       Possibilities:
               disabled   (0)
               enabled   (1)"
   ::= {er1645v2ATMCfgEntry 456130560}

er1645v2ATMCfgBridgingMaxCacheSize OBJECT-TYPE
   SYNTAX      INTEGER
               {
               unlimited (0)
               }
   MAX-ACCESS  read-write
   STATUS      current
   DESCRIPTION
      "Path: atm.editConf.pvcTable.bridging.maxCacheSize

       Possibilities:
               unlimited   (0)"
   ::= {er1645v2ATMCfgEntry 456392704}

er1645v2ATMCfgBridgingRelearnDropOnRelearn OBJECT-TYPE
   SYNTAX      INTEGER
               {
               disabled (0),
               enabled (1)
               }
   MAX-ACCESS  read-write
   STATUS      current
   DESCRIPTION
      "Path: atm.editConf.pvcTable.bridging.relearn.dropOnRelearn

       Possibilities:
               disabled   (0)
               enabled   (1)"
   ::= {er1645v2ATMCfgEntry 456655872}

er1645v2ATMCfgBridgingRelearnShutdownThreshold OBJECT-TYPE
   SYNTAX      Integer32
   MAX-ACCESS  read-write
   STATUS      current
   DESCRIPTION
      "Path: atm.editConf.pvcTable.bridging.relearn.shutdownThreshold"
   ::= {er1645v2ATMCfgEntry 456656896}

er1645v2ATMCfgBridgingRelearnShutdownTime OBJECT-TYPE
   SYNTAX      TimeTicks
   MAX-ACCESS  read-write
   STATUS      current
   DESCRIPTION
      "Path: atm.editConf.pvcTable.bridging.relearn.shutdownTime

       Time in centi-second."
   ::= {er1645v2ATMCfgEntry 456657920}

er1645v2ATMCfgBridgingRelearnLoopDetection OBJECT-TYPE
   SYNTAX      INTEGER
               {
               disabled (0),
               passive (1),
               active (2)
               }
   MAX-ACCESS  read-write
   STATUS      current
   DESCRIPTION
      "Path: atm.editConf.pvcTable.bridging.relearn.loopDetection

       Possibilities:
               disabled   (0)
               passive   (1)
               active   (2)"
   ::= {er1645v2ATMCfgEntry 456658944}

er1645v2ATMCfgBridgingRelearnLoopDetectionInterval OBJECT-TYPE
   SYNTAX      TimeTicks
   MAX-ACCESS  read-write
   STATUS      current
   DESCRIPTION
      "Path: atm.editConf.pvcTable.bridging.relearn.loopDetectionInterval

       Time in centi-second."
   ::= {er1645v2ATMCfgEntry 456659968}

er1645v2ATMCfgBridgingVlanMemberShip OBJECT-TYPE
   SYNTAX      INTEGER
               {
               all (0),
               none (1),
               grouped (2)
               }
   MAX-ACCESS  read-write
   STATUS      current
   DESCRIPTION
      "Path: atm.editConf.pvcTable.bridging.vlanMemberShip

       Possibilities:
               all   (0)
               none   (1)
               grouped   (2)"
   ::= {er1645v2ATMCfgEntry 457965568}

er1645v2ATMCfgBridgingVlTUntaggedAction OBJECT-TYPE
   SYNTAX      INTEGER
               {
               discard (0),
               accept (1),
               tag (2)
               }
   MAX-ACCESS  read-write
   STATUS      current
   DESCRIPTION
      "Path: atm.editConf.pvcTable.bridging.vlanTagging.untagged.action

       Possibilities:
               discard   (0)
               accept   (1)
               tag   (2)"
   ::= {er1645v2ATMCfgEntry 459055104}

er1645v2ATMCfgBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.untagged.tagInfo.tpid

       Possibilities:
               dot1Q   (33024)
               dot1ad   (34984)
               0x9100   (37120)
               0x9200   (37376)
               0x9300   (37632)"
   ::= {er1645v2ATMCfgEntry 459059712}

er1645v2ATMCfgBridgingVlTUntaggedTagInfoVid OBJECT-TYPE
   SYNTAX      Integer32
   MAX-ACCESS  read-write
   STATUS      current
   DESCRIPTION
      "Path: atm.editConf.pvcTable.bridging.vlanTagging.untagged.tagInfo.vid"
   ::= {er1645v2ATMCfgEntry 459060224}

er1645v2ATMCfgBridgingVlTUnknownVlansAction OBJECT-TYPE
   SYNTAX      INTEGER
               {
               discard (0),
               accept (1),
               tag (2)
               }
   MAX-ACCESS  read-write
   STATUS      current
   DESCRIPTION
      "Path: atm.editConf.pvcTable.bridging.vlanTagging.unknownVlans.action

       Possibilities:
               discard   (0)
               accept   (1)
               tag   (2)"
   ::= {er1645v2ATMCfgEntry 459120640}

er1645v2ATMCfgBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.unknownVlans.tagInfo.tpid

       Possibilities:
               dot1Q   (33024)
               dot1ad   (34984)
               0x9100   (37120)
               0x9200   (37376)
               0x9300   (37632)"
   ::= {er1645v2ATMCfgEntry 459125248}

er1645v2ATMCfgBridgingVlTUnknownVlansTagInfoVid OBJECT-TYPE
   SYNTAX      Integer32
   MAX-ACCESS  read-write
   STATUS      current
   DESCRIPTION
      "Path: atm.editConf.pvcTable.bridging.vlanTagging.unknownVlans.tagInfo.vid"
   ::= {er1645v2ATMCfgEntry 459125760}

er1645v2ATMCfgBridgingDot1adType OBJECT-TYPE
   SYNTAX      INTEGER
               {
               slOPTg (0),
               cPort (4),
               sPort (1),
               nni (2)
               }
   MAX-ACCESS  read-write
   STATUS      current
   DESCRIPTION
      "Path: atm.editConf.pvcTable.bridging.dot1ad.type

       Possibilities:
               <OPT>   (0)
               cPort   (4)
               sPort   (1)
               nni   (2)"
   ::= {er1645v2ATMCfgEntry 460850176}

er1645v2ATMCfgBridgingPriority OBJECT-TYPE
   SYNTAX      Integer32
   MAX-ACCESS  read-write
   STATUS      current
   DESCRIPTION
      "Path: atm.editConf.pvcTable.bridging.priority"
   ::= {er1645v2ATMCfgEntry 453509120}

er1645v2ATMCfgBridgingPathCost OBJECT-TYPE
   SYNTAX      Integer32
   MAX-ACCESS  read-write
   STATUS      current
   DESCRIPTION
      "Path: atm.editConf.pvcTable.bridging.pathCost"
   ::= {er1645v2ATMCfgEntry 453771264}

er1645v2ATMCfgBridgingInternalPathCost OBJECT-TYPE
   SYNTAX      Integer32
   MAX-ACCESS  read-write
   STATUS      current
   DESCRIPTION
      "Path: atm.editConf.pvcTable.bridging.internalPathCost"
   ::= {er1645v2ATMCfgEntry 457703424}

er1645v2ATMCfgBridgingTCD OBJECT-TYPE
   SYNTAX      INTEGER
               {
               disabled (0),
               enabled (1)
               }
   MAX-ACCESS  read-write
   STATUS      current
   DESCRIPTION
      "Path: atm.editConf.pvcTable.bridging.topologyChangeDetection

       Possibilities:
               disabled   (0)
               enabled   (1)"
   ::= {er1645v2ATMCfgEntry 454033408}

er1645v2ATMCfgBridgingRestrictedRole OBJECT-TYPE
   SYNTAX      INTEGER
               {
               disabled (0),
               enabled (1)
               }
   MAX-ACCESS  read-write
   STATUS      current
   DESCRIPTION
      "Path: atm.editConf.pvcTable.bridging.restrictedRole

       Possibilities:
               disabled   (0)
               enabled   (1)"
   ::= {er1645v2ATMCfgEntry 458227712}

er1645v2ATMCfgBridgingAdminEdge OBJECT-TYPE
   SYNTAX      INTEGER
               {
               disabled (0),
               enabled (1)
               }
   MAX-ACCESS  read-write
   STATUS      current
   DESCRIPTION
      "Path: atm.editConf.pvcTable.bridging.adminEdge

       Possibilities:
               disabled   (0)
               enabled   (1)"
   ::= {er1645v2ATMCfgEntry 457179136}

er1645v2ATMCfgBridgingOamMacDeviceMac OBJECT-TYPE
   SYNTAX      DisplayString
   MAX-ACCESS  read-write
   STATUS      current
   DESCRIPTION
      "Path: atm.editConf.pvcTable.bridging.ethOam.macAddress.deviceMac"
   ::= {er1645v2ATMCfgEntry 458506496}

er1645v2ATMCfgBridgingOamMacUserMac OBJECT-TYPE
   SYNTAX      OCTET STRING
   MAX-ACCESS  read-write
   STATUS      current
   DESCRIPTION
      "Path: atm.editConf.pvcTable.bridging.ethOam.macAddress.userMac

       MAC address."
   ::= {er1645v2ATMCfgEntry 458506368}

er1645v2ATMCfgBridgingOamMacBridgeMac OBJECT-TYPE
   SYNTAX      DisplayString
   MAX-ACCESS  read-write
   STATUS      current
   DESCRIPTION
      "Path: atm.editConf.pvcTable.bridging.ethOam.macAddress.bridgeMac"
   ::= {er1645v2ATMCfgEntry 458506432}

er1645v2ATMCfgBridgingMgmtInline OBJECT-TYPE
   SYNTAX      INTEGER
               {
               disabled (0),
               enabled (1)
               }
   MAX-ACCESS  read-write
   STATUS      current
   DESCRIPTION
      "Path: atm.editConf.pvcTable.bridging.mgmtInline

       Possibilities:
               disabled   (0)
               enabled   (1)"
   ::= {er1645v2ATMCfgEntry 458752000}

er1645v2ATMCfgBridgingL2ptMode OBJECT-TYPE
   SYNTAX      INTEGER
               {
               disabled (0),
               enabled (1)
               }
   MAX-ACCESS  read-write
   STATUS      current
   DESCRIPTION
      "Path: atm.editConf.pvcTable.bridging.l2ProtTunnel.mode

       Possibilities:
               disabled   (0)
               enabled   (1)"
   ::= {er1645v2ATMCfgEntry 459292672}

er1645v2ATMCfgBridgingL2ptProtocols OBJECT-TYPE
   SYNTAX      Integer32
   MAX-ACCESS  read-write
   STATUS      current
   DESCRIPTION
      "Path: atm.editConf.pvcTable.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2ATMCfgEntry 459309056}

er1645v2ATMCfgBridgingL2ptDestMac OBJECT-TYPE
   SYNTAX      OCTET STRING
   MAX-ACCESS  read-write
   STATUS      current
   DESCRIPTION
      "Path: atm.editConf.pvcTable.bridging.l2ProtTunnel.destinationMac

       MAC address."
   ::= {er1645v2ATMCfgEntry 459325440}

er1645v2ATMCfgBridgingL2ptCos OBJECT-TYPE
   SYNTAX      INTEGER
               {
               unchanged (255)
               }
   MAX-ACCESS  read-write
   STATUS      current
   DESCRIPTION
      "Path: atm.editConf.pvcTable.bridging.l2ProtTunnel.cos

       Possibilities:
               unchanged   (255)"
   ::= {er1645v2ATMCfgEntry 459341824}

er1645v2ATMCfgBridgingL2ptDropThrStp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.stp

       unit name = packets/sec

       Possibilities:
               unlimited   (0)"
   ::= {er1645v2ATMCfgEntry 459358272}

er1645v2ATMCfgBridgingL2ptDropThrLldp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.lldp

       unit name = packets/sec

       Possibilities:
               unlimited   (0)"
   ::= {er1645v2ATMCfgEntry 459358336}

er1645v2ATMCfgBridgingL2ptDropThrOam OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.oam

       unit name = packets/sec

       Possibilities:
               unlimited   (0)"
   ::= {er1645v2ATMCfgEntry 459358400}

er1645v2ATMCfgBridgingL2ptDropThrCdp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.cdp

       unit name = packets/sec

       Possibilities:
               unlimited   (0)"
   ::= {er1645v2ATMCfgEntry 459358464}

er1645v2ATMCfgBridgingL2ptDropThrVtp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.vtp

       unit name = packets/sec

       Possibilities:
               unlimited   (0)"
   ::= {er1645v2ATMCfgEntry 459358528}

er1645v2ATMCfgBridgingL2ptDropThrLacp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.lacp

       unit name = packets/sec

       Possibilities:
               unlimited   (0)"
   ::= {er1645v2ATMCfgEntry 459358592}

er1645v2ATMCfgBridgingL2ptDropThrEfmOam OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.efmOam

       unit name = packets/sec

       Possibilities:
               unlimited   (0)"
   ::= {er1645v2ATMCfgEntry 459358656}

er1645v2ATMCfgBridgingL2ptDropThrPvst OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.pvst

       unit name = packets/sec

       Possibilities:
               unlimited   (0)"
   ::= {er1645v2ATMCfgEntry 459358720}

er1645v2ATMCfgBridgingL2ptDropThrMmrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.mmrp

       unit name = packets/sec

       Possibilities:
               unlimited   (0)"
   ::= {er1645v2ATMCfgEntry 459358784}

er1645v2ATMCfgBridgingL2ptDropThrMvrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.mvrp

       unit name = packets/sec

       Possibilities:
               unlimited   (0)"
   ::= {er1645v2ATMCfgEntry 459358848}

er1645v2ATMCfgBridgingL2ptDropThrGvrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.gvrp

       unit name = packets/sec

       Possibilities:
               unlimited   (0)"
   ::= {er1645v2ATMCfgEntry 459358912}

er1645v2ATMCfgBridgingL2ptDropThrGmrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.gmrp

       unit name = packets/sec

       Possibilities:
               unlimited   (0)"
   ::= {er1645v2ATMCfgEntry 459358976}

er1645v2ATMCfgBridgingL2ptDropThrDtp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.dtp

       unit name = packets/sec

       Possibilities:
               unlimited   (0)"
   ::= {er1645v2ATMCfgEntry 459359040}

er1645v2ATMCfgBridgingL2ptDropThrPagp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.pagp

       unit name = packets/sec

       Possibilities:
               unlimited   (0)"
   ::= {er1645v2ATMCfgEntry 459359104}

er1645v2ATMCfgBridgingL2ptDropThrUdld OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.udld

       unit name = packets/sec

       Possibilities:
               unlimited   (0)"
   ::= {er1645v2ATMCfgEntry 459359168}

er1645v2ATMCfgVirtEthernetVirtualEthernet OBJECT-TYPE
   SYNTAX      DisplayString
   MAX-ACCESS  read-write
   STATUS      current
   DESCRIPTION
      "Path: atm.editConf.pvcTable.virtEthernet.virtualEthernet"
   ::= {er1645v2ATMCfgEntry 151060480}

er1645v2ATMCfgAtmVpi OBJECT-TYPE
   SYNTAX      Integer32
   MAX-ACCESS  read-write
   STATUS      current
   DESCRIPTION
      "Path: atm.editConf.pvcTable.atm.vpi"
   ::= {er1645v2ATMCfgEntry 285278208}

er1645v2ATMCfgAtmVci OBJECT-TYPE
   SYNTAX      Integer32
   MAX-ACCESS  read-write
   STATUS      current
   DESCRIPTION
      "Path: atm.editConf.pvcTable.atm.vci"
   ::= {er1645v2ATMCfgEntry 285343744}

er1645v2ATMCfgAtmHighLayProt OBJECT-TYPE
   SYNTAX      INTEGER
               {
               rfc2684 (7),
               ppp (2),
               pppOverEthernet (11)
               }
   MAX-ACCESS  read-write
   STATUS      current
   DESCRIPTION
      "Path: atm.editConf.pvcTable.atm.higherLayerProtocol

       Possibilities:
               rfc2684   (7)
               ppp   (2)
               pppOverEthernet   (11)"
   ::= {er1645v2ATMCfgEntry 285409280}

er1645v2ATMCfgAtmMultiProt OBJECT-TYPE
   SYNTAX      INTEGER
               {
               llcEncapsulation (0),
               vcMultiplexing (1)
               }
   MAX-ACCESS  read-write
   STATUS      current
   DESCRIPTION
      "Path: atm.editConf.pvcTable.atm.multiProtocolMech

       Possibilities:
               llcEncapsulation   (0)
               vcMultiplexing   (1)"
   ::= {er1645v2ATMCfgEntry 285474816}

er1645v2ATMCfgAtmServCat OBJECT-TYPE
   SYNTAX      INTEGER
               {
               cbr (1),
               vbrmrt (2),
               vbrmnrt (3),
               ubr (4)
               }
   MAX-ACCESS  read-write
   STATUS      current
   DESCRIPTION
      "Path: atm.editConf.pvcTable.atm.serviceCategory

       Possibilities:
               cbr   (1)
               vbr-rt   (2)
               vbr-nrt   (3)
               ubr   (4)"
   ::= {er1645v2ATMCfgEntry 285999104}

er1645v2ATMCfgAtmPeakCellRate OBJECT-TYPE
   SYNTAX      INTEGER
               {
               auto (0)
               }
   UNITS       "bps"
   MAX-ACCESS  read-write
   STATUS      current
   DESCRIPTION
      "Path: atm.editConf.pvcTable.atm.peakCellRate

       unit name = bps

       Possibilities:
               auto   (0)"
   ::= {er1645v2ATMCfgEntry 285540352}

er1645v2ATMCfgAtmSustCellRate OBJECT-TYPE
   SYNTAX      INTEGER
               {
               auto (0)
               }
   UNITS       "bps"
   MAX-ACCESS  read-write
   STATUS      current
   DESCRIPTION
      "Path: atm.editConf.pvcTable.atm.sustCellRate

       unit name = bps

       Possibilities:
               auto   (0)"
   ::= {er1645v2ATMCfgEntry 285868032}

er1645v2ATMCfgAtmMaxBurstSize OBJECT-TYPE
   SYNTAX      Integer32
   UNITS       "cellTimes"
   MAX-ACCESS  read-write
   STATUS      current
   DESCRIPTION
      "Path: atm.editConf.pvcTable.atm.maxBurstSize

       unit name = cellTimes"
   ::= {er1645v2ATMCfgEntry 285933568}

er1645v2ATMCfgAtmInArpTimeOut OBJECT-TYPE
   SYNTAX      TimeTicks
   MAX-ACCESS  read-write
   STATUS      current
   DESCRIPTION
      "Path: atm.editConf.pvcTable.atm.inArpTimeOut

       Time in centi-second."
   ::= {er1645v2ATMCfgEntry 285605888}

er1645v2ATMCfgAtmF5LbOper OBJECT-TYPE
   SYNTAX      INTEGER
               {
               disabled (0),
               enabled (1)
               }
   MAX-ACCESS  read-write
   STATUS      current
   DESCRIPTION
      "Path: atm.editConf.pvcTable.atm.oamF5Loopback.operation

       Possibilities:
               disabled   (0)
               enabled   (1)"
   ::= {er1645v2ATMCfgEntry 285671680}

er1645v2ATMCfgAtmF5LbInterval OBJECT-TYPE
   SYNTAX      TimeTicks
   MAX-ACCESS  read-write
   STATUS      current
   DESCRIPTION
      "Path: atm.editConf.pvcTable.atm.oamF5Loopback.interval

       Time in centi-second."
   ::= {er1645v2ATMCfgEntry 285671936}

er1645v2ATMCfgAtmF5LbFailsPerm OBJECT-TYPE
   SYNTAX      Integer32
   MAX-ACCESS  read-write
   STATUS      current
   DESCRIPTION
      "Path: atm.editConf.pvcTable.atm.oamF5Loopback.failsPermitted"
   ::= {er1645v2ATMCfgEntry 285672448}

er1645v2ATMCfgAtmF5LbTar OBJECT-TYPE
   SYNTAX      INTEGER
               {
               endToEnd (0),
               segment (1),
               both (2)
               }
   MAX-ACCESS  read-write
   STATUS      current
   DESCRIPTION
      "Path: atm.editConf.pvcTable.atm.oamF5Loopback.target

       Possibilities:
               endToEnd   (0)
               segment   (1)
               both   (2)"
   ::= {er1645v2ATMCfgEntry 285672704}

er1645v2ATMCfgAtmF5ccDir OBJECT-TYPE
   SYNTAX      INTEGER
               {
               sink (1),
               source (2),
               both (3)
               }
   MAX-ACCESS  read-write
   STATUS      current
   DESCRIPTION
      "Path: atm.editConf.pvcTable.atm.oamF5CC.direction

       Possibilities:
               sink   (1)
               source   (2)
               both   (3)"
   ::= {er1645v2ATMCfgEntry 285737216}

er1645v2ATMCfgAtmF5ccTar OBJECT-TYPE
   SYNTAX      INTEGER
               {
               endToEnd (0),
               segment (1),
               both (2)
               }
   MAX-ACCESS  read-write
   STATUS      current
   DESCRIPTION
      "Path: atm.editConf.pvcTable.atm.oamF5CC.target

       Possibilities:
               endToEnd   (0)
               segment   (1)
               both   (2)"
   ::= {er1645v2ATMCfgEntry 285737472}

er1645v2ATMCfgAtmF5ccTxMode OBJECT-TYPE
   SYNTAX      INTEGER
               {
               continuously (0),
               onIdle (1)
               }
   MAX-ACCESS  read-write
   STATUS      current
   DESCRIPTION
      "Path: atm.editConf.pvcTable.atm.oamF5CC.tx.mode

       Possibilities:
               continuously   (0)
               onIdle   (1)"
   ::= {er1645v2ATMCfgEntry 285737729}

er1645v2ATMCfgAtmF5ccTxTxPer OBJECT-TYPE
   SYNTAX      TimeTicks
   MAX-ACCESS  read-write
   STATUS      current
   DESCRIPTION
      "Path: atm.editConf.pvcTable.atm.oamF5CC.tx.interval

       Time in centi-second."
   ::= {er1645v2ATMCfgEntry 285737730}

er1645v2ATMCfgAtmF5ccRxRcvTim OBJECT-TYPE
   SYNTAX      TimeTicks
   MAX-ACCESS  read-write
   STATUS      current
   DESCRIPTION
      "Path: atm.editConf.pvcTable.atm.oamF5CC.rx.timeOut

       Time in centi-second."
   ::= {er1645v2ATMCfgEntry 285738497}

er1645v2ATMCfgAtmF5ccActProc OBJECT-TYPE
   SYNTAX      INTEGER
               {
               passive (0),
               activated (1),
               deactivated (2),
               initActivation (3)
               }
   MAX-ACCESS  read-write
   STATUS      current
   DESCRIPTION
      "Path: atm.editConf.pvcTable.atm.oamF5CC.actDeact.initProcedure

       Possibilities:
               passive   (0)
               activated   (1)
               deactivated   (2)
               initActivation   (3)"
   ::= {er1645v2ATMCfgEntry 285737985}

er1645v2ATMCfgAtmF5ccActTim OBJECT-TYPE
   SYNTAX      TimeTicks
   MAX-ACCESS  read-write
   STATUS      current
   DESCRIPTION
      "Path: atm.editConf.pvcTable.atm.oamF5CC.actDeact.retryInterval

       Time in centi-second."
   ::= {er1645v2ATMCfgEntry 285737986}

er1645v2ATMCfgAtmF5ccActCnt OBJECT-TYPE
   SYNTAX      Integer32
   MAX-ACCESS  read-write
   STATUS      current
   DESCRIPTION
      "Path: atm.editConf.pvcTable.atm.oamF5CC.actDeact.retryCount"
   ::= {er1645v2ATMCfgEntry 285737987}

er1645v2ATMCfgAtmCpt OBJECT-TYPE
   SYNTAX      INTEGER
               {
               no (0),
               yes (1)
               }
   MAX-ACCESS  read-write
   STATUS      current
   DESCRIPTION
      "Path: atm.editConf.pvcTable.atm.segmentEndPoint

       Possibilities:
               no   (0)
               yes   (1)"
   ::= {er1645v2ATMCfgEntry 286195712}

er1645v2ATMCfgPppLnkMOperation OBJECT-TYPE
   SYNTAX      INTEGER
               {
               disabled (0),
               enabled (1)
               }
   MAX-ACCESS  read-write
   STATUS      current
   DESCRIPTION
      "Path: atm.editConf.pvcTable.ppp.linkMonitoring.operation

       Possibilities:
               disabled   (0)
               enabled   (1)"
   ::= {er1645v2ATMCfgEntry 201392384}

er1645v2ATMCfgPppLnkMInterval OBJECT-TYPE
   SYNTAX      TimeTicks
   MAX-ACCESS  read-write
   STATUS      current
   DESCRIPTION
      "Path: atm.editConf.pvcTable.ppp.linkMonitoring.interval

       Time in centi-second."
   ::= {er1645v2ATMCfgEntry 201392640}

er1645v2ATMCfgPppLnkMRepTimeOut OBJECT-TYPE
   SYNTAX      TimeTicks
   MAX-ACCESS  read-write
   STATUS      current
   DESCRIPTION
      "Path: atm.editConf.pvcTable.ppp.linkMonitoring.replyTimeOut

       Time in centi-second."
   ::= {er1645v2ATMCfgEntry 201392896}

er1645v2ATMCfgPppLnkMFailsPrmt OBJECT-TYPE
   SYNTAX      Integer32
   MAX-ACCESS  read-write
   STATUS      current
   DESCRIPTION
      "Path: atm.editConf.pvcTable.ppp.linkMonitoring.failsPermitted"
   ::= {er1645v2ATMCfgEntry 201393152}

er1645v2ATMCfgPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: atm.editConf.pvcTable.ppp.authentication

       Possibilities:
               disabled   (0)
               chap   (1)
               pap   (2)
               chapOrPap   (3)
               msChap   (4)
               msChapV2   (5)"
   ::= {er1645v2ATMCfgEntry 201457664}

er1645v2ATMCfgPppAuthenPeriod OBJECT-TYPE
   SYNTAX      TimeTicks
   MAX-ACCESS  read-write
   STATUS      current
   DESCRIPTION
      "Path: atm.editConf.pvcTable.ppp.authenPeriod

       Time in centi-second."
   ::= {er1645v2ATMCfgEntry 201523200}

er1645v2ATMCfgPppCompression OBJECT-TYPE
   SYNTAX      INTEGER
               {
               disabled (0),
               predictor1 (1)
               }
   MAX-ACCESS  read-write
   STATUS      current
   DESCRIPTION
      "Path: atm.editConf.pvcTable.ppp.compression

       Possibilities:
               disabled   (0)
               predictor1   (1)"
   ::= {er1645v2ATMCfgEntry 201588736}

er1645v2ATMCfgPppSessionName OBJECT-TYPE
   SYNTAX      DisplayString
   MAX-ACCESS  read-write
   STATUS      current
   DESCRIPTION
      "Path: atm.editConf.pvcTable.ppp.sessionName"
   ::= {er1645v2ATMCfgEntry 201654272}

er1645v2ATMCfgPppSessionSecret OBJECT-TYPE
   SYNTAX      DisplayString
   MAX-ACCESS  read-write
   STATUS      current
   DESCRIPTION
      "Path: atm.editConf.pvcTable.ppp.sessionSecret"
   ::= {er1645v2ATMCfgEntry 201719808}

er1645v2ATMCfgPppEncModeSessionSecret OBJECT-TYPE
   SYNTAX      INTEGER
               {
               none (1),
               encrypt (2),
               encType1 (3),
               invalid (128)
               }
   MAX-ACCESS  read-write
   STATUS      current
   DESCRIPTION
      "Path: atm.editConf.pvcTable.ppp.encModeSessionSecret

       Possibilities:
               none   (1)
               encrypt   (2)
               encType1   (3)
               invalid   (128)"
   ::= {er1645v2ATMCfgEntry 201850880}

er1645v2ATMCfgPppEncSessionSecret OBJECT-TYPE
   SYNTAX      DisplayString
   MAX-ACCESS  read-write
   STATUS      current
   DESCRIPTION
      "Path: atm.editConf.pvcTable.ppp.encSessionSecret"
   ::= {er1645v2ATMCfgEntry 201916416}

er1645v2ATMCfgPppServiceName OBJECT-TYPE
   SYNTAX      DisplayString
   MAX-ACCESS  read-write
   STATUS      current
   DESCRIPTION
      "Path: atm.editConf.pvcTable.ppp.serviceName"
   ::= {er1645v2ATMCfgEntry 201785344}

er1645v2ATMCfgInbBwCir OBJECT-TYPE
   SYNTAX      Integer32
   MAX-ACCESS  read-write
   STATUS      current
   DESCRIPTION
      "Path: atm.editConf.pvcTable.inboundBandwidth.cir"
   ::= {er1645v2ATMCfgEntry 117506048}

er1645v2ATMCfgInbBwTc OBJECT-TYPE
   SYNTAX      INTEGER
               {
               auto (0)
               }
   MAX-ACCESS  read-write
   STATUS      current
   DESCRIPTION
      "Path: atm.editConf.pvcTable.inboundBandwidth.tc

       Possibilities:
               auto   (0)"
   ::= {er1645v2ATMCfgEntry 117833728}

er1645v2ATMCfgInbBwCorrType OBJECT-TYPE
   SYNTAX      INTEGER
               {
               noCorrection (0),
               predefined (1),
               manual (2)
               }
   MAX-ACCESS  read-write
   STATUS      current
   DESCRIPTION
      "Path: atm.editConf.pvcTable.inboundBandwidth.correction.type

       Possibilities:
               noCorrection   (0)
               predefined   (1)
               manual   (2)"
   ::= {er1645v2ATMCfgEntry 117579776}

er1645v2ATMCfgInbBwCorrPredefEncapsFrameRelay OBJECT-TYPE
   SYNTAX      DisplayString
   MAX-ACCESS  read-write
   STATUS      current
   DESCRIPTION
      "Path: atm.editConf.pvcTable.inboundBandwidth.correction.predefined.encapsulation.frameRelay"
   ::= {er1645v2ATMCfgEntry 117589056}

er1645v2ATMCfgInbBwCorrPredefEncapsPpp OBJECT-TYPE
   SYNTAX      DisplayString
   MAX-ACCESS  read-write
   STATUS      current
   DESCRIPTION
      "Path: atm.editConf.pvcTable.inboundBandwidth.correction.predefined.encapsulation.ppp"
   ::= {er1645v2ATMCfgEntry 117589120}

er1645v2ATMCfgInbBwCorrPredefEncapsAtmHl OBJECT-TYPE
   SYNTAX      INTEGER
               {
               rfc2684 (0),
               ppp (1),
               pppOverEthernet (2)
               }
   MAX-ACCESS  read-write
   STATUS      current
   DESCRIPTION
      "Path: atm.editConf.pvcTable.inboundBandwidth.correction.predefined.encapsulation.atm.higherLayer

       Possibilities:
               rfc2684   (0)
               ppp   (1)
               pppOverEthernet   (2)"
   ::= {er1645v2ATMCfgEntry 117589192}

er1645v2ATMCfgInbBwCorrPredefEncapsAtmMp OBJECT-TYPE
   SYNTAX      INTEGER
               {
               llcEncapsulation (0),
               vcMultiplexing (1)
               }
   MAX-ACCESS  read-write
   STATUS      current
   DESCRIPTION
      "Path: atm.editConf.pvcTable.inboundBandwidth.correction.predefined.encapsulation.atm.multiProtocol

       Possibilities:
               llcEncapsulation   (0)
               vcMultiplexing   (1)"
   ::= {er1645v2ATMCfgEntry 117589200}

er1645v2ATMCfgInbBwCorrPredefEncapsHdlc OBJECT-TYPE
   SYNTAX      DisplayString
   MAX-ACCESS  read-write
   STATUS      current
   DESCRIPTION
      "Path: atm.editConf.pvcTable.inboundBandwidth.correction.predefined.encapsulation.hdlc"
   ::= {er1645v2ATMCfgEntry 117589248}

er1645v2ATMCfgInbBwCorrPredefEncapsEfmFs OBJECT-TYPE
   SYNTAX      Integer32
   MAX-ACCESS  read-write
   STATUS      current
   DESCRIPTION
      "Path: atm.editConf.pvcTable.inboundBandwidth.correction.predefined.encapsulation.efm.fragmentSize"
   ::= {er1645v2ATMCfgEntry 117589320}

er1645v2ATMCfgInbBwCorrPredefEncapsEfmIb OBJECT-TYPE
   SYNTAX      Integer32
   MAX-ACCESS  read-write
   STATUS      current
   DESCRIPTION
      "Path: atm.editConf.pvcTable.inboundBandwidth.correction.predefined.encapsulation.efm.idleBytes"
   ::= {er1645v2ATMCfgEntry 117589328}

er1645v2ATMCfgInbBwCorrPredefMode OBJECT-TYPE
   SYNTAX      INTEGER
               {
               routing (0),
               bridging (1)
               }
   MAX-ACCESS  read-write
   STATUS      current
   DESCRIPTION
      "Path: atm.editConf.pvcTable.inboundBandwidth.correction.predefined.mode

       Possibilities:
               routing   (0)
               bridging   (1)"
   ::= {er1645v2ATMCfgEntry 117590016}

er1645v2ATMCfgInbBwCorrManualOverhead OBJECT-TYPE
   SYNTAX      Integer32
   MAX-ACCESS  read-write
   STATUS      current
   DESCRIPTION
      "Path: atm.editConf.pvcTable.inboundBandwidth.correction.manual.overhead"
   ::= {er1645v2ATMCfgEntry 117596192}

er1645v2ATMCfgInbBwCorrManualFrameData OBJECT-TYPE
   SYNTAX      Counter32
   MAX-ACCESS  read-write
   STATUS      current
   DESCRIPTION
      "Path: atm.editConf.pvcTable.inboundBandwidth.correction.manual.frameData

       32 bit unsigned wrappable counter."
   ::= {er1645v2ATMCfgEntry 117596224}

er1645v2ATMCfgInbBwCorrManualFrameHeader OBJECT-TYPE
   SYNTAX      Counter32
   MAX-ACCESS  read-write
   STATUS      current
   DESCRIPTION
      "Path: atm.editConf.pvcTable.inboundBandwidth.correction.manual.frameHeader

       32 bit unsigned wrappable counter."
   ::= {er1645v2ATMCfgEntry 117596256}

er1645v2ATMCfgInbBwMaxFifoQLen OBJECT-TYPE
   SYNTAX      Integer32
   MAX-ACCESS  read-write
   STATUS      current
   DESCRIPTION
      "Path: atm.editConf.pvcTable.inboundBandwidth.maxFifoQLen"
   ::= {er1645v2ATMCfgEntry 117637120}

er1645v2ATMCfgInbBwPriorityPolicy OBJECT-TYPE
   SYNTAX      DisplayString
   MAX-ACCESS  read-write
   STATUS      current
   DESCRIPTION
      "Path: atm.editConf.pvcTable.inboundBandwidth.priorityPolicy"
   ::= {er1645v2ATMCfgEntry 117702656}

er1645v2ATMCfgIpH OBJECT-TYPE
   SYNTAX      SEQUENCE OF Er1645v2ATMCfgIpHEntry
   MAX-ACCESS  not-accessible
   STATUS      current
   DESCRIPTION
      ""
   ::= {er1645v2ATMCfg 51314688}

er1645v2ATMCfgIpHEntry OBJECT-TYPE
   SYNTAX      Er1645v2ATMCfgIpHEntry
   MAX-ACCESS  not-accessible
   STATUS      current
   DESCRIPTION
      ""
   INDEX      { er1645v2ATMCfgTableIx,
                er1645v2ATMCfgIpHTableIx }
   ::= {er1645v2ATMCfgIpH 1}

Er1645v2ATMCfgIpHEntry ::=
   SEQUENCE
      {
      er1645v2ATMCfgIpHActions
         VariableLengthTableActions,
      er1645v2ATMCfgIpHTableIx
         TableIndex,
      er1645v2ATMCfgIpHAddress
         IpAddress,
      er1645v2ATMCfgIpHDhcpRelayOptionSubscriberId
         DisplayString
      }

er1645v2ATMCfgIpHActions OBJECT-TYPE
   SYNTAX      VariableLengthTableActions
   MAX-ACCESS  read-write
   STATUS      current
   DESCRIPTION
      "By way of this field, some manipulations
       on this table may be performed."
   ::= {er1645v2ATMCfgIpHEntry 2}

er1645v2ATMCfgIpHTableIx OBJECT-TYPE
   SYNTAX      TableIndex
   MAX-ACCESS  not-accessible
   STATUS      current
   DESCRIPTION
      ""
   ::= {er1645v2ATMCfgIpHEntry 11}

er1645v2ATMCfgIpHAddress OBJECT-TYPE
   SYNTAX      IpAddress
   MAX-ACCESS  read-write
   STATUS      current
   DESCRIPTION
      "Path: atm.editConf.pvcTable.ip.helpers.address"
   ::= {er1645v2ATMCfgIpHEntry 16777216}

er1645v2ATMCfgIpHDhcpRelayOptionSubscriberId OBJECT-TYPE
   SYNTAX      DisplayString
   MAX-ACCESS  read-write
   STATUS      current
   DESCRIPTION
      "Path: atm.editConf.pvcTable.ip.helpers.dhcpRelayOption.subscriberId"
   ::= {er1645v2ATMCfgIpHEntry 33947648}

er1645v2ATMCfgIpV6Addresses OBJECT-TYPE
   SYNTAX      SEQUENCE OF Er1645v2ATMCfgIpV6AddressesEntry
   MAX-ACCESS  not-accessible
   STATUS      current
   DESCRIPTION
      ""
   ::= {er1645v2ATMCfg 704839680}

er1645v2ATMCfgIpV6AddressesEntry OBJECT-TYPE
   SYNTAX      Er1645v2ATMCfgIpV6AddressesEntry
   MAX-ACCESS  not-accessible
   STATUS      current
   DESCRIPTION
      ""
   INDEX      { er1645v2ATMCfgTableIx,
                er1645v2ATMCfgIpV6AddressesTableIx }
   ::= {er1645v2ATMCfgIpV6Addresses 1}

Er1645v2ATMCfgIpV6AddressesEntry ::=
   SEQUENCE
      {
      er1645v2ATMCfgIpV6AddressesActions
         VariableLengthTableActions,
      er1645v2ATMCfgIpV6AddressesTableIx
         TableIndex,
      er1645v2ATMCfgIpV6AddressesType
         INTEGER,
      er1645v2ATMCfgIpV6AddressesAddress
         Ipv6Address,
      er1645v2ATMCfgIpV6AddressesPrefixLength
         Integer32,
      er1645v2ATMCfgIpV6AddressesGeneralPrefix
         DisplayString,
      er1645v2ATMCfgIpV6AddressesRaSend
         INTEGER,
      er1645v2ATMCfgIpV6AddressesRaOnLinkFlag
         INTEGER,
      er1645v2ATMCfgIpV6AddressesRaAutoFlag
         INTEGER,
      er1645v2ATMCfgIpV6AddressesRaValidLifeTime
         TimeTicks,
      er1645v2ATMCfgIpV6AddressesRaValidLTMode
         INTEGER,
      er1645v2ATMCfgIpV6AddressesRaPrefLifeTime
         TimeTicks,
      er1645v2ATMCfgIpV6AddressesRaPrefLTMode
         INTEGER
      }

er1645v2ATMCfgIpV6AddressesActions OBJECT-TYPE
   SYNTAX      VariableLengthTableActions
   MAX-ACCESS  read-write
   STATUS      current
   DESCRIPTION
      "By way of this field, some manipulations
       on this table may be performed."
   ::= {er1645v2ATMCfgIpV6AddressesEntry 2}

er1645v2ATMCfgIpV6AddressesTableIx OBJECT-TYPE
   SYNTAX      TableIndex
   MAX-ACCESS  not-accessible
   STATUS      current
   DESCRIPTION
      ""
   ::= {er1645v2ATMCfgIpV6AddressesEntry 11}

er1645v2ATMCfgIpV6AddressesType OBJECT-TYPE
   SYNTAX      INTEGER
               {
               unicast (0),
               eui64 (1),
               anycast (2),
               linkLocal (3),
               generalPrefix (4)
               }
   MAX-ACCESS  read-write
   STATUS      current
   DESCRIPTION
      "Path: atm.editConf.pvcTable.ipV6.addresses.type

       Possibilities:
               unicast   (0)
               eui64   (1)
               anycast   (2)
               linkLocal   (3)
               generalPrefix   (4)"
   ::= {er1645v2ATMCfgIpV6AddressesEntry 50331648}

er1645v2ATMCfgIpV6AddressesAddress OBJECT-TYPE
   SYNTAX      Ipv6Address
   MAX-ACCESS  read-write
   STATUS      current
   DESCRIPTION
      "Path: atm.editConf.pvcTable.ipV6.addresses.address

       ipv6 address"
   ::= {er1645v2ATMCfgIpV6AddressesEntry 16777216}

er1645v2ATMCfgIpV6AddressesPrefixLength OBJECT-TYPE
   SYNTAX      Integer32
   MAX-ACCESS  read-write
   STATUS      current
   DESCRIPTION
      "Path: atm.editConf.pvcTable.ipV6.addresses.prefixLength"
   ::= {er1645v2ATMCfgIpV6AddressesEntry 33554432}

er1645v2ATMCfgIpV6AddressesGeneralPrefix OBJECT-TYPE
   SYNTAX      DisplayString
   MAX-ACCESS  read-write
   STATUS      current
   DESCRIPTION
      "Path: atm.editConf.pvcTable.ipV6.addresses.generalPrefix"
   ::= {er1645v2ATMCfgIpV6AddressesEntry 83886080}

er1645v2ATMCfgIpV6AddressesRaSend OBJECT-TYPE
   SYNTAX      INTEGER
               {
               disabled (0),
               enabled (1)
               }
   MAX-ACCESS  read-write
   STATUS      current
   DESCRIPTION
      "Path: atm.editConf.pvcTable.ipV6.addresses.ra.send

       Possibilities:
               disabled   (0)
               enabled   (1)"
   ::= {er1645v2ATMCfgIpV6AddressesEntry 67174400}

er1645v2ATMCfgIpV6AddressesRaOnLinkFlag OBJECT-TYPE
   SYNTAX      INTEGER
               {
               disabled (0),
               enabled (1)
               }
   MAX-ACCESS  read-write
   STATUS      current
   DESCRIPTION
      "Path: atm.editConf.pvcTable.ipV6.addresses.ra.onLinkFlag

       Possibilities:
               disabled   (0)
               enabled   (1)"
   ::= {er1645v2ATMCfgIpV6AddressesEntry 67371008}

er1645v2ATMCfgIpV6AddressesRaAutoFlag OBJECT-TYPE
   SYNTAX      INTEGER
               {
               disabled (0),
               enabled (1)
               }
   MAX-ACCESS  read-write
   STATUS      current
   DESCRIPTION
      "Path: atm.editConf.pvcTable.ipV6.addresses.ra.autonomousFlag

       Possibilities:
               disabled   (0)
               enabled   (1)"
   ::= {er1645v2ATMCfgIpV6AddressesEntry 67567616}

er1645v2ATMCfgIpV6AddressesRaValidLifeTime OBJECT-TYPE
   SYNTAX      TimeTicks
   MAX-ACCESS  read-write
   STATUS      current
   DESCRIPTION
      "Path: atm.editConf.pvcTable.ipV6.addresses.ra.validLifeTime

       Time in centi-second."
   ::= {er1645v2ATMCfgIpV6AddressesEntry 67239936}

er1645v2ATMCfgIpV6AddressesRaValidLTMode OBJECT-TYPE
   SYNTAX      INTEGER
               {
               fixed (0),
               infinite (2)
               }
   MAX-ACCESS  read-write
   STATUS      current
   DESCRIPTION
      "Path: atm.editConf.pvcTable.ipV6.addresses.ra.validLifeTimeMode

       Possibilities:
               fixed   (0)
               infinite   (2)"
   ::= {er1645v2ATMCfgIpV6AddressesEntry 67305472}

er1645v2ATMCfgIpV6AddressesRaPrefLifeTime OBJECT-TYPE
   SYNTAX      TimeTicks
   MAX-ACCESS  read-write
   STATUS      current
   DESCRIPTION
      "Path: atm.editConf.pvcTable.ipV6.addresses.ra.prefLifeTime

       Time in centi-second."
   ::= {er1645v2ATMCfgIpV6AddressesEntry 67436544}

er1645v2ATMCfgIpV6AddressesRaPrefLTMode OBJECT-TYPE
   SYNTAX      INTEGER
               {
               fixed (0),
               infinite (2)
               }
   MAX-ACCESS  read-write
   STATUS      current
   DESCRIPTION
      "Path: atm.editConf.pvcTable.ipV6.addresses.ra.prefLifeTimeMode

       Possibilities:
               fixed   (0)
               infinite   (2)"
   ::= {er1645v2ATMCfgIpV6AddressesEntry 67502080}

er1645v2ATMCfgIpV6RaDnsOptionsRdnssServers OBJECT-TYPE
   SYNTAX      SEQUENCE OF Er1645v2ATMCfgIpV6RaDnsOptionsRdnssServersEntry
   MAX-ACCESS  not-accessible
   STATUS      current
   DESCRIPTION
      ""
   ::= {er1645v2ATMCfg 705039144}

er1645v2ATMCfgIpV6RaDnsOptionsRdnssServersEntry OBJECT-TYPE
   SYNTAX      Er1645v2ATMCfgIpV6RaDnsOptionsRdnssServersEntry
   MAX-ACCESS  not-accessible
   STATUS      current
   DESCRIPTION
      ""
   INDEX      { er1645v2ATMCfgTableIx,
                er1645v2ATMCfgIpV6RaDnsOptionsRdnssServersTableIx }
   ::= {er1645v2ATMCfgIpV6RaDnsOptionsRdnssServers 1}

Er1645v2ATMCfgIpV6RaDnsOptionsRdnssServersEntry ::=
   SEQUENCE
      {
      er1645v2ATMCfgIpV6RaDnsOptionsRdnssServersActions
         VariableLengthTableActions,
      er1645v2ATMCfgIpV6RaDnsOptionsRdnssServersTableIx
         TableIndex,
      er1645v2ATMCfgIpV6RaDnsOptionsRdnssServersAddress
         Ipv6Address
      }

er1645v2ATMCfgIpV6RaDnsOptionsRdnssServersActions OBJECT-TYPE
   SYNTAX      VariableLengthTableActions
   MAX-ACCESS  read-write
   STATUS      current
   DESCRIPTION
      "By way of this field, some manipulations
       on this table may be performed."
   ::= {er1645v2ATMCfgIpV6RaDnsOptionsRdnssServersEntry 2}

er1645v2ATMCfgIpV6RaDnsOptionsRdnssServersTableIx OBJECT-TYPE
   SYNTAX      TableIndex
   MAX-ACCESS  not-accessible
   STATUS      current
   DESCRIPTION
      ""
   ::= {er1645v2ATMCfgIpV6RaDnsOptionsRdnssServersEntry 11}

er1645v2ATMCfgIpV6RaDnsOptionsRdnssServersAddress OBJECT-TYPE
   SYNTAX      Ipv6Address
   MAX-ACCESS  read-write
   STATUS      current
   DESCRIPTION
      "Path: atm.editConf.pvcTable.ipV6.ra.dnsOptions.rdnss.servers.address

       ipv6 address"
   ::= {er1645v2ATMCfgIpV6RaDnsOptionsRdnssServersEntry 16777216}

er1645v2ATMCfgIpV6RaDnsOptionsDnsslDomains OBJECT-TYPE
   SYNTAX      SEQUENCE OF Er1645v2ATMCfgIpV6RaDnsOptionsDnsslDomainsEntry
   MAX-ACCESS  not-accessible
   STATUS      current
   DESCRIPTION
      ""
   ::= {er1645v2ATMCfg 705039176}

er1645v2ATMCfgIpV6RaDnsOptionsDnsslDomainsEntry OBJECT-TYPE
   SYNTAX      Er1645v2ATMCfgIpV6RaDnsOptionsDnsslDomainsEntry
   MAX-ACCESS  not-accessible
   STATUS      current
   DESCRIPTION
      ""
   INDEX      { er1645v2ATMCfgTableIx,
                er1645v2ATMCfgIpV6RaDnsOptionsDnsslDomainsTableIx }
   ::= {er1645v2ATMCfgIpV6RaDnsOptionsDnsslDomains 1}

Er1645v2ATMCfgIpV6RaDnsOptionsDnsslDomainsEntry ::=
   SEQUENCE
      {
      er1645v2ATMCfgIpV6RaDnsOptionsDnsslDomainsActions
         VariableLengthTableActions,
      er1645v2ATMCfgIpV6RaDnsOptionsDnsslDomainsTableIx
         TableIndex,
      er1645v2ATMCfgIpV6RaDnsOptionsDnsslDomainsName
         DisplayString
      }

er1645v2ATMCfgIpV6RaDnsOptionsDnsslDomainsActions OBJECT-TYPE
   SYNTAX      VariableLengthTableActions
   MAX-ACCESS  read-write
   STATUS      current
   DESCRIPTION
      "By way of this field, some manipulations
       on this table may be performed."
   ::= {er1645v2ATMCfgIpV6RaDnsOptionsDnsslDomainsEntry 2}

er1645v2ATMCfgIpV6RaDnsOptionsDnsslDomainsTableIx OBJECT-TYPE
   SYNTAX      TableIndex
   MAX-ACCESS  not-accessible
   STATUS      current
   DESCRIPTION
      ""
   ::= {er1645v2ATMCfgIpV6RaDnsOptionsDnsslDomainsEntry 11}

er1645v2ATMCfgIpV6RaDnsOptionsDnsslDomainsName OBJECT-TYPE
   SYNTAX      DisplayString
   MAX-ACCESS  read-write
   STATUS      current
   DESCRIPTION
      "Path: atm.editConf.pvcTable.ipV6.ra.dnsOptions.dnssl.domains.name"
   ::= {er1645v2ATMCfgIpV6RaDnsOptionsDnsslDomainsEntry 16777216}

er1645v2ATMCfgIpV6DhcpClientUserClassOpt OBJECT-TYPE
   SYNTAX      SEQUENCE OF Er1645v2ATMCfgIpV6DhcpClientUserClassOptEntry
   MAX-ACCESS  not-accessible
   STATUS      current
   DESCRIPTION
      ""
   ::= {er1645v2ATMCfg 705312768}

er1645v2ATMCfgIpV6DhcpClientUserClassOptEntry OBJECT-TYPE
   SYNTAX      Er1645v2ATMCfgIpV6DhcpClientUserClassOptEntry
   MAX-ACCESS  not-accessible
   STATUS      current
   DESCRIPTION
      ""
   INDEX      { er1645v2ATMCfgTableIx,
                er1645v2ATMCfgIpV6DhcpClientUserClassOptTableIx }
   ::= {er1645v2ATMCfgIpV6DhcpClientUserClassOpt 1}

Er1645v2ATMCfgIpV6DhcpClientUserClassOptEntry ::=
   SEQUENCE
      {
      er1645v2ATMCfgIpV6DhcpClientUserClassOptActions
         VariableLengthTableActions,
      er1645v2ATMCfgIpV6DhcpClientUserClassOptTableIx
         TableIndex,
      er1645v2ATMCfgIpV6DhcpClientUserClassOptValueAscii
         DisplayString,
      er1645v2ATMCfgIpV6DhcpClientUserClassOptValueDecimal
         Integer32,
      er1645v2ATMCfgIpV6DhcpClientUserClassOptValueHexData
         OCTET STRING
      }

er1645v2ATMCfgIpV6DhcpClientUserClassOptActions OBJECT-TYPE
   SYNTAX      VariableLengthTableActions
   MAX-ACCESS  read-write
   STATUS      current
   DESCRIPTION
      "By way of this field, some manipulations
       on this table may be performed."
   ::= {er1645v2ATMCfgIpV6DhcpClientUserClassOptEntry 2}

er1645v2ATMCfgIpV6DhcpClientUserClassOptTableIx OBJECT-TYPE
   SYNTAX      TableIndex
   MAX-ACCESS  not-accessible
   STATUS      current
   DESCRIPTION
      ""
   ::= {er1645v2ATMCfgIpV6DhcpClientUserClassOptEntry 11}

er1645v2ATMCfgIpV6DhcpClientUserClassOptValueAscii OBJECT-TYPE
   SYNTAX      DisplayString
   MAX-ACCESS  read-write
   STATUS      current
   DESCRIPTION
      "Path: atm.editConf.pvcTable.ipV6.dhcp.client.userClassOpt.value.ascii"
   ::= {er1645v2ATMCfgIpV6DhcpClientUserClassOptEntry 16842752}

er1645v2ATMCfgIpV6DhcpClientUserClassOptValueDecimal OBJECT-TYPE
   SYNTAX      Integer32
   MAX-ACCESS  read-write
   STATUS      current
   DESCRIPTION
      "Path: atm.editConf.pvcTable.ipV6.dhcp.client.userClassOpt.value.decimal"
   ::= {er1645v2ATMCfgIpV6DhcpClientUserClassOptEntry 16908288}

er1645v2ATMCfgIpV6DhcpClientUserClassOptValueHexData OBJECT-TYPE
   SYNTAX      OCTET STRING
   MAX-ACCESS  read-write
   STATUS      current
   DESCRIPTION
      "Path: atm.editConf.pvcTable.ipV6.dhcp.client.userClassOpt.value.hexData"
   ::= {er1645v2ATMCfgIpV6DhcpClientUserClassOptEntry 16973824}

er1645v2ATMCfgIpV6DhcpClientVendorCl OBJECT-TYPE
   SYNTAX      SEQUENCE OF Er1645v2ATMCfgIpV6DhcpClientVendorClEntry
   MAX-ACCESS  not-accessible
   STATUS      current
   DESCRIPTION
      ""
   ::= {er1645v2ATMCfg 705313792}

er1645v2ATMCfgIpV6DhcpClientVendorClEntry OBJECT-TYPE
   SYNTAX      Er1645v2ATMCfgIpV6DhcpClientVendorClEntry
   MAX-ACCESS  not-accessible
   STATUS      current
   DESCRIPTION
      ""
   INDEX      { er1645v2ATMCfgTableIx,
                er1645v2ATMCfgIpV6DhcpClientVendorClTableIx }
   ::= {er1645v2ATMCfgIpV6DhcpClientVendorCl 1}

Er1645v2ATMCfgIpV6DhcpClientVendorClEntry ::=
   SEQUENCE
      {
      er1645v2ATMCfgIpV6DhcpClientVendorClActions
         VariableLengthTableActions,
      er1645v2ATMCfgIpV6DhcpClientVendorClTableIx
         TableIndex,
      er1645v2ATMCfgIpV6DhcpClientVendorClValueAscii
         DisplayString,
      er1645v2ATMCfgIpV6DhcpClientVendorClValueDecimal
         Integer32,
      er1645v2ATMCfgIpV6DhcpClientVendorClValueHexData
         OCTET STRING
      }

er1645v2ATMCfgIpV6DhcpClientVendorClActions OBJECT-TYPE
   SYNTAX      VariableLengthTableActions
   MAX-ACCESS  read-write
   STATUS      current
   DESCRIPTION
      "By way of this field, some manipulations
       on this table may be performed."
   ::= {er1645v2ATMCfgIpV6DhcpClientVendorClEntry 2}

er1645v2ATMCfgIpV6DhcpClientVendorClTableIx OBJECT-TYPE
   SYNTAX      TableIndex
   MAX-ACCESS  not-accessible
   STATUS      current
   DESCRIPTION
      ""
   ::= {er1645v2ATMCfgIpV6DhcpClientVendorClEntry 11}

er1645v2ATMCfgIpV6DhcpClientVendorClValueAscii OBJECT-TYPE
   SYNTAX      DisplayString
   MAX-ACCESS  read-write
   STATUS      current
   DESCRIPTION
      "Path: atm.editConf.pvcTable.ipV6.dhcp.client.vendorClassOpt.value.ascii"
   ::= {er1645v2ATMCfgIpV6DhcpClientVendorClEntry 16842752}

er1645v2ATMCfgIpV6DhcpClientVendorClValueDecimal OBJECT-TYPE
   SYNTAX      Integer32
   MAX-ACCESS  read-write
   STATUS      current
   DESCRIPTION
      "Path: atm.editConf.pvcTable.ipV6.dhcp.client.vendorClassOpt.value.decimal"
   ::= {er1645v2ATMCfgIpV6DhcpClientVendorClEntry 16908288}

er1645v2ATMCfgIpV6DhcpClientVendorClValueHexData OBJECT-TYPE
   SYNTAX      OCTET STRING
   MAX-ACCESS  read-write
   STATUS      current
   DESCRIPTION
      "Path: atm.editConf.pvcTable.ipV6.dhcp.client.vendorClassOpt.value.hexData"
   ::= {er1645v2ATMCfgIpV6DhcpClientVendorClEntry 16973824}

er1645v2ATMCfgIpV6DhcpRelayDestinations OBJECT-TYPE
   SYNTAX      SEQUENCE OF Er1645v2ATMCfgIpV6DhcpRelayDestinationsEntry
   MAX-ACCESS  not-accessible
   STATUS      current
   DESCRIPTION
      ""
   ::= {er1645v2ATMCfg 705323072}

er1645v2ATMCfgIpV6DhcpRelayDestinationsEntry OBJECT-TYPE
   SYNTAX      Er1645v2ATMCfgIpV6DhcpRelayDestinationsEntry
   MAX-ACCESS  not-accessible
   STATUS      current
   DESCRIPTION
      ""
   INDEX      { er1645v2ATMCfgTableIx,
                er1645v2ATMCfgIpV6DhcpRelayDestinationsTableIx }
   ::= {er1645v2ATMCfgIpV6DhcpRelayDestinations 1}

Er1645v2ATMCfgIpV6DhcpRelayDestinationsEntry ::=
   SEQUENCE
      {
      er1645v2ATMCfgIpV6DhcpRelayDestinationsActions
         VariableLengthTableActions,
      er1645v2ATMCfgIpV6DhcpRelayDestinationsTableIx
         TableIndex,
      er1645v2ATMCfgIpV6DhcpRelayDestinationsAddress
         Ipv6Address,
      er1645v2ATMCfgIpV6DhcpRelayDestinationsInterface
         DisplayString
      }

er1645v2ATMCfgIpV6DhcpRelayDestinationsActions OBJECT-TYPE
   SYNTAX      VariableLengthTableActions
   MAX-ACCESS  read-write
   STATUS      current
   DESCRIPTION
      "By way of this field, some manipulations
       on this table may be performed."
   ::= {er1645v2ATMCfgIpV6DhcpRelayDestinationsEntry 2}

er1645v2ATMCfgIpV6DhcpRelayDestinationsTableIx OBJECT-TYPE
   SYNTAX      TableIndex
   MAX-ACCESS  not-accessible
   STATUS      current
   DESCRIPTION
      ""
   ::= {er1645v2ATMCfgIpV6DhcpRelayDestinationsEntry 11}

er1645v2ATMCfgIpV6DhcpRelayDestinationsAddress OBJECT-TYPE
   SYNTAX      Ipv6Address
   MAX-ACCESS  read-write
   STATUS      current
   DESCRIPTION
      "Path: atm.editConf.pvcTable.ipV6.dhcp.relay.destinations.address

       ipv6 address"
   ::= {er1645v2ATMCfgIpV6DhcpRelayDestinationsEntry 16777216}

er1645v2ATMCfgIpV6DhcpRelayDestinationsInterface OBJECT-TYPE
   SYNTAX      DisplayString
   MAX-ACCESS  read-write
   STATUS      current
   DESCRIPTION
      "Path: atm.editConf.pvcTable.ipV6.dhcp.relay.destinations.interface"
   ::= {er1645v2ATMCfgIpV6DhcpRelayDestinationsEntry 33554432}

er1645v2ATMCfgBridgingVlTVlans OBJECT-TYPE
   SYNTAX      SEQUENCE OF Er1645v2ATMCfgBridgingVlTVlansEntry
   MAX-ACCESS  not-accessible
   STATUS      current
   DESCRIPTION
      ""
   ::= {er1645v2ATMCfg 459079680}

er1645v2ATMCfgBridgingVlTVlansEntry OBJECT-TYPE
   SYNTAX      Er1645v2ATMCfgBridgingVlTVlansEntry
   MAX-ACCESS  not-accessible
   STATUS      current
   DESCRIPTION
      ""
   INDEX      { er1645v2ATMCfgTableIx,
                er1645v2ATMCfgBridgingVlTVlansTableIx }
   ::= {er1645v2ATMCfgBridgingVlTVlans 1}

Er1645v2ATMCfgBridgingVlTVlansEntry ::=
   SEQUENCE
      {
      er1645v2ATMCfgBridgingVlTVlansActions
         VariableLengthTableActions,
      er1645v2ATMCfgBridgingVlTVlansTableIx
         TableIndex,
      er1645v2ATMCfgBridgingVlTVlansVid
         Integer32,
      er1645v2ATMCfgBridgingVlTVlansEndVid
         Integer32,
      er1645v2ATMCfgBridgingVlTVlansAction
         INTEGER,
      er1645v2ATMCfgBridgingVlTVlansTagInfoTpid
         INTEGER,
      er1645v2ATMCfgBridgingVlTVlansTagInfoVid
         Integer32
      }

er1645v2ATMCfgBridgingVlTVlansActions OBJECT-TYPE
   SYNTAX      VariableLengthTableActions
   MAX-ACCESS  read-write
   STATUS      current
   DESCRIPTION
      "By way of this field, some manipulations
       on this table may be performed."
   ::= {er1645v2ATMCfgBridgingVlTVlansEntry 2}

er1645v2ATMCfgBridgingVlTVlansTableIx OBJECT-TYPE
   SYNTAX      TableIndex
   MAX-ACCESS  not-accessible
   STATUS      current
   DESCRIPTION
      ""
   ::= {er1645v2ATMCfgBridgingVlTVlansEntry 11}

er1645v2ATMCfgBridgingVlTVlansVid OBJECT-TYPE
   SYNTAX      Integer32
   MAX-ACCESS  read-write
   STATUS      current
   DESCRIPTION
      "Path: atm.editConf.pvcTable.bridging.vlanTagging.vlans.vid"
   ::= {er1645v2ATMCfgBridgingVlTVlansEntry 536870912}

er1645v2ATMCfgBridgingVlTVlansEndVid OBJECT-TYPE
   SYNTAX      Integer32
   MAX-ACCESS  read-write
   STATUS      current
   DESCRIPTION
      "Path: atm.editConf.pvcTable.bridging.vlanTagging.vlans.endVid"
   ::= {er1645v2ATMCfgBridgingVlTVlansEntry 2147483648}

er1645v2ATMCfgBridgingVlTVlansAction OBJECT-TYPE
   SYNTAX      INTEGER
               {
               discard (0),
               accept (1),
               tag (2)
               }
   MAX-ACCESS  read-write
   STATUS      current
   DESCRIPTION
      "Path: atm.editConf.pvcTable.bridging.vlanTagging.vlans.action

       Possibilities:
               discard   (0)
               accept   (1)
               tag   (2)"
   ::= {er1645v2ATMCfgBridgingVlTVlansEntry 1073741824}

er1645v2ATMCfgBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.vlans.tagInfo.tpid

       Possibilities:
               dot1Q   (33024)
               dot1ad   (34984)
               0x9100   (37120)
               0x9200   (37376)
               0x9300   (37632)"
   ::= {er1645v2ATMCfgBridgingVlTVlansEntry 1677721600}

er1645v2ATMCfgBridgingVlTVlansTagInfoVid OBJECT-TYPE
   SYNTAX      Integer32
   MAX-ACCESS  read-write
   STATUS      current
   DESCRIPTION
      "Path: atm.editConf.pvcTable.bridging.vlanTagging.vlans.tagInfo.vid"
   ::= {er1645v2ATMCfgBridgingVlTVlansEntry 1744830464}


er1645v2ATMVp OBJECT IDENTIFIER ::= {er1645v2ATM 92}

er1645v2ATMVpSSCTable OBJECT-TYPE
   SYNTAX      SEQUENCE OF Er1645v2ATMVpEntry
   MAX-ACCESS  not-accessible
   STATUS      current
   DESCRIPTION
      ""
   ::= {er1645v2ATMVp 1}

er1645v2ATMVpEntry OBJECT-TYPE
   SYNTAX      Er1645v2ATMVpEntry
   MAX-ACCESS  not-accessible
   STATUS      current
   DESCRIPTION
      ""
   INDEX      { er1645v2ATMVpTableIx }
   ::= {er1645v2ATMVpSSCTable 1}

Er1645v2ATMVpEntry ::=
   SEQUENCE
      {
      er1645v2ATMVpActions
         VariableLengthTableActions,
      er1645v2ATMVpTableIx
         TableIndex,
      er1645v2ATMVpVpi
         Integer32,
      er1645v2ATMVpLbOper
         INTEGER,
      er1645v2ATMVpLbInterval
         TimeTicks,
      er1645v2ATMVpLbFailsPerm
         Integer32,
      er1645v2ATMVpLbTar
         INTEGER,
      er1645v2ATMVpCcDir
         INTEGER,
      er1645v2ATMVpCcTar
         INTEGER,
      er1645v2ATMVpCcTxMode
         INTEGER,
      er1645v2ATMVpCcTxTxPer
         TimeTicks,
      er1645v2ATMVpCcRxRcvTim
         TimeTicks,
      er1645v2ATMVpCcActProc
         INTEGER,
      er1645v2ATMVpCcActTim
         TimeTicks,
      er1645v2ATMVpCcActCnt
         Integer32,
      er1645v2ATMVpCpt
         INTEGER
      }

er1645v2ATMVpActions OBJECT-TYPE
   SYNTAX      VariableLengthTableActions
   MAX-ACCESS  read-write
   STATUS      current
   DESCRIPTION
      "By way of this field, some manipulations
       on this table may be performed."
   ::= {er1645v2ATMVpEntry 2}

er1645v2ATMVpTableIx OBJECT-TYPE
   SYNTAX      TableIndex
   MAX-ACCESS  not-accessible
   STATUS      current
   DESCRIPTION
      ""
   ::= {er1645v2ATMVpEntry 11}

er1645v2ATMVpVpi OBJECT-TYPE
   SYNTAX      Integer32
   MAX-ACCESS  read-write
   STATUS      current
   DESCRIPTION
      "Path: atm.editConf.vp.vpi"
   ::= {er1645v2ATMVpEntry 16777216}

er1645v2ATMVpLbOper OBJECT-TYPE
   SYNTAX      INTEGER
               {
               disabled (0),
               enabled (1)
               }
   MAX-ACCESS  read-write
   STATUS      current
   DESCRIPTION
      "Path: atm.editConf.vp.oamF4Loopback.operation

       Possibilities:
               disabled   (0)
               enabled   (1)"
   ::= {er1645v2ATMVpEntry 33619968}

er1645v2ATMVpLbInterval OBJECT-TYPE
   SYNTAX      TimeTicks
   MAX-ACCESS  read-write
   STATUS      current
   DESCRIPTION
      "Path: atm.editConf.vp.oamF4Loopback.interval

       Time in centi-second."
   ::= {er1645v2ATMVpEntry 33685504}

er1645v2ATMVpLbFailsPerm OBJECT-TYPE
   SYNTAX      Integer32
   MAX-ACCESS  read-write
   STATUS      current
   DESCRIPTION
      "Path: atm.editConf.vp.oamF4Loopback.failsPermitted"
   ::= {er1645v2ATMVpEntry 33816576}

er1645v2ATMVpLbTar OBJECT-TYPE
   SYNTAX      INTEGER
               {
               endToEnd (0),
               segment (1),
               both (2)
               }
   MAX-ACCESS  read-write
   STATUS      current
   DESCRIPTION
      "Path: atm.editConf.vp.oamF4Loopback.target

       Possibilities:
               endToEnd   (0)
               segment   (1)
               both   (2)"
   ::= {er1645v2ATMVpEntry 33882112}

er1645v2ATMVpCcDir OBJECT-TYPE
   SYNTAX      INTEGER
               {
               sink (1),
               source (2),
               both (3)
               }
   MAX-ACCESS  read-write
   STATUS      current
   DESCRIPTION
      "Path: atm.editConf.vp.oamF4CC.direction

       Possibilities:
               sink   (1)
               source   (2)
               both   (3)"
   ::= {er1645v2ATMVpEntry 50397184}

er1645v2ATMVpCcTar OBJECT-TYPE
   SYNTAX      INTEGER
               {
               endToEnd (0),
               segment (1),
               both (2)
               }
   MAX-ACCESS  read-write
   STATUS      current
   DESCRIPTION
      "Path: atm.editConf.vp.oamF4CC.target

       Possibilities:
               endToEnd   (0)
               segment   (1)
               both   (2)"
   ::= {er1645v2ATMVpEntry 50462720}

er1645v2ATMVpCcTxMode OBJECT-TYPE
   SYNTAX      INTEGER
               {
               continuously (0),
               onIdle (1)
               }
   MAX-ACCESS  read-write
   STATUS      current
   DESCRIPTION
      "Path: atm.editConf.vp.oamF4CC.tx.mode

       Possibilities:
               continuously   (0)
               onIdle   (1)"
   ::= {er1645v2ATMVpEntry 50528512}

er1645v2ATMVpCcTxTxPer OBJECT-TYPE
   SYNTAX      TimeTicks
   MAX-ACCESS  read-write
   STATUS      current
   DESCRIPTION
      "Path: atm.editConf.vp.oamF4CC.tx.interval

       Time in centi-second."
   ::= {er1645v2ATMVpEntry 50528768}

er1645v2ATMVpCcRxRcvTim OBJECT-TYPE
   SYNTAX      TimeTicks
   MAX-ACCESS  read-write
   STATUS      current
   DESCRIPTION
      "Path: atm.editConf.vp.oamF4CC.rx.timeOut

       Time in centi-second."
   ::= {er1645v2ATMVpEntry 50725120}

er1645v2ATMVpCcActProc OBJECT-TYPE
   SYNTAX      INTEGER
               {
               passive (0),
               activated (1),
               deactivated (2),
               initActivation (3)
               }
   MAX-ACCESS  read-write
   STATUS      current
   DESCRIPTION
      "Path: atm.editConf.vp.oamF4CC.actDeact.initProcedure

       Possibilities:
               passive   (0)
               activated   (1)
               deactivated   (2)
               initActivation   (3)"
   ::= {er1645v2ATMVpEntry 50594048}

er1645v2ATMVpCcActTim OBJECT-TYPE
   SYNTAX      TimeTicks
   MAX-ACCESS  read-write
   STATUS      current
   DESCRIPTION
      "Path: atm.editConf.vp.oamF4CC.actDeact.retryInterval

       Time in centi-second."
   ::= {er1645v2ATMVpEntry 50594304}

er1645v2ATMVpCcActCnt OBJECT-TYPE
   SYNTAX      Integer32
   MAX-ACCESS  read-write
   STATUS      current
   DESCRIPTION
      "Path: atm.editConf.vp.oamF4CC.actDeact.retryCount"
   ::= {er1645v2ATMVpEntry 50594560}

er1645v2ATMVpCpt OBJECT-TYPE
   SYNTAX      INTEGER
               {
               no (0),
               yes (1)
               }
   MAX-ACCESS  read-write
   STATUS      current
   DESCRIPTION
      "Path: atm.editConf.vp.segmentEndPoint

       Possibilities:
               no   (0)
               yes   (1)"
   ::= {er1645v2ATMVpEntry 83886080}



sr1645v2ATM OBJECT IDENTIFIER ::= {r1645v2ATM 14}


sr1645v2ATMAtmSync OBJECT-TYPE
   SYNTAX      INTEGER
               {
               notSynced (0),
               synced (1)
               }
   MAX-ACCESS  read-only
   STATUS      current
   DESCRIPTION
      "Path: atm.status.atmSync

       Possibilities:
               notSynced   (0)
               synced   (1)"
   ::= {sr1645v2ATM 91}


sr1645v2ATMStat OBJECT IDENTIFIER ::= {sr1645v2ATM 2}

sr1645v2ATMStatSSCTable OBJECT-TYPE
   SYNTAX      SEQUENCE OF Sr1645v2ATMStatEntry
   MAX-ACCESS  not-accessible
   STATUS      current
   DESCRIPTION
      ""
   ::= {sr1645v2ATMStat 1}

sr1645v2ATMStatEntry OBJECT-TYPE
   SYNTAX      Sr1645v2ATMStatEntry
   MAX-ACCESS  not-accessible
   STATUS      current
   DESCRIPTION
      ""
   INDEX      { sr1645v2ATMStatTableIx }
   ::= {sr1645v2ATMStatSSCTable 1}

Sr1645v2ATMStatEntry ::=
   SEQUENCE
      {
      sr1645v2ATMStatTableIx
         TableIndex,
      sr1645v2ATMStatName
         DisplayString,
      sr1645v2ATMStatMode
         INTEGER,
      sr1645v2ATMStatIfOperStatus
         INTEGER,
      sr1645v2ATMStatIfLastChange
         TimeTicks,
      sr1645v2ATMStatIfLastChangeDate
         DisplayString,
      sr1645v2ATMStatIpAddress
         IpAddress,
      sr1645v2ATMStatIpNetMask
         IpAddress,
      sr1645v2ATMStatIpRemote
         IpAddress,
      sr1645v2ATMStatIpV6State
         INTEGER,
      sr1645v2ATMStatIpV6InterfaceId
         OCTET STRING,
      sr1645v2ATMStatIpV6LinkMtu
         Integer32,
      sr1645v2ATMStatIpV6HopLimit
         Integer32,
      sr1645v2ATMStatIpV6DhcpIaid
         Counter32,
      sr1645v2ATMStatIpV6RaRcvOption
         Integer32,
      sr1645v2ATMStatBridgingStatus
         INTEGER,
      sr1645v2ATMStatBridgingSpanningTreePortRole
         INTEGER,
      sr1645v2ATMStatBridgingSpanningTreePortId
         Integer32,
      sr1645v2ATMStatBridgingSpanningTreePpCostExtPathCost
         Integer32,
      sr1645v2ATMStatBridgingSpanningTreePpCostIntPathCost
         Integer32,
      sr1645v2ATMStatBridgingSpanningTreeExtRpCost
         Integer32,
      sr1645v2ATMStatBridgingSpanningTreeIntRpCost
         Integer32,
      sr1645v2ATMStatBridgingSpanningTreeDesBrIdPriority
         Integer32,
      sr1645v2ATMStatBridgingSpanningTreeDesBrIdMacAddress
         OCTET STRING,
      sr1645v2ATMStatBridgingSpanningTreeDesPrtId
         Integer32,
      sr1645v2ATMStatBridgingSpanningTreeDesInt
         INTEGER,
      sr1645v2ATMStatBridgingSpanningTreeEdgeDetection
         INTEGER,
      sr1645v2ATMStatAtmVpi
         Integer32,
      sr1645v2ATMStatAtmVci
         Integer32,
      sr1645v2ATMStatAtmServCat
         INTEGER,
      sr1645v2ATMStatAtmPeakCellRate
         Integer32,
      sr1645v2ATMStatAtmSustCellRate
         Integer32,
      sr1645v2ATMStatAtmMaxBurstSize
         Integer32,
      sr1645v2ATMStatAtmPppOEthDiscState
         INTEGER,
      sr1645v2ATMStatAtmPppOEthPeerMac
         OCTET STRING,
      sr1645v2ATMStatAtmPppOEthServiceName
         DisplayString,
      sr1645v2ATMStatAtmPppLcpState
         INTEGER,
      sr1645v2ATMStatAtmPppIpcpState
         INTEGER,
      sr1645v2ATMStatAtmPppIp6cpState
         INTEGER,
      sr1645v2ATMStatAtmPppBcpState
         INTEGER,
      sr1645v2ATMStatAtmPppCcpState
         INTEGER,
      sr1645v2ATMStatAtmPppHisCompRat
         Integer32,
      sr1645v2ATMStatAtmPppMyCompRat
         Integer32,
      sr1645v2ATMStatAtmPppMyAutSt
         INTEGER,
      sr1645v2ATMStatAtmPppHisAutSt
         INTEGER,
      sr1645v2ATMStatAtmOamF5SegOamLB
         INTEGER,
      sr1645v2ATMStatAtmOamF5SegOamCC
         INTEGER,
      sr1645v2ATMStatAtmOamF5SegAis
         INTEGER,
      sr1645v2ATMStatAtmOamF5SegRdi
         INTEGER,
      sr1645v2ATMStatAtmOamF5EteOamLB
         INTEGER,
      sr1645v2ATMStatAtmOamF5EteOamCC
         INTEGER,
      sr1645v2ATMStatAtmOamF5EteAis
         INTEGER,
      sr1645v2ATMStatAtmOamF5EteRdi
         INTEGER,
      sr1645v2ATMStatAtmOamF5SegEP
         INTEGER,
      sr1645v2ATMStatAtmOamF5CnxEP
         INTEGER
      }

sr1645v2ATMStatTableIx OBJECT-TYPE
   SYNTAX      TableIndex
   MAX-ACCESS  not-accessible
   STATUS      current
   DESCRIPTION
      ""
   ::= {sr1645v2ATMStatEntry 11}

sr1645v2ATMStatName OBJECT-TYPE
   SYNTAX      DisplayString
   MAX-ACCESS  read-only
   STATUS      current
   DESCRIPTION
      "Path: atm.status.pvcTable.name"
   ::= {sr1645v2ATMStatEntry 16777216}

sr1645v2ATMStatMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: atm.status.pvcTable.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2ATMStatEntry 335544320}

sr1645v2ATMStatIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: atm.status.pvcTable.ifOperStatus

       Possibilities:
               up   (1)
               down   (2)
               testing   (3)
               unknown   (4)
               dormant   (5)
               notPresent   (6)
               lowerLayerDown   (7)"
   ::= {sr1645v2ATMStatEntry 1795162112}

sr1645v2ATMStatIfLastChange OBJECT-TYPE
   SYNTAX      TimeTicks
   MAX-ACCESS  read-only
   STATUS      current
   DESCRIPTION
      "Path: atm.status.pvcTable.ifLastChange

       Time in centi-second."
   ::= {sr1645v2ATMStatEntry 1811939328}

sr1645v2ATMStatIfLastChangeDate OBJECT-TYPE
   SYNTAX      DisplayString
   MAX-ACCESS  read-only
   STATUS      current
   DESCRIPTION
      "Path: atm.status.pvcTable.ifLastChangeDate"
   ::= {sr1645v2ATMStatEntry 3070230528}

sr1645v2ATMStatIpAddress OBJECT-TYPE
   SYNTAX      IpAddress
   MAX-ACCESS  read-only
   STATUS      current
   DESCRIPTION
      "Path: atm.status.pvcTable.ip.address"
   ::= {sr1645v2ATMStatEntry 51380224}

sr1645v2ATMStatIpNetMask OBJECT-TYPE
   SYNTAX      IpAddress
   MAX-ACCESS  read-only
   STATUS      current
   DESCRIPTION
      "Path: atm.status.pvcTable.ip.netMask"
   ::= {sr1645v2ATMStatEntry 51445760}

sr1645v2ATMStatIpRemote OBJECT-TYPE
   SYNTAX      IpAddress
   MAX-ACCESS  read-only
   STATUS      current
   DESCRIPTION
      "Path: atm.status.pvcTable.ip.remote"
   ::= {sr1645v2ATMStatEntry 51511296}

sr1645v2ATMStatIpV6State OBJECT-TYPE
   SYNTAX      INTEGER
               {
               disabled (0),
               enabled (1)
               }
   MAX-ACCESS  read-only
   STATUS      current
   DESCRIPTION
      "Path: atm.status.pvcTable.ipV6.state

       Possibilities:
               disabled   (0)
               enabled   (1)"
   ::= {sr1645v2ATMStatEntry 100728832}

sr1645v2ATMStatIpV6InterfaceId OBJECT-TYPE
   SYNTAX      OCTET STRING
   MAX-ACCESS  read-only
   STATUS      current
   DESCRIPTION
      "Path: atm.status.pvcTable.ipV6.interfaceId"
   ::= {sr1645v2ATMStatEntry 100794368}

sr1645v2ATMStatIpV6LinkMtu OBJECT-TYPE
   SYNTAX      Integer32
   MAX-ACCESS  read-only
   STATUS      current
   DESCRIPTION
      "Path: atm.status.pvcTable.ipV6.linkMtu"
   ::= {sr1645v2ATMStatEntry 100925440}

sr1645v2ATMStatIpV6HopLimit OBJECT-TYPE
   SYNTAX      Integer32
   MAX-ACCESS  read-only
   STATUS      current
   DESCRIPTION
      "Path: atm.status.pvcTable.ipV6.hopLimit"
   ::= {sr1645v2ATMStatEntry 100990976}

sr1645v2ATMStatIpV6DhcpIaid OBJECT-TYPE
   SYNTAX      Counter32
   MAX-ACCESS  read-only
   STATUS      current
   DESCRIPTION
      "Path: atm.status.pvcTable.ipV6.dhcp.iaid

       32 bit unsigned wrappable counter."
   ::= {sr1645v2ATMStatEntry 101056768}

sr1645v2ATMStatIpV6RaRcvOption OBJECT-TYPE
   SYNTAX      Integer32
   MAX-ACCESS  read-only
   STATUS      current
   DESCRIPTION
      "Path: atm.status.pvcTable.ipV6.raRcvOption

       Bit meanings:
               bit 0 = linkMtu,
               bit 1 = srcLinkLayer,
               bit 2 = prefixInfo,
               bit 3 = rdnss,
               bit 4 = dnssl"
   ::= {sr1645v2ATMStatEntry 101122048}

sr1645v2ATMStatBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: atm.status.pvcTable.bridging.status

       Possibilities:
               disabled   (0)
               discarding   (1)
               learning   (2)
               forwarding   (3)
               backupBlockedIntfDown   (256)
               backupBlockedIntfUp   (259)
               shutdown   (255)"
   ::= {sr1645v2ATMStatEntry 453050368}

sr1645v2ATMStatBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: atm.status.pvcTable.bridging.spanningTree.portRole

       Possibilities:
               none   (0)
               root   (1)
               designated   (2)
               alternate   (3)
               backup   (4)
               disabled   (5)
               master   (6)"
   ::= {sr1645v2ATMStatEntry 453116160}

sr1645v2ATMStatBridgingSpanningTreePortId OBJECT-TYPE
   SYNTAX      Integer32
   MAX-ACCESS  read-only
   STATUS      current
   DESCRIPTION
      "Path: atm.status.pvcTable.bridging.spanningTree.portId"
   ::= {sr1645v2ATMStatEntry 453116416}

sr1645v2ATMStatBridgingSpanningTreePpCostExtPathCost OBJECT-TYPE
   SYNTAX      Integer32
   MAX-ACCESS  read-only
   STATUS      current
   DESCRIPTION
      "Path: atm.status.pvcTable.bridging.spanningTree.portPathCosts.extPathCost"
   ::= {sr1645v2ATMStatEntry 453116673}

sr1645v2ATMStatBridgingSpanningTreePpCostIntPathCost OBJECT-TYPE
   SYNTAX      Integer32
   MAX-ACCESS  read-only
   STATUS      current
   DESCRIPTION
      "Path: atm.status.pvcTable.bridging.spanningTree.portPathCosts.intPathCost"
   ::= {sr1645v2ATMStatEntry 453116674}

sr1645v2ATMStatBridgingSpanningTreeExtRpCost OBJECT-TYPE
   SYNTAX      Integer32
   MAX-ACCESS  read-only
   STATUS      current
   DESCRIPTION
      "Path: atm.status.pvcTable.bridging.spanningTree.extRootPathCost"
   ::= {sr1645v2ATMStatEntry 453116928}

sr1645v2ATMStatBridgingSpanningTreeIntRpCost OBJECT-TYPE
   SYNTAX      Integer32
   MAX-ACCESS  read-only
   STATUS      current
   DESCRIPTION
      "Path: atm.status.pvcTable.bridging.spanningTree.intRootPathCost"
   ::= {sr1645v2ATMStatEntry 453117184}

sr1645v2ATMStatBridgingSpanningTreeDesBrIdPriority OBJECT-TYPE
   SYNTAX      Integer32
   MAX-ACCESS  read-only
   STATUS      current
   DESCRIPTION
      "Path: atm.status.pvcTable.bridging.spanningTree.designatedBridgeId.priority"
   ::= {sr1645v2ATMStatEntry 453117441}

sr1645v2ATMStatBridgingSpanningTreeDesBrIdMacAddress OBJECT-TYPE
   SYNTAX      OCTET STRING
   MAX-ACCESS  read-only
   STATUS      current
   DESCRIPTION
      "Path: atm.status.pvcTable.bridging.spanningTree.designatedBridgeId.macAddress

       MAC address."
   ::= {sr1645v2ATMStatEntry 453117442}

sr1645v2ATMStatBridgingSpanningTreeDesPrtId OBJECT-TYPE
   SYNTAX      Integer32
   MAX-ACCESS  read-only
   STATUS      current
   DESCRIPTION
      "Path: atm.status.pvcTable.bridging.spanningTree.designatedPortId"
   ::= {sr1645v2ATMStatEntry 453117696}

sr1645v2ATMStatBridgingSpanningTreeDesInt OBJECT-TYPE
   SYNTAX      INTEGER
               {
               no (0),
               yes (1)
               }
   MAX-ACCESS  read-only
   STATUS      current
   DESCRIPTION
      "Path: atm.status.pvcTable.bridging.spanningTree.designatedOrInternal

       Possibilities:
               no   (0)
               yes   (1)"
   ::= {sr1645v2ATMStatEntry 453117952}

sr1645v2ATMStatBridgingSpanningTreeEdgeDetection OBJECT-TYPE
   SYNTAX      INTEGER
               {
               none (0),
               edge (1),
               notEdge (2)
               }
   MAX-ACCESS  read-only
   STATUS      current
   DESCRIPTION
      "Path: atm.status.pvcTable.bridging.spanningTree.edgeDetection

       Possibilities:
               none   (0)
               edge   (1)
               notEdge   (2)"
   ::= {sr1645v2ATMStatEntry 453118208}

sr1645v2ATMStatAtmVpi OBJECT-TYPE
   SYNTAX      Integer32
   MAX-ACCESS  read-only
   STATUS      current
   DESCRIPTION
      "Path: atm.status.pvcTable.atm.vpi"
   ::= {sr1645v2ATMStatEntry 285278208}

sr1645v2ATMStatAtmVci OBJECT-TYPE
   SYNTAX      Integer32
   MAX-ACCESS  read-only
   STATUS      current
   DESCRIPTION
      "Path: atm.status.pvcTable.atm.vci"
   ::= {sr1645v2ATMStatEntry 285343744}

sr1645v2ATMStatAtmServCat OBJECT-TYPE
   SYNTAX      INTEGER
               {
               notAssigned (0),
               cbr (1),
               vbrmrt (2),
               vbrmnrt (3),
               ubr (4),
               cbrudg (5),
               vbrudgmrt (6),
               vbrudgmnrt (7),
               optional (50)
               }
   MAX-ACCESS  read-only
   STATUS      current
   DESCRIPTION
      "Path: atm.status.pvcTable.atm.serviceCategory

       Possibilities:
               notAssigned   (0)
               cbr   (1)
               vbr-rt   (2)
               vbr-nrt   (3)
               ubr   (4)
               cbr_dg   (5)
               vbr_dg-rt   (6)
               vbr_dg-nrt   (7)
               optional   (50)"
   ::= {sr1645v2ATMStatEntry 285736960}

sr1645v2ATMStatAtmPeakCellRate OBJECT-TYPE
   SYNTAX      Integer32
   UNITS       "bps"
   MAX-ACCESS  read-only
   STATUS      current
   DESCRIPTION
      "Path: atm.status.pvcTable.atm.peakCellRate

       unit name = bps"
   ::= {sr1645v2ATMStatEntry 285605888}

sr1645v2ATMStatAtmSustCellRate OBJECT-TYPE
   SYNTAX      Integer32
   UNITS       "bps"
   MAX-ACCESS  read-only
   STATUS      current
   DESCRIPTION
      "Path: atm.status.pvcTable.atm.sustCellRate

       unit name = bps"
   ::= {sr1645v2ATMStatEntry 285671424}

sr1645v2ATMStatAtmMaxBurstSize OBJECT-TYPE
   SYNTAX      Integer32
   UNITS       "cellTimes"
   MAX-ACCESS  read-only
   STATUS      current
   DESCRIPTION
      "Path: atm.status.pvcTable.atm.maxBurstSize

       unit name = cellTimes"
   ::= {sr1645v2ATMStatEntry 285802496}

sr1645v2ATMStatAtmPppOEthDiscState OBJECT-TYPE
   SYNTAX      INTEGER
               {
               idle (0),
               waitForPADO (1),
               waitForPADS (2),
               established (3)
               }
   MAX-ACCESS  read-only
   STATUS      current
   DESCRIPTION
      "Path: atm.status.pvcTable.atm.pppOverEth.discState

       Possibilities:
               idle   (0)
               waitForPADO   (1)
               waitForPADS   (2)
               established   (3)"
   ::= {sr1645v2ATMStatEntry 285409536}

sr1645v2ATMStatAtmPppOEthPeerMac OBJECT-TYPE
   SYNTAX      OCTET STRING
   MAX-ACCESS  read-only
   STATUS      current
   DESCRIPTION
      "Path: atm.status.pvcTable.atm.pppOverEth.remoteMacAddress

       MAC address."
   ::= {sr1645v2ATMStatEntry 285409792}

sr1645v2ATMStatAtmPppOEthServiceName OBJECT-TYPE
   SYNTAX      DisplayString
   MAX-ACCESS  read-only
   STATUS      current
   DESCRIPTION
      "Path: atm.status.pvcTable.atm.pppOverEth.serviceName"
   ::= {sr1645v2ATMStatEntry 285410048}

sr1645v2ATMStatAtmPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2ATMStatEntry 285475072}

sr1645v2ATMStatAtmPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2ATMStatEntry 285475328}

sr1645v2ATMStatAtmPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2ATMStatEntry 285478656}

sr1645v2ATMStatAtmPppBcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2ATMStatEntry 285475584}

sr1645v2ATMStatAtmPppCcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ccpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2ATMStatEntry 285477888}

sr1645v2ATMStatAtmPppHisCompRat OBJECT-TYPE
   SYNTAX      Integer32
   UNITS       "%"
   MAX-ACCESS  read-only
   STATUS      current
   DESCRIPTION
      "Path: atm.status.pvcTable.atm.ppp.myCompressionRatio

       unit name = %"
   ::= {sr1645v2ATMStatEntry 285478144}

sr1645v2ATMStatAtmPppMyCompRat OBJECT-TYPE
   SYNTAX      Integer32
   UNITS       "%"
   MAX-ACCESS  read-only
   STATUS      current
   DESCRIPTION
      "Path: atm.status.pvcTable.atm.ppp.hisCompressionRatio

       unit name = %"
   ::= {sr1645v2ATMStatEntry 285478400}

sr1645v2ATMStatAtmPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: atm.status.pvcTable.atm.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2ATMStatEntry 285477376}

sr1645v2ATMStatAtmPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: atm.status.pvcTable.atm.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2ATMStatEntry 285477632}

sr1645v2ATMStatAtmOamF5SegOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.segment.oamLB

       Possibilities:
               ready   (0)
               waitActRes   (1)
               waitActCon   (2)
               waitDeactCon   (3)
               active   (4)
               deactivated   (5)"
   ::= {sr1645v2ATMStatEntry 285540640}

sr1645v2ATMStatAtmOamF5SegOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.segment.oamCC

       Possibilities:
               ready   (0)
               waitActRes   (1)
               waitActCon   (2)
               waitDeactCon   (3)
               active   (4)
               deactivated   (5)"
   ::= {sr1645v2ATMStatEntry 285540672}

sr1645v2ATMStatAtmOamF5SegAis OBJECT-TYPE
   SYNTAX      INTEGER
               {
               inactive (0),
               active (1)
               }
   MAX-ACCESS  read-only
   STATUS      current
   DESCRIPTION
      "Path: atm.status.pvcTable.atm.oamF5.segment.aisState

       Possibilities:
               inactive   (0)
               active   (1)"
   ::= {sr1645v2ATMStatEntry 285540736}

sr1645v2ATMStatAtmOamF5SegRdi OBJECT-TYPE
   SYNTAX      INTEGER
               {
               inactive (0),
               active (1)
               }
   MAX-ACCESS  read-only
   STATUS      current
   DESCRIPTION
      "Path: atm.status.pvcTable.atm.oamF5.segment.rdiState

       Possibilities:
               inactive   (0)
               active   (1)"
   ::= {sr1645v2ATMStatEntry 285540768}

sr1645v2ATMStatAtmOamF5EteOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.endToEnd.oamLB

       Possibilities:
               ready   (0)
               waitActRes   (1)
               waitActCon   (2)
               waitDeactCon   (3)
               active   (4)
               deactivated   (5)"
   ::= {sr1645v2ATMStatEntry 285540896}

sr1645v2ATMStatAtmOamF5EteOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.endToEnd.oamCC

       Possibilities:
               ready   (0)
               waitActRes   (1)
               waitActCon   (2)
               waitDeactCon   (3)
               active   (4)
               deactivated   (5)"
   ::= {sr1645v2ATMStatEntry 285540928}

sr1645v2ATMStatAtmOamF5EteAis OBJECT-TYPE
   SYNTAX      INTEGER
               {
               inactive (0),
               active (1)
               }
   MAX-ACCESS  read-only
   STATUS      current
   DESCRIPTION
      "Path: atm.status.pvcTable.atm.oamF5.endToEnd.aisState

       Possibilities:
               inactive   (0)
               active   (1)"
   ::= {sr1645v2ATMStatEntry 285540992}

sr1645v2ATMStatAtmOamF5EteRdi OBJECT-TYPE
   SYNTAX      INTEGER
               {
               inactive (0),
               active (1)
               }
   MAX-ACCESS  read-only
   STATUS      current
   DESCRIPTION
      "Path: atm.status.pvcTable.atm.oamF5.endToEnd.rdiState

       Possibilities:
               inactive   (0)
               active   (1)"
   ::= {sr1645v2ATMStatEntry 285541024}

sr1645v2ATMStatAtmOamF5SegEP OBJECT-TYPE
   SYNTAX      INTEGER
               {
               no (0),
               yes (1)
               }
   MAX-ACCESS  read-only
   STATUS      current
   DESCRIPTION
      "Path: atm.status.pvcTable.atm.oamF5.segmentEndPoint

       Possibilities:
               no   (0)
               yes   (1)"
   ::= {sr1645v2ATMStatEntry 285541120}

sr1645v2ATMStatAtmOamF5CnxEP OBJECT-TYPE
   SYNTAX      INTEGER
               {
               no (0),
               yes (1)
               }
   MAX-ACCESS  read-only
   STATUS      current
   DESCRIPTION
      "Path: atm.status.pvcTable.atm.oamF5.connectionEndPoint

       Possibilities:
               no   (0)
               yes   (1)"
   ::= {sr1645v2ATMStatEntry 285541376}

sr1645v2ATMStatIpV6Addresses OBJECT-TYPE
   SYNTAX      SEQUENCE OF Sr1645v2ATMStatIpV6AddressesEntry
   MAX-ACCESS  not-accessible
   STATUS      current
   DESCRIPTION
      ""
   ::= {sr1645v2ATMStat 100859904}

sr1645v2ATMStatIpV6AddressesEntry OBJECT-TYPE
   SYNTAX      Sr1645v2ATMStatIpV6AddressesEntry
   MAX-ACCESS  not-accessible
   STATUS      current
   DESCRIPTION
      ""
   INDEX      { sr1645v2ATMStatTableIx,
                sr1645v2ATMStatIpV6AddressesTableIx }
   ::= {sr1645v2ATMStatIpV6Addresses 1}

Sr1645v2ATMStatIpV6AddressesEntry ::=
   SEQUENCE
      {
      sr1645v2ATMStatIpV6AddressesTableIx
         TableIndex,
      sr1645v2ATMStatIpV6AddressesAddress
         Ipv6Address,
      sr1645v2ATMStatIpV6AddressesPrefixLength
         Integer32,
      sr1645v2ATMStatIpV6AddressesStatus
         INTEGER,
      sr1645v2ATMStatIpV6AddressesOrigin
         INTEGER,
      sr1645v2ATMStatIpV6AddressesFlagsInterfaceId
         INTEGER,
      sr1645v2ATMStatIpV6AddressesFlagsAnycast
         INTEGER,
      sr1645v2ATMStatIpV6AddressesTimersValidLifeTime
         TimeTicks,
      sr1645v2ATMStatIpV6AddressesTimersPrefLifeTime
         TimeTicks
      }

sr1645v2ATMStatIpV6AddressesTableIx OBJECT-TYPE
   SYNTAX      TableIndex
   MAX-ACCESS  not-accessible
   STATUS      current
   DESCRIPTION
      ""
   ::= {sr1645v2ATMStatIpV6AddressesEntry 11}

sr1645v2ATMStatIpV6AddressesAddress OBJECT-TYPE
   SYNTAX      Ipv6Address
   MAX-ACCESS  read-only
   STATUS      current
   DESCRIPTION
      "Path: atm.status.pvcTable.ipV6.addresses.address

       ipv6 address"
   ::= {sr1645v2ATMStatIpV6AddressesEntry 16777216}

sr1645v2ATMStatIpV6AddressesPrefixLength OBJECT-TYPE
   SYNTAX      Integer32
   MAX-ACCESS  read-only
   STATUS      current
   DESCRIPTION
      "Path: atm.status.pvcTable.ipV6.addresses.prefixLength"
   ::= {sr1645v2ATMStatIpV6AddressesEntry 33554432}

sr1645v2ATMStatIpV6AddressesStatus OBJECT-TYPE
   SYNTAX      INTEGER
               {
               invalid (0),
               tentative (1),
               deprecated (2),
               preferred (3)
               }
   MAX-ACCESS  read-only
   STATUS      current
   DESCRIPTION
      "Path: atm.status.pvcTable.ipV6.addresses.status

       Possibilities:
               invalid   (0)
               tentative   (1)
               deprecated   (2)
               preferred   (3)"
   ::= {sr1645v2ATMStatIpV6AddressesEntry 50331648}

sr1645v2ATMStatIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: atm.status.pvcTable.ipV6.addresses.origin

       Possibilities:
               unknown   (0)
               manual   (1)
               generalPrefix   (2)
               statelessAuto   (3)
               statefullAuto   (4)"
   ::= {sr1645v2ATMStatIpV6AddressesEntry 67108864}

sr1645v2ATMStatIpV6AddressesFlagsInterfaceId OBJECT-TYPE
   SYNTAX      INTEGER
               {
               no (0),
               yes (1)
               }
   MAX-ACCESS  read-only
   STATUS      current
   DESCRIPTION
      "Path: atm.status.pvcTable.ipV6.addresses.flags.interfaceId

       Possibilities:
               no   (0)
               yes   (1)"
   ::= {sr1645v2ATMStatIpV6AddressesEntry 83951616}

sr1645v2ATMStatIpV6AddressesFlagsAnycast OBJECT-TYPE
   SYNTAX      INTEGER
               {
               no (0),
               yes (1)
               }
   MAX-ACCESS  read-only
   STATUS      current
   DESCRIPTION
      "Path: atm.status.pvcTable.ipV6.addresses.flags.anycast

       Possibilities:
               no   (0)
               yes   (1)"
   ::= {sr1645v2ATMStatIpV6AddressesEntry 84017152}

sr1645v2ATMStatIpV6AddressesTimersValidLifeTime OBJECT-TYPE
   SYNTAX      TimeTicks
   MAX-ACCESS  read-only
   STATUS      current
   DESCRIPTION
      "Path: atm.status.pvcTable.ipV6.addresses.timers.validLifeTime

       Time in centi-second."
   ::= {sr1645v2ATMStatIpV6AddressesEntry 100794368}

sr1645v2ATMStatIpV6AddressesTimersPrefLifeTime OBJECT-TYPE
   SYNTAX      TimeTicks
   MAX-ACCESS  read-only
   STATUS      current
   DESCRIPTION
      "Path: atm.status.pvcTable.ipV6.addresses.timers.prefLifeTime

       Time in centi-second."
   ::= {sr1645v2ATMStatIpV6AddressesEntry 100728832}


sr1645v2ATMVp OBJECT IDENTIFIER ::= {sr1645v2ATM 93}

sr1645v2ATMVpSSCTable OBJECT-TYPE
   SYNTAX      SEQUENCE OF Sr1645v2ATMVpEntry
   MAX-ACCESS  not-accessible
   STATUS      current
   DESCRIPTION
      ""
   ::= {sr1645v2ATMVp 1}

sr1645v2ATMVpEntry OBJECT-TYPE
   SYNTAX      Sr1645v2ATMVpEntry
   MAX-ACCESS  not-accessible
   STATUS      current
   DESCRIPTION
      ""
   INDEX      { sr1645v2ATMVpTableIx }
   ::= {sr1645v2ATMVpSSCTable 1}

Sr1645v2ATMVpEntry ::=
   SEQUENCE
      {
      sr1645v2ATMVpTableIx
         TableIndex,
      sr1645v2ATMVpVpi
         Integer32,
      sr1645v2ATMVpIfOperStatus
         INTEGER,
      sr1645v2ATMVpOamF4SegOamLB
         INTEGER,
      sr1645v2ATMVpOamF4SegOamCC
         INTEGER,
      sr1645v2ATMVpOamF4SegAis
         INTEGER,
      sr1645v2ATMVpOamF4SegRdi
         INTEGER,
      sr1645v2ATMVpOamF4EteOamLB
         INTEGER,
      sr1645v2ATMVpOamF4EteOamCC
         INTEGER,
      sr1645v2ATMVpOamF4EteAis
         INTEGER,
      sr1645v2ATMVpOamF4EteRdi
         INTEGER,
      sr1645v2ATMVpOamF4SegEP
         INTEGER,
      sr1645v2ATMVpOamF4CnxEP
         INTEGER
      }

sr1645v2ATMVpTableIx OBJECT-TYPE
   SYNTAX      TableIndex
   MAX-ACCESS  not-accessible
   STATUS      current
   DESCRIPTION
      ""
   ::= {sr1645v2ATMVpEntry 11}

sr1645v2ATMVpVpi OBJECT-TYPE
   SYNTAX      Integer32
   MAX-ACCESS  read-only
   STATUS      current
   DESCRIPTION
      "Path: atm.status.vp.vpi"
   ::= {sr1645v2ATMVpEntry 16777216}

sr1645v2ATMVpIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: atm.status.vp.ifOperStatus

       Possibilities:
               up   (1)
               down   (2)
               testing   (3)
               unknown   (4)
               dormant   (5)
               notPresent   (6)
               lowerLayerDown   (7)"
   ::= {sr1645v2ATMVpEntry 1795162112}

sr1645v2ATMVpOamF4SegOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.segment.oamLB

       Possibilities:
               ready   (0)
               waitActRes   (1)
               waitActCon   (2)
               waitDeactCon   (3)
               active   (4)
               deactivated   (5)"
   ::= {sr1645v2ATMVpEntry 33628160}

sr1645v2ATMVpOamF4SegOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.segment.oamCC

       Possibilities:
               ready   (0)
               waitActRes   (1)
               waitActCon   (2)
               waitDeactCon   (3)
               active   (4)
               deactivated   (5)"
   ::= {sr1645v2ATMVpEntry 33636352}

sr1645v2ATMVpOamF4SegAis OBJECT-TYPE
   SYNTAX      INTEGER
               {
               inactive (0),
               active (1)
               }
   MAX-ACCESS  read-only
   STATUS      current
   DESCRIPTION
      "Path: atm.status.vp.oamF4.segment.aisState

       Possibilities:
               inactive   (0)
               active   (1)"
   ::= {sr1645v2ATMVpEntry 33652736}

sr1645v2ATMVpOamF4SegRdi OBJECT-TYPE
   SYNTAX      INTEGER
               {
               inactive (0),
               active (1)
               }
   MAX-ACCESS  read-only
   STATUS      current
   DESCRIPTION
      "Path: atm.status.vp.oamF4.segment.rdiState

       Possibilities:
               inactive   (0)
               active   (1)"
   ::= {sr1645v2ATMVpEntry 33660928}

sr1645v2ATMVpOamF4EteOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.endToEnd.oamLB

       Possibilities:
               ready   (0)
               waitActRes   (1)
               waitActCon   (2)
               waitDeactCon   (3)
               active   (4)
               deactivated   (5)"
   ::= {sr1645v2ATMVpEntry 33693696}

sr1645v2ATMVpOamF4EteOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.endToEnd.oamCC

       Possibilities:
               ready   (0)
               waitActRes   (1)
               waitActCon   (2)
               waitDeactCon   (3)
               active   (4)
               deactivated   (5)"
   ::= {sr1645v2ATMVpEntry 33701888}

sr1645v2ATMVpOamF4EteAis OBJECT-TYPE
   SYNTAX      INTEGER
               {
               inactive (0),
               active (1)
               }
   MAX-ACCESS  read-only
   STATUS      current
   DESCRIPTION
      "Path: atm.status.vp.oamF4.endToEnd.aisState

       Possibilities:
               inactive   (0)
               active   (1)"
   ::= {sr1645v2ATMVpEntry 33718272}

sr1645v2ATMVpOamF4EteRdi OBJECT-TYPE
   SYNTAX      INTEGER
               {
               inactive (0),
               active (1)
               }
   MAX-ACCESS  read-only
   STATUS      current
   DESCRIPTION
      "Path: atm.status.vp.oamF4.endToEnd.rdiState

       Possibilities:
               inactive   (0)
               active   (1)"
   ::= {sr1645v2ATMVpEntry 33726464}

sr1645v2ATMVpOamF4SegEP OBJECT-TYPE
   SYNTAX      INTEGER
               {
               no (0),
               yes (1)
               }
   MAX-ACCESS  read-only
   STATUS      current
   DESCRIPTION
      "Path: atm.status.vp.oamF4.segmentEndPoint

       Possibilities:
               no   (0)
               yes   (1)"
   ::= {sr1645v2ATMVpEntry 33751040}

sr1645v2ATMVpOamF4CnxEP OBJECT-TYPE
   SYNTAX      INTEGER
               {
               no (0),
               yes (1)
               }
   MAX-ACCESS  read-only
   STATUS      current
   DESCRIPTION
      "Path: atm.status.vp.oamF4.connectionEndPoint

       Possibilities:
               no   (0)
               yes   (1)"
   ::= {sr1645v2ATMVpEntry 33816576}



ar1645v2ATM OBJECT IDENTIFIER ::= {r1645v2ATM 16}


ar1645v2ATMClearCounters OBJECT-TYPE
   SYNTAX      Integer32
   MAX-ACCESS  read-write
   STATUS      current
   DESCRIPTION
      "Path: atm.actions.clearCounters
       Info: reset counters"
   ::= {ar1645v2ATM 263}



pr1645v2ATM OBJECT IDENTIFIER ::= {r1645v2ATM 12}


pr1645v2ATMPer OBJECT IDENTIFIER ::= {pr1645v2ATM 3}

pr1645v2ATMPerSSCTable OBJECT-TYPE
   SYNTAX      SEQUENCE OF Pr1645v2ATMPerEntry
   MAX-ACCESS  not-accessible
   STATUS      current
   DESCRIPTION
      ""
   ::= {pr1645v2ATMPer 1}

pr1645v2ATMPerEntry OBJECT-TYPE
   SYNTAX      Pr1645v2ATMPerEntry
   MAX-ACCESS  not-accessible
   STATUS      current
   DESCRIPTION
      ""
   INDEX      { pr1645v2ATMPerTableIx }
   ::= {pr1645v2ATMPerSSCTable 1}

Pr1645v2ATMPerEntry ::=
   SEQUENCE
      {
      pr1645v2ATMPerTableIx
         TableIndex,
      pr1645v2ATMPerName
         DisplayString,
      pr1645v2ATMPerMCInOctets
         Counter64,
      pr1645v2ATMPerMCInUcast
         Counter64,
      pr1645v2ATMPerMCInNUcastPkts
         Counter64,
      pr1645v2ATMPerMCInBcastPkts
         Counter64,
      pr1645v2ATMPerMCInMcastPkts
         Counter64,
      pr1645v2ATMPerMCInDiscards
         Counter64,
      pr1645v2ATMPerMCInErrors
         Counter64,
      pr1645v2ATMPerMCInUnknownProtos
         Counter64,
      pr1645v2ATMPerMCInDropEx
         Counter64,
      pr1645v2ATMPerMCInDropNoMac
         Counter64,
      pr1645v2ATMPerMCInDropNUCast
         Counter64,
      pr1645v2ATMPerMCInDropFilter
         Counter64,
      pr1645v2ATMPerMCInBandwidth15sec
         Integer32,
      pr1645v2ATMPerMCInBandwidth30sec
         Integer32,
      pr1645v2ATMPerMCInBandwidth1min
         Integer32,
      pr1645v2ATMPerMCInBandwidth2min
         Integer32,
      pr1645v2ATMPerMCInBandwidth5min
         Integer32,
      pr1645v2ATMPerMCOutOctets
         Counter64,
      pr1645v2ATMPerMCOutUcastPkts
         Counter64,
      pr1645v2ATMPerMCOutNUcastPkts
         Counter64,
      pr1645v2ATMPerMCOutBcastPkts
         Counter64,
      pr1645v2ATMPerMCOutMcastPkts
         Counter64,
      pr1645v2ATMPerMCOutDiscards
         Counter64,
      pr1645v2ATMPerMCOutErrors
         Counter64,
      pr1645v2ATMPerMCOutQLen
         Counter32,
      pr1645v2ATMPerMCOutDropEx
         Counter64,
      pr1645v2ATMPerMCOutDropNoArp
         Counter64,
      pr1645v2ATMPerMCOutDropFilter
         Counter64,
      pr1645v2ATMPerMCOutBandwidth15sec
         Integer32,
      pr1645v2ATMPerMCOutBandwidth30sec
         Integer32,
      pr1645v2ATMPerMCOutBandwidth1min
         Integer32,
      pr1645v2ATMPerMCOutBandwidth2min
         Integer32,
      pr1645v2ATMPerMCOutBandwidth5min
         Integer32,
      pr1645v2ATMPerAtmVpi
         Integer32,
      pr1645v2ATMPerAtmVci
         Integer32,
      pr1645v2ATMPerAtmF5SegLbRx
         Gauge32,
      pr1645v2ATMPerAtmF5SegLbTx
         Gauge32,
      pr1645v2ATMPerAtmF5SegCcRx
         Gauge32,
      pr1645v2ATMPerAtmF5SegCcTx
         Gauge32,
      pr1645v2ATMPerAtmF5SegFpmRx
         Gauge32,
      pr1645v2ATMPerAtmF5SegFpmTx
         Gauge32,
      pr1645v2ATMPerAtmF5SegBrRx
         Gauge32,
      pr1645v2ATMPerAtmF5SegBrTx
         Gauge32,
      pr1645v2ATMPerAtmF5SegAdRx
         Gauge32,
      pr1645v2ATMPerAtmF5SegAdTx
         Gauge32,
      pr1645v2ATMPerAtmF5SegAisRx
         Gauge32,
      pr1645v2ATMPerAtmF5SegAisTx
         Gauge32,
      pr1645v2ATMPerAtmF5SegRdiRx
         Gauge32,
      pr1645v2ATMPerAtmF5SegRdiTx
         Gauge32,
      pr1645v2ATMPerAtmF5EteLbRx
         Gauge32,
      pr1645v2ATMPerAtmF5EteLbTx
         Gauge32,
      pr1645v2ATMPerAtmF5EteCcRx
         Gauge32,
      pr1645v2ATMPerAtmF5EteCcTx
         Gauge32,
      pr1645v2ATMPerAtmF5EteFpmRx
         Gauge32,
      pr1645v2ATMPerAtmF5EteFpmTx
         Gauge32,
      pr1645v2ATMPerAtmF5EteBrRx
         Gauge32,
      pr1645v2ATMPerAtmF5EteBrTx
         Gauge32,
      pr1645v2ATMPerAtmF5EteAdRx
         Gauge32,
      pr1645v2ATMPerAtmF5EteAdTx
         Gauge32,
      pr1645v2ATMPerAtmF5EteAisRx
         Gauge32,
      pr1645v2ATMPerAtmF5EteAisTx
         Gauge32,
      pr1645v2ATMPerAtmF5EteRdiRx
         Gauge32,
      pr1645v2ATMPerAtmF5EteRdiTx
         Gauge32,
      pr1645v2ATMPerAtmPppLinkMonitoringRequestsSent
         Gauge32,
      pr1645v2ATMPerAtmPppLinkMonitoringRepliesRcvd
         Gauge32,
      pr1645v2ATMPerAtmPppLinkMonitoringRequestsRcvd
         Gauge32,
      pr1645v2ATMPerAtmPppLinkMonitoringRepliesSent
         Gauge32
      }

pr1645v2ATMPerTableIx OBJECT-TYPE
   SYNTAX      TableIndex
   MAX-ACCESS  not-accessible
   STATUS      current
   DESCRIPTION
      ""
   ::= {pr1645v2ATMPerEntry 11}

pr1645v2ATMPerName OBJECT-TYPE
   SYNTAX      DisplayString
   MAX-ACCESS  read-only
   STATUS      current
   DESCRIPTION
      "Path: atm.performance.pvcTable.name"
   ::= {pr1645v2ATMPerEntry 16777216}

pr1645v2ATMPerMCInOctets OBJECT-TYPE
   SYNTAX      Counter64
   MAX-ACCESS  read-only
   STATUS      current
   DESCRIPTION
      "Path: atm.performance.pvcTable.mibCounters.ifInOctets

       64 bit unsigned wrappable counter."
   ::= {pr1645v2ATMPerEntry 40697856}

pr1645v2ATMPerMCInUcast OBJECT-TYPE
   SYNTAX      Counter64
   MAX-ACCESS  read-only
   STATUS      current
   DESCRIPTION
      "Path: atm.performance.pvcTable.mibCounters.ifInUcastPkts

       64 bit unsigned wrappable counter."
   ::= {pr1645v2ATMPerEntry 40763392}

pr1645v2ATMPerMCInNUcastPkts OBJECT-TYPE
   SYNTAX      Counter64
   MAX-ACCESS  read-only
   STATUS      current
   DESCRIPTION
      "Path: atm.performance.pvcTable.mibCounters.ifInNUcastPkts

       64 bit unsigned wrappable counter."
   ::= {pr1645v2ATMPerEntry 40828928}

pr1645v2ATMPerMCInBcastPkts OBJECT-TYPE
   SYNTAX      Counter64
   MAX-ACCESS  read-only
   STATUS      current
   DESCRIPTION
      "Path: atm.performance.pvcTable.mibCounters.ifInBcastPkts

       64 bit unsigned wrappable counter."
   ::= {pr1645v2ATMPerEntry 47382528}

pr1645v2ATMPerMCInMcastPkts OBJECT-TYPE
   SYNTAX      Counter64
   MAX-ACCESS  read-only
   STATUS      current
   DESCRIPTION
      "Path: atm.performance.pvcTable.mibCounters.ifInMcastPkts

       64 bit unsigned wrappable counter."
   ::= {pr1645v2ATMPerEntry 48037888}

pr1645v2ATMPerMCInDiscards OBJECT-TYPE
   SYNTAX      Counter64
   MAX-ACCESS  read-only
   STATUS      current
   DESCRIPTION
      "Path: atm.performance.pvcTable.mibCounters.ifInDiscards

       64 bit unsigned wrappable counter."
   ::= {pr1645v2ATMPerEntry 40894464}

pr1645v2ATMPerMCInErrors OBJECT-TYPE
   SYNTAX      Counter64
   MAX-ACCESS  read-only
   STATUS      current
   DESCRIPTION
      "Path: atm.performance.pvcTable.mibCounters.ifInErrors

       64 bit unsigned wrappable counter."
   ::= {pr1645v2ATMPerEntry 40960000}

pr1645v2ATMPerMCInUnknownProtos OBJECT-TYPE
   SYNTAX      Counter64
   MAX-ACCESS  read-only
   STATUS      current
   DESCRIPTION
      "Path: atm.performance.pvcTable.mibCounters.ifInUnknownProtos

       64 bit unsigned wrappable counter."
   ::= {pr1645v2ATMPerEntry 41025536}

pr1645v2ATMPerMCInDropEx OBJECT-TYPE
   SYNTAX      Counter64
   MAX-ACCESS  read-only
   STATUS      current
   DESCRIPTION
      "Path: atm.performance.pvcTable.mibCounters.ifInDropLevelExceeded

       64 bit unsigned wrappable counter."
   ::= {pr1645v2ATMPerEntry 42074112}

pr1645v2ATMPerMCInDropNoMac OBJECT-TYPE
   SYNTAX      Counter64
   MAX-ACCESS  read-only
   STATUS      current
   DESCRIPTION
      "Path: atm.performance.pvcTable.mibCounters.ifInDiscardsNoMacFit

       64 bit unsigned wrappable counter."
   ::= {pr1645v2ATMPerEntry 42270720}

pr1645v2ATMPerMCInDropNUCast OBJECT-TYPE
   SYNTAX      Counter64
   MAX-ACCESS  read-only
   STATUS      current
   DESCRIPTION
      "Path: atm.performance.pvcTable.mibCounters.ifInDiscardsNUCast

       64 bit unsigned wrappable counter."
   ::= {pr1645v2ATMPerEntry 42467328}

pr1645v2ATMPerMCInDropFilter OBJECT-TYPE
   SYNTAX      Counter64
   MAX-ACCESS  read-only
   STATUS      current
   DESCRIPTION
      "Path: atm.performance.pvcTable.mibCounters.ifInDiscardsFilter

       64 bit unsigned wrappable counter."
   ::= {pr1645v2ATMPerEntry 42532864}

pr1645v2ATMPerMCInBandwidth15sec OBJECT-TYPE
   SYNTAX      Integer32
   MAX-ACCESS  read-only
   STATUS      current
   DESCRIPTION
      "Path: atm.performance.pvcTable.mibCounters.ifInBandwidth.15sec

       unit name = bps
       formula = 8 * ; 8 /"
   ::= {pr1645v2ATMPerEntry 45417728}

pr1645v2ATMPerMCInBandwidth30sec OBJECT-TYPE
   SYNTAX      Integer32
   MAX-ACCESS  read-only
   STATUS      current
   DESCRIPTION
      "Path: atm.performance.pvcTable.mibCounters.ifInBandwidth.30sec

       unit name = bps
       formula = 8 * ; 8 /"
   ::= {pr1645v2ATMPerEntry 45419008}

pr1645v2ATMPerMCInBandwidth1min OBJECT-TYPE
   SYNTAX      Integer32
   MAX-ACCESS  read-only
   STATUS      current
   DESCRIPTION
      "Path: atm.performance.pvcTable.mibCounters.ifInBandwidth.1min

       unit name = bps
       formula = 8 * ; 8 /"
   ::= {pr1645v2ATMPerEntry 45421568}

pr1645v2ATMPerMCInBandwidth2min OBJECT-TYPE
   SYNTAX      Integer32
   MAX-ACCESS  read-only
   STATUS      current
   DESCRIPTION
      "Path: atm.performance.pvcTable.mibCounters.ifInBandwidth.2min

       unit name = bps
       formula = 8 * ; 8 /"
   ::= {pr1645v2ATMPerEntry 45426688}

pr1645v2ATMPerMCInBandwidth5min OBJECT-TYPE
   SYNTAX      Integer32
   MAX-ACCESS  read-only
   STATUS      current
   DESCRIPTION
      "Path: atm.performance.pvcTable.mibCounters.ifInBandwidth.5min

       unit name = bps
       formula = 8 * ; 8 /"
   ::= {pr1645v2ATMPerEntry 45442048}

pr1645v2ATMPerMCOutOctets OBJECT-TYPE
   SYNTAX      Counter64
   MAX-ACCESS  read-only
   STATUS      current
   DESCRIPTION
      "Path: atm.performance.pvcTable.mibCounters.ifOutOctets

       64 bit unsigned wrappable counter."
   ::= {pr1645v2ATMPerEntry 41091072}

pr1645v2ATMPerMCOutUcastPkts OBJECT-TYPE
   SYNTAX      Counter64
   MAX-ACCESS  read-only
   STATUS      current
   DESCRIPTION
      "Path: atm.performance.pvcTable.mibCounters.ifOutUcastPkts

       64 bit unsigned wrappable counter."
   ::= {pr1645v2ATMPerEntry 41156608}

pr1645v2ATMPerMCOutNUcastPkts OBJECT-TYPE
   SYNTAX      Counter64
   MAX-ACCESS  read-only
   STATUS      current
   DESCRIPTION
      "Path: atm.performance.pvcTable.mibCounters.ifOutNUcastPkts

       64 bit unsigned wrappable counter."
   ::= {pr1645v2ATMPerEntry 41222144}

pr1645v2ATMPerMCOutBcastPkts OBJECT-TYPE
   SYNTAX      Counter64
   MAX-ACCESS  read-only
   STATUS      current
   DESCRIPTION
      "Path: atm.performance.pvcTable.mibCounters.ifOutBcastPkts

       64 bit unsigned wrappable counter."
   ::= {pr1645v2ATMPerEntry 47775744}

pr1645v2ATMPerMCOutMcastPkts OBJECT-TYPE
   SYNTAX      Counter64
   MAX-ACCESS  read-only
   STATUS      current
   DESCRIPTION
      "Path: atm.performance.pvcTable.mibCounters.ifOutMcastPkts

       64 bit unsigned wrappable counter."
   ::= {pr1645v2ATMPerEntry 48431104}

pr1645v2ATMPerMCOutDiscards OBJECT-TYPE
   SYNTAX      Counter64
   MAX-ACCESS  read-only
   STATUS      current
   DESCRIPTION
      "Path: atm.performance.pvcTable.mibCounters.ifOutDiscards

       64 bit unsigned wrappable counter."
   ::= {pr1645v2ATMPerEntry 41287680}

pr1645v2ATMPerMCOutErrors OBJECT-TYPE
   SYNTAX      Counter64
   MAX-ACCESS  read-only
   STATUS      current
   DESCRIPTION
      "Path: atm.performance.pvcTable.mibCounters.ifOutErrors

       64 bit unsigned wrappable counter."
   ::= {pr1645v2ATMPerEntry 41353216}

pr1645v2ATMPerMCOutQLen OBJECT-TYPE
   SYNTAX      Counter32
   MAX-ACCESS  read-only
   STATUS      current
   DESCRIPTION
      "Path: atm.performance.pvcTable.mibCounters.ifOutQLen

       32 bit unsigned wrappable counter."
   ::= {pr1645v2ATMPerEntry 41418752}

pr1645v2ATMPerMCOutDropEx OBJECT-TYPE
   SYNTAX      Counter64
   MAX-ACCESS  read-only
   STATUS      current
   DESCRIPTION
      "Path: atm.performance.pvcTable.mibCounters.ifOutDropLevelExceeded

       64 bit unsigned wrappable counter."
   ::= {pr1645v2ATMPerEntry 41484288}

pr1645v2ATMPerMCOutDropNoArp OBJECT-TYPE
   SYNTAX      Counter64
   MAX-ACCESS  read-only
   STATUS      current
   DESCRIPTION
      "Path: atm.performance.pvcTable.mibCounters.ifOutDiscardsNoArp

       64 bit unsigned wrappable counter."
   ::= {pr1645v2ATMPerEntry 42336256}

pr1645v2ATMPerMCOutDropFilter OBJECT-TYPE
   SYNTAX      Counter64
   MAX-ACCESS  read-only
   STATUS      current
   DESCRIPTION
      "Path: atm.performance.pvcTable.mibCounters.ifOutDiscardsFilter

       64 bit unsigned wrappable counter."
   ::= {pr1645v2ATMPerEntry 42598400}

pr1645v2ATMPerMCOutBandwidth15sec OBJECT-TYPE
   SYNTAX      Integer32
   MAX-ACCESS  read-only
   STATUS      current
   DESCRIPTION
      "Path: atm.performance.pvcTable.mibCounters.ifOutBandwidth.15sec

       unit name = bps
       formula = 8 * ; 8 /"
   ::= {pr1645v2ATMPerEntry 45483264}

pr1645v2ATMPerMCOutBandwidth30sec OBJECT-TYPE
   SYNTAX      Integer32
   MAX-ACCESS  read-only
   STATUS      current
   DESCRIPTION
      "Path: atm.performance.pvcTable.mibCounters.ifOutBandwidth.30sec

       unit name = bps
       formula = 8 * ; 8 /"
   ::= {pr1645v2ATMPerEntry 45484544}

pr1645v2ATMPerMCOutBandwidth1min OBJECT-TYPE
   SYNTAX      Integer32
   MAX-ACCESS  read-only
   STATUS      current
   DESCRIPTION
      "Path: atm.performance.pvcTable.mibCounters.ifOutBandwidth.1min

       unit name = bps
       formula = 8 * ; 8 /"
   ::= {pr1645v2ATMPerEntry 45487104}

pr1645v2ATMPerMCOutBandwidth2min OBJECT-TYPE
   SYNTAX      Integer32
   MAX-ACCESS  read-only
   STATUS      current
   DESCRIPTION
      "Path: atm.performance.pvcTable.mibCounters.ifOutBandwidth.2min

       unit name = bps
       formula = 8 * ; 8 /"
   ::= {pr1645v2ATMPerEntry 45492224}

pr1645v2ATMPerMCOutBandwidth5min OBJECT-TYPE
   SYNTAX      Integer32
   MAX-ACCESS  read-only
   STATUS      current
   DESCRIPTION
      "Path: atm.performance.pvcTable.mibCounters.ifOutBandwidth.5min

       unit name = bps
       formula = 8 * ; 8 /"
   ::= {pr1645v2ATMPerEntry 45507584}

pr1645v2ATMPerAtmVpi OBJECT-TYPE
   SYNTAX      Integer32
   MAX-ACCESS  read-only
   STATUS      current
   DESCRIPTION
      "Path: atm.performance.pvcTable.atm.vpi"
   ::= {pr1645v2ATMPerEntry 286261248}

pr1645v2ATMPerAtmVci OBJECT-TYPE
   SYNTAX      Integer32
   MAX-ACCESS  read-only
   STATUS      current
   DESCRIPTION
      "Path: atm.performance.pvcTable.atm.vci"
   ::= {pr1645v2ATMPerEntry 287309824}

pr1645v2ATMPerAtmF5SegLbRx OBJECT-TYPE
   SYNTAX      Gauge32
   MAX-ACCESS  read-only
   STATUS      current
   DESCRIPTION
      "Path: atm.performance.pvcTable.atm.oamF5.segment.lbRx

       32 bit unsigned gauge value."
   ::= {pr1645v2ATMPerEntry 288493568}

pr1645v2ATMPerAtmF5SegLbTx OBJECT-TYPE
   SYNTAX      Gauge32
   MAX-ACCESS  read-only
   STATUS      current
   DESCRIPTION
      "Path: atm.performance.pvcTable.atm.oamF5.segment.lbTx

       32 bit unsigned gauge value."
   ::= {pr1645v2ATMPerEntry 288497664}

pr1645v2ATMPerAtmF5SegCcRx OBJECT-TYPE
   SYNTAX      Gauge32
   MAX-ACCESS  read-only
   STATUS      current
   DESCRIPTION
      "Path: atm.performance.pvcTable.atm.oamF5.segment.ccRx

       32 bit unsigned gauge value."
   ::= {pr1645v2ATMPerEntry 288501760}

pr1645v2ATMPerAtmF5SegCcTx OBJECT-TYPE
   SYNTAX      Gauge32
   MAX-ACCESS  read-only
   STATUS      current
   DESCRIPTION
      "Path: atm.performance.pvcTable.atm.oamF5.segment.ccTx

       32 bit unsigned gauge value."
   ::= {pr1645v2ATMPerEntry 288505856}

pr1645v2ATMPerAtmF5SegFpmRx OBJECT-TYPE
   SYNTAX      Gauge32
   MAX-ACCESS  read-only
   STATUS      current
   DESCRIPTION
      "Path: atm.performance.pvcTable.atm.oamF5.segment.fpmRx

       32 bit unsigned gauge value."
   ::= {pr1645v2ATMPerEntry 288509952}

pr1645v2ATMPerAtmF5SegFpmTx OBJECT-TYPE
   SYNTAX      Gauge32
   MAX-ACCESS  read-only
   STATUS      current
   DESCRIPTION
      "Path: atm.performance.pvcTable.atm.oamF5.segment.fpmTx

       32 bit unsigned gauge value."
   ::= {pr1645v2ATMPerEntry 288514048}

pr1645v2ATMPerAtmF5SegBrRx OBJECT-TYPE
   SYNTAX      Gauge32
   MAX-ACCESS  read-only
   STATUS      current
   DESCRIPTION
      "Path: atm.performance.pvcTable.atm.oamF5.segment.brRx

       32 bit unsigned gauge value."
   ::= {pr1645v2ATMPerEntry 288518144}

pr1645v2ATMPerAtmF5SegBrTx OBJECT-TYPE
   SYNTAX      Gauge32
   MAX-ACCESS  read-only
   STATUS      current
   DESCRIPTION
      "Path: atm.performance.pvcTable.atm.oamF5.segment.brTx

       32 bit unsigned gauge value."
   ::= {pr1645v2ATMPerEntry 288522240}

pr1645v2ATMPerAtmF5SegAdRx OBJECT-TYPE
   SYNTAX      Gauge32
   MAX-ACCESS  read-only
   STATUS      current
   DESCRIPTION
      "Path: atm.performance.pvcTable.atm.oamF5.segment.actDeactRx

       32 bit unsigned gauge value."
   ::= {pr1645v2ATMPerEntry 288526336}

pr1645v2ATMPerAtmF5SegAdTx OBJECT-TYPE
   SYNTAX      Gauge32
   MAX-ACCESS  read-only
   STATUS      current
   DESCRIPTION
      "Path: atm.performance.pvcTable.atm.oamF5.segment.actDeactTx

       32 bit unsigned gauge value."
   ::= {pr1645v2ATMPerEntry 288530432}

pr1645v2ATMPerAtmF5SegAisRx OBJECT-TYPE
   SYNTAX      Gauge32
   MAX-ACCESS  read-only
   STATUS      current
   DESCRIPTION
      "Path: atm.performance.pvcTable.atm.oamF5.segment.aisRx

       32 bit unsigned gauge value."
   ::= {pr1645v2ATMPerEntry 288534528}

pr1645v2ATMPerAtmF5SegAisTx OBJECT-TYPE
   SYNTAX      Gauge32
   MAX-ACCESS  read-only
   STATUS      current
   DESCRIPTION
      "Path: atm.performance.pvcTable.atm.oamF5.segment.aisTx

       32 bit unsigned gauge value."
   ::= {pr1645v2ATMPerEntry 288538624}

pr1645v2ATMPerAtmF5SegRdiRx OBJECT-TYPE
   SYNTAX      Gauge32
   MAX-ACCESS  read-only
   STATUS      current
   DESCRIPTION
      "Path: atm.performance.pvcTable.atm.oamF5.segment.rdiRx

       32 bit unsigned gauge value."
   ::= {pr1645v2ATMPerEntry 288542720}

pr1645v2ATMPerAtmF5SegRdiTx OBJECT-TYPE
   SYNTAX      Gauge32
   MAX-ACCESS  read-only
   STATUS      current
   DESCRIPTION
      "Path: atm.performance.pvcTable.atm.oamF5.segment.rdiTx

       32 bit unsigned gauge value."
   ::= {pr1645v2ATMPerEntry 288546816}

pr1645v2ATMPerAtmF5EteLbRx OBJECT-TYPE
   SYNTAX      Gauge32
   MAX-ACCESS  read-only
   STATUS      current
   DESCRIPTION
      "Path: atm.performance.pvcTable.atm.oamF5.endToEnd.lbRx

       32 bit unsigned gauge value."
   ::= {pr1645v2ATMPerEntry 288624640}

pr1645v2ATMPerAtmF5EteLbTx OBJECT-TYPE
   SYNTAX      Gauge32
   MAX-ACCESS  read-only
   STATUS      current
   DESCRIPTION
      "Path: atm.performance.pvcTable.atm.oamF5.endToEnd.lbTx

       32 bit unsigned gauge value."
   ::= {pr1645v2ATMPerEntry 288628736}

pr1645v2ATMPerAtmF5EteCcRx OBJECT-TYPE
   SYNTAX      Gauge32
   MAX-ACCESS  read-only
   STATUS      current
   DESCRIPTION
      "Path: atm.performance.pvcTable.atm.oamF5.endToEnd.ccRx

       32 bit unsigned gauge value."
   ::= {pr1645v2ATMPerEntry 288632832}

pr1645v2ATMPerAtmF5EteCcTx OBJECT-TYPE
   SYNTAX      Gauge32
   MAX-ACCESS  read-only
   STATUS      current
   DESCRIPTION
      "Path: atm.performance.pvcTable.atm.oamF5.endToEnd.ccTx

       32 bit unsigned gauge value."
   ::= {pr1645v2ATMPerEntry 288636928}

pr1645v2ATMPerAtmF5EteFpmRx OBJECT-TYPE
   SYNTAX      Gauge32
   MAX-ACCESS  read-only
   STATUS      current
   DESCRIPTION
      "Path: atm.performance.pvcTable.atm.oamF5.endToEnd.fpmRx

       32 bit unsigned gauge value."
   ::= {pr1645v2ATMPerEntry 288641024}

pr1645v2ATMPerAtmF5EteFpmTx OBJECT-TYPE
   SYNTAX      Gauge32
   MAX-ACCESS  read-only
   STATUS      current
   DESCRIPTION
      "Path: atm.performance.pvcTable.atm.oamF5.endToEnd.fpmTx

       32 bit unsigned gauge value."
   ::= {pr1645v2ATMPerEntry 288645120}

pr1645v2ATMPerAtmF5EteBrRx OBJECT-TYPE
   SYNTAX      Gauge32
   MAX-ACCESS  read-only
   STATUS      current
   DESCRIPTION
      "Path: atm.performance.pvcTable.atm.oamF5.endToEnd.brRx

       32 bit unsigned gauge value."
   ::= {pr1645v2ATMPerEntry 288649216}

pr1645v2ATMPerAtmF5EteBrTx OBJECT-TYPE
   SYNTAX      Gauge32
   MAX-ACCESS  read-only
   STATUS      current
   DESCRIPTION
      "Path: atm.performance.pvcTable.atm.oamF5.endToEnd.brTx

       32 bit unsigned gauge value."
   ::= {pr1645v2ATMPerEntry 288653312}

pr1645v2ATMPerAtmF5EteAdRx OBJECT-TYPE
   SYNTAX      Gauge32
   MAX-ACCESS  read-only
   STATUS      current
   DESCRIPTION
      "Path: atm.performance.pvcTable.atm.oamF5.endToEnd.actDeactRx

       32 bit unsigned gauge value."
   ::= {pr1645v2ATMPerEntry 288657408}

pr1645v2ATMPerAtmF5EteAdTx OBJECT-TYPE
   SYNTAX      Gauge32
   MAX-ACCESS  read-only
   STATUS      current
   DESCRIPTION
      "Path: atm.performance.pvcTable.atm.oamF5.endToEnd.actDeactTx

       32 bit unsigned gauge value."
   ::= {pr1645v2ATMPerEntry 288661504}

pr1645v2ATMPerAtmF5EteAisRx OBJECT-TYPE
   SYNTAX      Gauge32
   MAX-ACCESS  read-only
   STATUS      current
   DESCRIPTION
      "Path: atm.performance.pvcTable.atm.oamF5.endToEnd.aisRx

       32 bit unsigned gauge value."
   ::= {pr1645v2ATMPerEntry 288665600}

pr1645v2ATMPerAtmF5EteAisTx OBJECT-TYPE
   SYNTAX      Gauge32
   MAX-ACCESS  read-only
   STATUS      current
   DESCRIPTION
      "Path: atm.performance.pvcTable.atm.oamF5.endToEnd.aisTx

       32 bit unsigned gauge value."
   ::= {pr1645v2ATMPerEntry 288669696}

pr1645v2ATMPerAtmF5EteRdiRx OBJECT-TYPE
   SYNTAX      Gauge32
   MAX-ACCESS  read-only
   STATUS      current
   DESCRIPTION
      "Path: atm.performance.pvcTable.atm.oamF5.endToEnd.rdiRx

       32 bit unsigned gauge value."
   ::= {pr1645v2ATMPerEntry 288673792}

pr1645v2ATMPerAtmF5EteRdiTx OBJECT-TYPE
   SYNTAX      Gauge32
   MAX-ACCESS  read-only
   STATUS      current
   DESCRIPTION
      "Path: atm.performance.pvcTable.atm.oamF5.endToEnd.rdiTx

       32 bit unsigned gauge value."
   ::= {pr1645v2ATMPerEntry 288677888}

pr1645v2ATMPerAtmPppLinkMonitoringRequestsSent OBJECT-TYPE
   SYNTAX      Gauge32
   MAX-ACCESS  read-only
   STATUS      current
   DESCRIPTION
      "Path: atm.performance.pvcTable.atm.ppp.linkMonitoring.requestsSent

       32 bit unsigned gauge value."
   ::= {pr1645v2ATMPerEntry 289411088}

pr1645v2ATMPerAtmPppLinkMonitoringRepliesRcvd OBJECT-TYPE
   SYNTAX      Gauge32
   MAX-ACCESS  read-only
   STATUS      current
   DESCRIPTION
      "Path: atm.performance.pvcTable.atm.ppp.linkMonitoring.repliesRcvd

       32 bit unsigned gauge value."
   ::= {pr1645v2ATMPerEntry 289411104}

pr1645v2ATMPerAtmPppLinkMonitoringRequestsRcvd OBJECT-TYPE
   SYNTAX      Gauge32
   MAX-ACCESS  read-only
   STATUS      current
   DESCRIPTION
      "Path: atm.performance.pvcTable.atm.ppp.linkMonitoring.requestsRcvd

       32 bit unsigned gauge value."
   ::= {pr1645v2ATMPerEntry 289411120}

pr1645v2ATMPerAtmPppLinkMonitoringRepliesSent OBJECT-TYPE
   SYNTAX      Gauge32
   MAX-ACCESS  read-only
   STATUS      current
   DESCRIPTION
      "Path: atm.performance.pvcTable.atm.ppp.linkMonitoring.repliesSent

       32 bit unsigned gauge value."
   ::= {pr1645v2ATMPerEntry 289411136}

pr1645v2ATMPerMCH2P OBJECT-TYPE
   SYNTAX      SEQUENCE OF Pr1645v2ATMPerMCH2PEntry
   MAX-ACCESS  not-accessible
   STATUS      current
   DESCRIPTION
      ""
   ::= {pr1645v2ATMPer 41549824}

pr1645v2ATMPerMCH2PEntry OBJECT-TYPE
   SYNTAX      Pr1645v2ATMPerMCH2PEntry
   MAX-ACCESS  not-accessible
   STATUS      current
   DESCRIPTION
      ""
   INDEX      { pr1645v2ATMPerTableIx,
                pr1645v2ATMPerMCH2PTableIx }
   ::= {pr1645v2ATMPerMCH2P 1}

Pr1645v2ATMPerMCH2PEntry ::=
   SEQUENCE
      {
      pr1645v2ATMPerMCH2PTableIx
         TableIndex,
      pr1645v2ATMPerMCH2PSysUpTime
         TimeTicks,
      pr1645v2ATMPerMCH2PIfUpTime
         TimeTicks,
      pr1645v2ATMPerMCH2PIfStatChanges
         Counter32,
      pr1645v2ATMPerMCH2PIfInOctets
         Counter64,
      pr1645v2ATMPerMCH2PIfInUCPkts
         Counter64,
      pr1645v2ATMPerMCH2PIfInNUCPkts
         Counter64,
      pr1645v2ATMPerMCH2PIfInBCPkts
         Counter64,
      pr1645v2ATMPerMCH2PIfInMCPkts
         Counter64,
      pr1645v2ATMPerMCH2PIfInDiscards
         Counter64,
      pr1645v2ATMPerMCH2PIfInErrors
         Counter64,
      pr1645v2ATMPerMCH2PIfInUnkwn
         Counter64,
      pr1645v2ATMPerMCH2PInDropEx
         Counter64,
      pr1645v2ATMPerMCH2PInDropNoMac
         Counter64,
      pr1645v2ATMPerMCH2PInDropNUCast
         Counter64,
      pr1645v2ATMPerMCH2PInDropFilter
         Counter64,
      pr1645v2ATMPerMCH2PIfInBandwidth
         Integer32,
      pr1645v2ATMPerMCH2PIfOutOctets
         Counter64,
      pr1645v2ATMPerMCH2PIfOutUCPkts
         Counter64,
      pr1645v2ATMPerMCH2PIfOutNUCPkts
         Counter64,
      pr1645v2ATMPerMCH2PIfOutBCPkts
         Counter64,
      pr1645v2ATMPerMCH2PIfOutMCPkts
         Counter64,
      pr1645v2ATMPerMCH2PIfOutDiscards
         Counter64,
      pr1645v2ATMPerMCH2PIfOutErrors
         Counter64,
      pr1645v2ATMPerMCH2POutDropEx
         Counter64,
      pr1645v2ATMPerMCH2POutDropNoArp
         Counter64,
      pr1645v2ATMPerMCH2POutDropFilter
         Counter64,
      pr1645v2ATMPerMCH2PIfOutBandwidth
         Integer32,
      pr1645v2ATMPerMCH2PIfErrSec
         Counter32
      }

pr1645v2ATMPerMCH2PTableIx OBJECT-TYPE
   SYNTAX      TableIndex
   MAX-ACCESS  not-accessible
   STATUS      current
   DESCRIPTION
      ""
   ::= {pr1645v2ATMPerMCH2PEntry 11}

pr1645v2ATMPerMCH2PSysUpTime OBJECT-TYPE
   SYNTAX      TimeTicks
   MAX-ACCESS  read-only
   STATUS      current
   DESCRIPTION
      "Path: atm.performance.pvcTable.mibCounters.h2Performance.sysUpTime

       Time in centi-second."
   ::= {pr1645v2ATMPerMCH2PEntry 16777216}

pr1645v2ATMPerMCH2PIfUpTime OBJECT-TYPE
   SYNTAX      TimeTicks
   MAX-ACCESS  read-only
   STATUS      current
   DESCRIPTION
      "Path: atm.performance.pvcTable.mibCounters.h2Performance.ifUpTime

       Time in centi-second."
   ::= {pr1645v2ATMPerMCH2PEntry 33554432}

pr1645v2ATMPerMCH2PIfStatChanges OBJECT-TYPE
   SYNTAX      Counter32
   MAX-ACCESS  read-only
   STATUS      current
   DESCRIPTION
      "Path: atm.performance.pvcTable.mibCounters.h2Performance.ifStatusChanges

       32 bit unsigned wrappable counter."
   ::= {pr1645v2ATMPerMCH2PEntry 50331648}

pr1645v2ATMPerMCH2PIfInOctets OBJECT-TYPE
   SYNTAX      Counter64
   MAX-ACCESS  read-only
   STATUS      current
   DESCRIPTION
      "Path: atm.performance.pvcTable.mibCounters.h2Performance.ifInOctets

       64 bit unsigned wrappable counter."
   ::= {pr1645v2ATMPerMCH2PEntry 67108864}

pr1645v2ATMPerMCH2PIfInUCPkts OBJECT-TYPE
   SYNTAX      Counter64
   MAX-ACCESS  read-only
   STATUS      current
   DESCRIPTION
      "Path: atm.performance.pvcTable.mibCounters.h2Performance.ifInUcastPkts

       64 bit unsigned wrappable counter."
   ::= {pr1645v2ATMPerMCH2PEntry 83886080}

pr1645v2ATMPerMCH2PIfInNUCPkts OBJECT-TYPE
   SYNTAX      Counter64
   MAX-ACCESS  read-only
   STATUS      current
   DESCRIPTION
      "Path: atm.performance.pvcTable.mibCounters.h2Performance.ifInNUcastPkts

       64 bit unsigned wrappable counter."
   ::= {pr1645v2ATMPerMCH2PEntry 100663296}

pr1645v2ATMPerMCH2PIfInBCPkts OBJECT-TYPE
   SYNTAX      Counter64
   MAX-ACCESS  read-only
   STATUS      current
   DESCRIPTION
      "Path: atm.performance.pvcTable.mibCounters.h2Performance.ifInBcastPkts

       64 bit unsigned wrappable counter."
   ::= {pr1645v2ATMPerMCH2PEntry 419430400}

pr1645v2ATMPerMCH2PIfInMCPkts OBJECT-TYPE
   SYNTAX      Counter64
   MAX-ACCESS  read-only
   STATUS      current
   DESCRIPTION
      "Path: atm.performance.pvcTable.mibCounters.h2Performance.ifInMcastPkts

       64 bit unsigned wrappable counter."
   ::= {pr1645v2ATMPerMCH2PEntry 436207616}

pr1645v2ATMPerMCH2PIfInDiscards OBJECT-TYPE
   SYNTAX      Counter64
   MAX-ACCESS  read-only
   STATUS      current
   DESCRIPTION
      "Path: atm.performance.pvcTable.mibCounters.h2Performance.ifInDiscards

       64 bit unsigned wrappable counter."
   ::= {pr1645v2ATMPerMCH2PEntry 117440512}

pr1645v2ATMPerMCH2PIfInErrors OBJECT-TYPE
   SYNTAX      Counter64
   MAX-ACCESS  read-only
   STATUS      current
   DESCRIPTION
      "Path: atm.performance.pvcTable.mibCounters.h2Performance.ifInErrors

       64 bit unsigned wrappable counter."
   ::= {pr1645v2ATMPerMCH2PEntry 134217728}

pr1645v2ATMPerMCH2PIfInUnkwn OBJECT-TYPE
   SYNTAX      Counter64
   MAX-ACCESS  read-only
   STATUS      current
   DESCRIPTION
      "Path: atm.performance.pvcTable.mibCounters.h2Performance.ifInUnknownProtos

       64 bit unsigned wrappable counter."
   ::= {pr1645v2ATMPerMCH2PEntry 150994944}

pr1645v2ATMPerMCH2PInDropEx OBJECT-TYPE
   SYNTAX      Counter64
   MAX-ACCESS  read-only
   STATUS      current
   DESCRIPTION
      "Path: atm.performance.pvcTable.mibCounters.h2Performance.ifInDropLevelExceeded

       64 bit unsigned wrappable counter."
   ::= {pr1645v2ATMPerMCH2PEntry 335544320}

pr1645v2ATMPerMCH2PInDropNoMac OBJECT-TYPE
   SYNTAX      Counter64
   MAX-ACCESS  read-only
   STATUS      current
   DESCRIPTION
      "Path: atm.performance.pvcTable.mibCounters.h2Performance.fInDiscardsNoMacFit

       64 bit unsigned wrappable counter."
   ::= {pr1645v2ATMPerMCH2PEntry 301989888}

pr1645v2ATMPerMCH2PInDropNUCast OBJECT-TYPE
   SYNTAX      Counter64
   MAX-ACCESS  read-only
   STATUS      current
   DESCRIPTION
      "Path: atm.performance.pvcTable.mibCounters.h2Performance.fInDiscardsNUCast

       64 bit unsigned wrappable counter."
   ::= {pr1645v2ATMPerMCH2PEntry 318767104}

pr1645v2ATMPerMCH2PInDropFilter OBJECT-TYPE
   SYNTAX      Counter64
   MAX-ACCESS  read-only
   STATUS      current
   DESCRIPTION
      "Path: atm.performance.pvcTable.mibCounters.h2Performance.fInDiscardsFilter

       64 bit unsigned wrappable counter."
   ::= {pr1645v2ATMPerMCH2PEntry 385875968}

pr1645v2ATMPerMCH2PIfInBandwidth OBJECT-TYPE
   SYNTAX      Integer32
   MAX-ACCESS  read-only
   STATUS      current
   DESCRIPTION
      "Path: atm.performance.pvcTable.mibCounters.h2Performance.ifInBandwidth

       unit name = bps
       formula = 8 * ; 8 /"
   ::= {pr1645v2ATMPerMCH2PEntry 268435456}

pr1645v2ATMPerMCH2PIfOutOctets OBJECT-TYPE
   SYNTAX      Counter64
   MAX-ACCESS  read-only
   STATUS      current
   DESCRIPTION
      "Path: atm.performance.pvcTable.mibCounters.h2Performance.ifOutOctets

       64 bit unsigned wrappable counter."
   ::= {pr1645v2ATMPerMCH2PEntry 167772160}

pr1645v2ATMPerMCH2PIfOutUCPkts OBJECT-TYPE
   SYNTAX      Counter64
   MAX-ACCESS  read-only
   STATUS      current
   DESCRIPTION
      "Path: atm.performance.pvcTable.mibCounters.h2Performance.ifOutUcastPkts

       64 bit unsigned wrappable counter."
   ::= {pr1645v2ATMPerMCH2PEntry 184549376}

pr1645v2ATMPerMCH2PIfOutNUCPkts OBJECT-TYPE
   SYNTAX      Counter64
   MAX-ACCESS  read-only
   STATUS      current
   DESCRIPTION
      "Path: atm.performance.pvcTable.mibCounters.h2Performance.ifOutNUcastPkts

       64 bit unsigned wrappable counter."
   ::= {pr1645v2ATMPerMCH2PEntry 201326592}

pr1645v2ATMPerMCH2PIfOutBCPkts OBJECT-TYPE
   SYNTAX      Counter64
   MAX-ACCESS  read-only
   STATUS      current
   DESCRIPTION
      "Path: atm.performance.pvcTable.mibCounters.h2Performance.ifOutBcastPkts

       64 bit unsigned wrappable counter."
   ::= {pr1645v2ATMPerMCH2PEntry 452984832}

pr1645v2ATMPerMCH2PIfOutMCPkts OBJECT-TYPE
   SYNTAX      Counter64
   MAX-ACCESS  read-only
   STATUS      current
   DESCRIPTION
      "Path: atm.performance.pvcTable.mibCounters.h2Performance.ifOutMcastPkts

       64 bit unsigned wrappable counter."
   ::= {pr1645v2ATMPerMCH2PEntry 469762048}

pr1645v2ATMPerMCH2PIfOutDiscards OBJECT-TYPE
   SYNTAX      Counter64
   MAX-ACCESS  read-only
   STATUS      current
   DESCRIPTION
      "Path: atm.performance.pvcTable.mibCounters.h2Performance.ifOutDiscards

       64 bit unsigned wrappable counter."
   ::= {pr1645v2ATMPerMCH2PEntry 218103808}

pr1645v2ATMPerMCH2PIfOutErrors OBJECT-TYPE
   SYNTAX      Counter64
   MAX-ACCESS  read-only
   STATUS      current
   DESCRIPTION
      "Path: atm.performance.pvcTable.mibCounters.h2Performance.ifOutErrors

       64 bit unsigned wrappable counter."
   ::= {pr1645v2ATMPerMCH2PEntry 234881024}

pr1645v2ATMPerMCH2POutDropEx OBJECT-TYPE
   SYNTAX      Counter64
   MAX-ACCESS  read-only
   STATUS      current
   DESCRIPTION
      "Path: atm.performance.pvcTable.mibCounters.h2Performance.ifOutDropLevelExceeded

       64 bit unsigned wrappable counter."
   ::= {pr1645v2ATMPerMCH2PEntry 352321536}

pr1645v2ATMPerMCH2POutDropNoArp OBJECT-TYPE
   SYNTAX      Counter64
   MAX-ACCESS  read-only
   STATUS      current
   DESCRIPTION
      "Path: atm.performance.pvcTable.mibCounters.h2Performance.ifOutDiscardsNoArp

       64 bit unsigned wrappable counter."
   ::= {pr1645v2ATMPerMCH2PEntry 369098752}

pr1645v2ATMPerMCH2POutDropFilter OBJECT-TYPE
   SYNTAX      Counter64
   MAX-ACCESS  read-only
   STATUS      current
   DESCRIPTION
      "Path: atm.performance.pvcTable.mibCounters.h2Performance.ifOutDiscardsFilter

       64 bit unsigned wrappable counter."
   ::= {pr1645v2ATMPerMCH2PEntry 402653184}

pr1645v2ATMPerMCH2PIfOutBandwidth OBJECT-TYPE
   SYNTAX      Integer32
   MAX-ACCESS  read-only
   STATUS      current
   DESCRIPTION
      "Path: atm.performance.pvcTable.mibCounters.h2Performance.ifOutBandwidth

       unit name = bps
       formula = 8 * ; 8 /"
   ::= {pr1645v2ATMPerMCH2PEntry 285212672}

pr1645v2ATMPerMCH2PIfErrSec OBJECT-TYPE
   SYNTAX      Counter32
   MAX-ACCESS  read-only
   STATUS      current
   DESCRIPTION
      "Path: atm.performance.pvcTable.mibCounters.h2Performance.ifErrSec

       32 bit unsigned wrappable counter."
   ::= {pr1645v2ATMPerMCH2PEntry 251658240}

pr1645v2ATMPerMCH24P OBJECT-TYPE
   SYNTAX      SEQUENCE OF Pr1645v2ATMPerMCH24PEntry
   MAX-ACCESS  not-accessible
   STATUS      current
   DESCRIPTION
      ""
   ::= {pr1645v2ATMPer 41615360}

pr1645v2ATMPerMCH24PEntry OBJECT-TYPE
   SYNTAX      Pr1645v2ATMPerMCH24PEntry
   MAX-ACCESS  not-accessible
   STATUS      current
   DESCRIPTION
      ""
   INDEX      { pr1645v2ATMPerTableIx,
                pr1645v2ATMPerMCH24PTableIx }
   ::= {pr1645v2ATMPerMCH24P 1}

Pr1645v2ATMPerMCH24PEntry ::=
   SEQUENCE
      {
      pr1645v2ATMPerMCH24PTableIx
         TableIndex,
      pr1645v2ATMPerMCH24PSysUpTime
         TimeTicks,
      pr1645v2ATMPerMCH24PIfUpTime
         TimeTicks,
      pr1645v2ATMPerMCH24PIfStatChanges
         Counter32,
      pr1645v2ATMPerMCH24PIfInOctets
         Counter64,
      pr1645v2ATMPerMCH24PIfInUCPkts
         Counter64,
      pr1645v2ATMPerMCH24PIfInNUCPkts
         Counter64,
      pr1645v2ATMPerMCH24PIfInBCPkts
         Counter64,
      pr1645v2ATMPerMCH24PIfInMCPkts
         Counter64,
      pr1645v2ATMPerMCH24PIfInDiscards
         Counter64,
      pr1645v2ATMPerMCH24PIfInErrors
         Counter64,
      pr1645v2ATMPerMCH24PIfInUnkwn
         Counter64,
      pr1645v2ATMPerMCH24PInDropEx
         Counter64,
      pr1645v2ATMPerMCH24PInDropNoMac
         Counter64,
      pr1645v2ATMPerMCH24PInDropNUCast
         Counter64,
      pr1645v2ATMPerMCH24PInDropFilter
         Counter64,
      pr1645v2ATMPerMCH24PIfInBandwidth
         Integer32,
      pr1645v2ATMPerMCH24PIfOutOctets
         Counter64,
      pr1645v2ATMPerMCH24PIfOutUCPkts
         Counter64,
      pr1645v2ATMPerMCH24PIfOutNUCPkts
         Counter64,
      pr1645v2ATMPerMCH24PIfOutBCPkts
         Counter64,
      pr1645v2ATMPerMCH24PIfOutMCPkts
         Counter64,
      pr1645v2ATMPerMCH24PIfOutDiscards
         Counter64,
      pr1645v2ATMPerMCH24PIfOutErrors
         Counter64,
      pr1645v2ATMPerMCH24POutDropEx
         Counter64,
      pr1645v2ATMPerMCH24POutDropNoArp
         Counter64,
      pr1645v2ATMPerMCH24POutDropFilter
         Counter64,
      pr1645v2ATMPerMCH24PIfOutBandwidth
         Integer32,
      pr1645v2ATMPerMCH24PIfErrSec
         Counter32
      }

pr1645v2ATMPerMCH24PTableIx OBJECT-TYPE
   SYNTAX      TableIndex
   MAX-ACCESS  not-accessible
   STATUS      current
   DESCRIPTION
      ""
   ::= {pr1645v2ATMPerMCH24PEntry 11}

pr1645v2ATMPerMCH24PSysUpTime OBJECT-TYPE
   SYNTAX      TimeTicks
   MAX-ACCESS  read-only
   STATUS      current
   DESCRIPTION
      "Path: atm.performance.pvcTable.mibCounters.h24Performance.sysUpTime

       Time in centi-second."
   ::= {pr1645v2ATMPerMCH24PEntry 16777216}

pr1645v2ATMPerMCH24PIfUpTime OBJECT-TYPE
   SYNTAX      TimeTicks
   MAX-ACCESS  read-only
   STATUS      current
   DESCRIPTION
      "Path: atm.performance.pvcTable.mibCounters.h24Performance.ifUpTime

       Time in centi-second."
   ::= {pr1645v2ATMPerMCH24PEntry 33554432}

pr1645v2ATMPerMCH24PIfStatChanges OBJECT-TYPE
   SYNTAX      Counter32
   MAX-ACCESS  read-only
   STATUS      current
   DESCRIPTION
      "Path: atm.performance.pvcTable.mibCounters.h24Performance.ifStatusChanges

       32 bit unsigned wrappable counter."
   ::= {pr1645v2ATMPerMCH24PEntry 50331648}

pr1645v2ATMPerMCH24PIfInOctets OBJECT-TYPE
   SYNTAX      Counter64
   MAX-ACCESS  read-only
   STATUS      current
   DESCRIPTION
      "Path: atm.performance.pvcTable.mibCounters.h24Performance.ifInOctets

       64 bit unsigned wrappable counter."
   ::= {pr1645v2ATMPerMCH24PEntry 67108864}

pr1645v2ATMPerMCH24PIfInUCPkts OBJECT-TYPE
   SYNTAX      Counter64
   MAX-ACCESS  read-only
   STATUS      current
   DESCRIPTION
      "Path: atm.performance.pvcTable.mibCounters.h24Performance.ifInUcastPkts

       64 bit unsigned wrappable counter."
   ::= {pr1645v2ATMPerMCH24PEntry 83886080}

pr1645v2ATMPerMCH24PIfInNUCPkts OBJECT-TYPE
   SYNTAX      Counter64
   MAX-ACCESS  read-only
   STATUS      current
   DESCRIPTION
      "Path: atm.performance.pvcTable.mibCounters.h24Performance.ifInNUcastPkts

       64 bit unsigned wrappable counter."
   ::= {pr1645v2ATMPerMCH24PEntry 100663296}

pr1645v2ATMPerMCH24PIfInBCPkts OBJECT-TYPE
   SYNTAX      Counter64
   MAX-ACCESS  read-only
   STATUS      current
   DESCRIPTION
      "Path: atm.performance.pvcTable.mibCounters.h24Performance.ifInBcastPkts

       64 bit unsigned wrappable counter."
   ::= {pr1645v2ATMPerMCH24PEntry 419430400}

pr1645v2ATMPerMCH24PIfInMCPkts OBJECT-TYPE
   SYNTAX      Counter64
   MAX-ACCESS  read-only
   STATUS      current
   DESCRIPTION
      "Path: atm.performance.pvcTable.mibCounters.h24Performance.ifInMcastPkts

       64 bit unsigned wrappable counter."
   ::= {pr1645v2ATMPerMCH24PEntry 436207616}

pr1645v2ATMPerMCH24PIfInDiscards OBJECT-TYPE
   SYNTAX      Counter64
   MAX-ACCESS  read-only
   STATUS      current
   DESCRIPTION
      "Path: atm.performance.pvcTable.mibCounters.h24Performance.ifInDiscards

       64 bit unsigned wrappable counter."
   ::= {pr1645v2ATMPerMCH24PEntry 117440512}

pr1645v2ATMPerMCH24PIfInErrors OBJECT-TYPE
   SYNTAX      Counter64
   MAX-ACCESS  read-only
   STATUS      current
   DESCRIPTION
      "Path: atm.performance.pvcTable.mibCounters.h24Performance.ifInErrors

       64 bit unsigned wrappable counter."
   ::= {pr1645v2ATMPerMCH24PEntry 134217728}

pr1645v2ATMPerMCH24PIfInUnkwn OBJECT-TYPE
   SYNTAX      Counter64
   MAX-ACCESS  read-only
   STATUS      current
   DESCRIPTION
      "Path: atm.performance.pvcTable.mibCounters.h24Performance.ifInUnknownProtos

       64 bit unsigned wrappable counter."
   ::= {pr1645v2ATMPerMCH24PEntry 150994944}

pr1645v2ATMPerMCH24PInDropEx OBJECT-TYPE
   SYNTAX      Counter64
   MAX-ACCESS  read-only
   STATUS      current
   DESCRIPTION
      "Path: atm.performance.pvcTable.mibCounters.h24Performance.ifInDropLevelExceeded

       64 bit unsigned wrappable counter."
   ::= {pr1645v2ATMPerMCH24PEntry 335544320}

pr1645v2ATMPerMCH24PInDropNoMac OBJECT-TYPE
   SYNTAX      Counter64
   MAX-ACCESS  read-only
   STATUS      current
   DESCRIPTION
      "Path: atm.performance.pvcTable.mibCounters.h24Performance.fInDiscardsNoMacFit

       64 bit unsigned wrappable counter."
   ::= {pr1645v2ATMPerMCH24PEntry 301989888}

pr1645v2ATMPerMCH24PInDropNUCast OBJECT-TYPE
   SYNTAX      Counter64
   MAX-ACCESS  read-only
   STATUS      current
   DESCRIPTION
      "Path: atm.performance.pvcTable.mibCounters.h24Performance.fInDiscardsNUCast

       64 bit unsigned wrappable counter."
   ::= {pr1645v2ATMPerMCH24PEntry 318767104}

pr1645v2ATMPerMCH24PInDropFilter OBJECT-TYPE
   SYNTAX      Counter64
   MAX-ACCESS  read-only
   STATUS      current
   DESCRIPTION
      "Path: atm.performance.pvcTable.mibCounters.h24Performance.fInDiscardsFilter

       64 bit unsigned wrappable counter."
   ::= {pr1645v2ATMPerMCH24PEntry 385875968}

pr1645v2ATMPerMCH24PIfInBandwidth OBJECT-TYPE
   SYNTAX      Integer32
   MAX-ACCESS  read-only
   STATUS      current
   DESCRIPTION
      "Path: atm.performance.pvcTable.mibCounters.h24Performance.ifInBandwidth

       unit name = bps
       formula = 8 * ; 8 /"
   ::= {pr1645v2ATMPerMCH24PEntry 268435456}

pr1645v2ATMPerMCH24PIfOutOctets OBJECT-TYPE
   SYNTAX      Counter64
   MAX-ACCESS  read-only
   STATUS      current
   DESCRIPTION
      "Path: atm.performance.pvcTable.mibCounters.h24Performance.ifOutOctets

       64 bit unsigned wrappable counter."
   ::= {pr1645v2ATMPerMCH24PEntry 167772160}

pr1645v2ATMPerMCH24PIfOutUCPkts OBJECT-TYPE
   SYNTAX      Counter64
   MAX-ACCESS  read-only
   STATUS      current
   DESCRIPTION
      "Path: atm.performance.pvcTable.mibCounters.h24Performance.ifOutUcastPkts

       64 bit unsigned wrappable counter."
   ::= {pr1645v2ATMPerMCH24PEntry 184549376}

pr1645v2ATMPerMCH24PIfOutNUCPkts OBJECT-TYPE
   SYNTAX      Counter64
   MAX-ACCESS  read-only
   STATUS      current
   DESCRIPTION
      "Path: atm.performance.pvcTable.mibCounters.h24Performance.ifOutNUcastPkts

       64 bit unsigned wrappable counter."
   ::= {pr1645v2ATMPerMCH24PEntry 201326592}

pr1645v2ATMPerMCH24PIfOutBCPkts OBJECT-TYPE
   SYNTAX      Counter64
   MAX-ACCESS  read-only
   STATUS      current
   DESCRIPTION
      "Path: atm.performance.pvcTable.mibCounters.h24Performance.ifOutBcastPkts

       64 bit unsigned wrappable counter."
   ::= {pr1645v2ATMPerMCH24PEntry 452984832}

pr1645v2ATMPerMCH24PIfOutMCPkts OBJECT-TYPE
   SYNTAX      Counter64
   MAX-ACCESS  read-only
   STATUS      current
   DESCRIPTION
      "Path: atm.performance.pvcTable.mibCounters.h24Performance.ifOutMcastPkts

       64 bit unsigned wrappable counter."
   ::= {pr1645v2ATMPerMCH24PEntry 469762048}

pr1645v2ATMPerMCH24PIfOutDiscards OBJECT-TYPE
   SYNTAX      Counter64
   MAX-ACCESS  read-only
   STATUS      current
   DESCRIPTION
      "Path: atm.performance.pvcTable.mibCounters.h24Performance.ifOutDiscards

       64 bit unsigned wrappable counter."
   ::= {pr1645v2ATMPerMCH24PEntry 218103808}

pr1645v2ATMPerMCH24PIfOutErrors OBJECT-TYPE
   SYNTAX      Counter64
   MAX-ACCESS  read-only
   STATUS      current
   DESCRIPTION
      "Path: atm.performance.pvcTable.mibCounters.h24Performance.ifOutErrors

       64 bit unsigned wrappable counter."
   ::= {pr1645v2ATMPerMCH24PEntry 234881024}

pr1645v2ATMPerMCH24POutDropEx OBJECT-TYPE
   SYNTAX      Counter64
   MAX-ACCESS  read-only
   STATUS      current
   DESCRIPTION
      "Path: atm.performance.pvcTable.mibCounters.h24Performance.ifOutDropLevelExceeded

       64 bit unsigned wrappable counter."
   ::= {pr1645v2ATMPerMCH24PEntry 352321536}

pr1645v2ATMPerMCH24POutDropNoArp OBJECT-TYPE
   SYNTAX      Counter64
   MAX-ACCESS  read-only
   STATUS      current
   DESCRIPTION
      "Path: atm.performance.pvcTable.mibCounters.h24Performance.ifOutDiscardsNoArp

       64 bit unsigned wrappable counter."
   ::= {pr1645v2ATMPerMCH24PEntry 369098752}

pr1645v2ATMPerMCH24POutDropFilter OBJECT-TYPE
   SYNTAX      Counter64
   MAX-ACCESS  read-only
   STATUS      current
   DESCRIPTION
      "Path: atm.performance.pvcTable.mibCounters.h24Performance.ifOutDiscardsFilter

       64 bit unsigned wrappable counter."
   ::= {pr1645v2ATMPerMCH24PEntry 402653184}

pr1645v2ATMPerMCH24PIfOutBandwidth OBJECT-TYPE
   SYNTAX      Integer32
   MAX-ACCESS  read-only
   STATUS      current
   DESCRIPTION
      "Path: atm.performance.pvcTable.mibCounters.h24Performance.ifOutBandwidth

       unit name = bps
       formula = 8 * ; 8 /"
   ::= {pr1645v2ATMPerMCH24PEntry 285212672}

pr1645v2ATMPerMCH24PIfErrSec OBJECT-TYPE
   SYNTAX      Counter32
   MAX-ACCESS  read-only
   STATUS      current
   DESCRIPTION
      "Path: atm.performance.pvcTable.mibCounters.h24Performance.ifErrSec

       32 bit unsigned wrappable counter."
   ::= {pr1645v2ATMPerMCH24PEntry 251658240}

pr1645v2ATMPerMCD7P OBJECT-TYPE
   SYNTAX      SEQUENCE OF Pr1645v2ATMPerMCD7PEntry
   MAX-ACCESS  not-accessible
   STATUS      current
   DESCRIPTION
      ""
   ::= {pr1645v2ATMPer 41680896}

pr1645v2ATMPerMCD7PEntry OBJECT-TYPE
   SYNTAX      Pr1645v2ATMPerMCD7PEntry
   MAX-ACCESS  not-accessible
   STATUS      current
   DESCRIPTION
      ""
   INDEX      { pr1645v2ATMPerTableIx,
                pr1645v2ATMPerMCD7PTableIx }
   ::= {pr1645v2ATMPerMCD7P 1}

Pr1645v2ATMPerMCD7PEntry ::=
   SEQUENCE
      {
      pr1645v2ATMPerMCD7PTableIx
         TableIndex,
      pr1645v2ATMPerMCD7PSysUpTime
         TimeTicks,
      pr1645v2ATMPerMCD7PIfUpTime
         TimeTicks,
      pr1645v2ATMPerMCD7PIfStatChanges
         Counter32,
      pr1645v2ATMPerMCD7PIfInOctets
         Counter64,
      pr1645v2ATMPerMCD7PIfInUCPkts
         Counter64,
      pr1645v2ATMPerMCD7PIfInNUCPkts
         Counter64,
      pr1645v2ATMPerMCD7PIfInBCPkts
         Counter64,
      pr1645v2ATMPerMCD7PIfInMCPkts
         Counter64,
      pr1645v2ATMPerMCD7PIfInDiscards
         Counter64,
      pr1645v2ATMPerMCD7PIfInErrors
         Counter64,
      pr1645v2ATMPerMCD7PIfInUnkwn
         Counter64,
      pr1645v2ATMPerMCD7PInDropEx
         Counter64,
      pr1645v2ATMPerMCD7PInDropNoMac
         Counter64,
      pr1645v2ATMPerMCD7PInDropNUCast
         Counter64,
      pr1645v2ATMPerMCD7PInDropFilter
         Counter64,
      pr1645v2ATMPerMCD7PIfInBandwidth
         Integer32,
      pr1645v2ATMPerMCD7PIfOutOctets
         Counter64,
      pr1645v2ATMPerMCD7PIfOutUCPkts
         Counter64,
      pr1645v2ATMPerMCD7PIfOutNUCPkts
         Counter64,
      pr1645v2ATMPerMCD7PIfOutBCPkts
         Counter64,
      pr1645v2ATMPerMCD7PIfOutMCPkts
         Counter64,
      pr1645v2ATMPerMCD7PIfOutDiscards
         Counter64,
      pr1645v2ATMPerMCD7PIfOutErrors
         Counter64,
      pr1645v2ATMPerMCD7POutDropEx
         Counter64,
      pr1645v2ATMPerMCD7POutDropNoArp
         Counter64,
      pr1645v2ATMPerMCD7POutDropFilter
         Counter64,
      pr1645v2ATMPerMCD7PIfOutBandwidth
         Integer32,
      pr1645v2ATMPerMCD7PIfErrSec
         Counter32
      }

pr1645v2ATMPerMCD7PTableIx OBJECT-TYPE
   SYNTAX      TableIndex
   MAX-ACCESS  not-accessible
   STATUS      current
   DESCRIPTION
      ""
   ::= {pr1645v2ATMPerMCD7PEntry 11}

pr1645v2ATMPerMCD7PSysUpTime OBJECT-TYPE
   SYNTAX      TimeTicks
   MAX-ACCESS  read-only
   STATUS      current
   DESCRIPTION
      "Path: atm.performance.pvcTable.mibCounters.d7Performance.sysUpTime

       Time in centi-second."
   ::= {pr1645v2ATMPerMCD7PEntry 16777216}

pr1645v2ATMPerMCD7PIfUpTime OBJECT-TYPE
   SYNTAX      TimeTicks
   MAX-ACCESS  read-only
   STATUS      current
   DESCRIPTION
      "Path: atm.performance.pvcTable.mibCounters.d7Performance.ifUpTime

       Time in centi-second."
   ::= {pr1645v2ATMPerMCD7PEntry 33554432}

pr1645v2ATMPerMCD7PIfStatChanges OBJECT-TYPE
   SYNTAX      Counter32
   MAX-ACCESS  read-only
   STATUS      current
   DESCRIPTION
      "Path: atm.performance.pvcTable.mibCounters.d7Performance.ifStatusChanges

       32 bit unsigned wrappable counter."
   ::= {pr1645v2ATMPerMCD7PEntry 50331648}

pr1645v2ATMPerMCD7PIfInOctets OBJECT-TYPE
   SYNTAX      Counter64
   MAX-ACCESS  read-only
   STATUS      current
   DESCRIPTION
      "Path: atm.performance.pvcTable.mibCounters.d7Performance.ifInOctets

       64 bit unsigned wrappable counter."
   ::= {pr1645v2ATMPerMCD7PEntry 67108864}

pr1645v2ATMPerMCD7PIfInUCPkts OBJECT-TYPE
   SYNTAX      Counter64
   MAX-ACCESS  read-only
   STATUS      current
   DESCRIPTION
      "Path: atm.performance.pvcTable.mibCounters.d7Performance.ifInUcastPkts

       64 bit unsigned wrappable counter."
   ::= {pr1645v2ATMPerMCD7PEntry 83886080}

pr1645v2ATMPerMCD7PIfInNUCPkts OBJECT-TYPE
   SYNTAX      Counter64
   MAX-ACCESS  read-only
   STATUS      current
   DESCRIPTION
      "Path: atm.performance.pvcTable.mibCounters.d7Performance.ifInNUcastPkts

       64 bit unsigned wrappable counter."
   ::= {pr1645v2ATMPerMCD7PEntry 100663296}

pr1645v2ATMPerMCD7PIfInBCPkts OBJECT-TYPE
   SYNTAX      Counter64
   MAX-ACCESS  read-only
   STATUS      current
   DESCRIPTION
      "Path: atm.performance.pvcTable.mibCounters.d7Performance.ifInBcastPkts

       64 bit unsigned wrappable counter."
   ::= {pr1645v2ATMPerMCD7PEntry 419430400}

pr1645v2ATMPerMCD7PIfInMCPkts OBJECT-TYPE
   SYNTAX      Counter64
   MAX-ACCESS  read-only
   STATUS      current
   DESCRIPTION
      "Path: atm.performance.pvcTable.mibCounters.d7Performance.ifInMcastPkts

       64 bit unsigned wrappable counter."
   ::= {pr1645v2ATMPerMCD7PEntry 436207616}

pr1645v2ATMPerMCD7PIfInDiscards OBJECT-TYPE
   SYNTAX      Counter64
   MAX-ACCESS  read-only
   STATUS      current
   DESCRIPTION
      "Path: atm.performance.pvcTable.mibCounters.d7Performance.ifInDiscards

       64 bit unsigned wrappable counter."
   ::= {pr1645v2ATMPerMCD7PEntry 117440512}

pr1645v2ATMPerMCD7PIfInErrors OBJECT-TYPE
   SYNTAX      Counter64
   MAX-ACCESS  read-only
   STATUS      current
   DESCRIPTION
      "Path: atm.performance.pvcTable.mibCounters.d7Performance.ifInErrors

       64 bit unsigned wrappable counter."
   ::= {pr1645v2ATMPerMCD7PEntry 134217728}

pr1645v2ATMPerMCD7PIfInUnkwn OBJECT-TYPE
   SYNTAX      Counter64
   MAX-ACCESS  read-only
   STATUS      current
   DESCRIPTION
      "Path: atm.performance.pvcTable.mibCounters.d7Performance.ifInUnknownProtos

       64 bit unsigned wrappable counter."
   ::= {pr1645v2ATMPerMCD7PEntry 150994944}

pr1645v2ATMPerMCD7PInDropEx OBJECT-TYPE
   SYNTAX      Counter64
   MAX-ACCESS  read-only
   STATUS      current
   DESCRIPTION
      "Path: atm.performance.pvcTable.mibCounters.d7Performance.ifInDropLevelExceeded

       64 bit unsigned wrappable counter."
   ::= {pr1645v2ATMPerMCD7PEntry 335544320}

pr1645v2ATMPerMCD7PInDropNoMac OBJECT-TYPE
   SYNTAX      Counter64
   MAX-ACCESS  read-only
   STATUS      current
   DESCRIPTION
      "Path: atm.performance.pvcTable.mibCounters.d7Performance.fInDiscardsNoMacFit

       64 bit unsigned wrappable counter."
   ::= {pr1645v2ATMPerMCD7PEntry 301989888}

pr1645v2ATMPerMCD7PInDropNUCast OBJECT-TYPE
   SYNTAX      Counter64
   MAX-ACCESS  read-only
   STATUS      current
   DESCRIPTION
      "Path: atm.performance.pvcTable.mibCounters.d7Performance.fInDiscardsNUCast

       64 bit unsigned wrappable counter."
   ::= {pr1645v2ATMPerMCD7PEntry 318767104}

pr1645v2ATMPerMCD7PInDropFilter OBJECT-TYPE
   SYNTAX      Counter64
   MAX-ACCESS  read-only
   STATUS      current
   DESCRIPTION
      "Path: atm.performance.pvcTable.mibCounters.d7Performance.fInDiscardsFilter

       64 bit unsigned wrappable counter."
   ::= {pr1645v2ATMPerMCD7PEntry 385875968}

pr1645v2ATMPerMCD7PIfInBandwidth OBJECT-TYPE
   SYNTAX      Integer32
   MAX-ACCESS  read-only
   STATUS      current
   DESCRIPTION
      "Path: atm.performance.pvcTable.mibCounters.d7Performance.ifInBandwidth

       unit name = bps
       formula = 8 * ; 8 /"
   ::= {pr1645v2ATMPerMCD7PEntry 268435456}

pr1645v2ATMPerMCD7PIfOutOctets OBJECT-TYPE
   SYNTAX      Counter64
   MAX-ACCESS  read-only
   STATUS      current
   DESCRIPTION
      "Path: atm.performance.pvcTable.mibCounters.d7Performance.ifOutOctets

       64 bit unsigned wrappable counter."
   ::= {pr1645v2ATMPerMCD7PEntry 167772160}

pr1645v2ATMPerMCD7PIfOutUCPkts OBJECT-TYPE
   SYNTAX      Counter64
   MAX-ACCESS  read-only
   STATUS      current
   DESCRIPTION
      "Path: atm.performance.pvcTable.mibCounters.d7Performance.ifOutUcastPkts

       64 bit unsigned wrappable counter."
   ::= {pr1645v2ATMPerMCD7PEntry 184549376}

pr1645v2ATMPerMCD7PIfOutNUCPkts OBJECT-TYPE
   SYNTAX      Counter64
   MAX-ACCESS  read-only
   STATUS      current
   DESCRIPTION
      "Path: atm.performance.pvcTable.mibCounters.d7Performance.ifOutNUcastPkts

       64 bit unsigned wrappable counter."
   ::= {pr1645v2ATMPerMCD7PEntry 201326592}

pr1645v2ATMPerMCD7PIfOutBCPkts OBJECT-TYPE
   SYNTAX      Counter64
   MAX-ACCESS  read-only
   STATUS      current
   DESCRIPTION
      "Path: atm.performance.pvcTable.mibCounters.d7Performance.ifOutBcastPkts

       64 bit unsigned wrappable counter."
   ::= {pr1645v2ATMPerMCD7PEntry 452984832}

pr1645v2ATMPerMCD7PIfOutMCPkts OBJECT-TYPE
   SYNTAX      Counter64
   MAX-ACCESS  read-only
   STATUS      current
   DESCRIPTION
      "Path: atm.performance.pvcTable.mibCounters.d7Performance.ifOutMcastPkts

       64 bit unsigned wrappable counter."
   ::= {pr1645v2ATMPerMCD7PEntry 469762048}

pr1645v2ATMPerMCD7PIfOutDiscards OBJECT-TYPE
   SYNTAX      Counter64
   MAX-ACCESS  read-only
   STATUS      current
   DESCRIPTION
      "Path: atm.performance.pvcTable.mibCounters.d7Performance.ifOutDiscards

       64 bit unsigned wrappable counter."
   ::= {pr1645v2ATMPerMCD7PEntry 218103808}

pr1645v2ATMPerMCD7PIfOutErrors OBJECT-TYPE
   SYNTAX      Counter64
   MAX-ACCESS  read-only
   STATUS      current
   DESCRIPTION
      "Path: atm.performance.pvcTable.mibCounters.d7Performance.ifOutErrors

       64 bit unsigned wrappable counter."
   ::= {pr1645v2ATMPerMCD7PEntry 234881024}

pr1645v2ATMPerMCD7POutDropEx OBJECT-TYPE
   SYNTAX      Counter64
   MAX-ACCESS  read-only
   STATUS      current
   DESCRIPTION
      "Path: atm.performance.pvcTable.mibCounters.d7Performance.ifOutDropLevelExceeded

       64 bit unsigned wrappable counter."
   ::= {pr1645v2ATMPerMCD7PEntry 352321536}

pr1645v2ATMPerMCD7POutDropNoArp OBJECT-TYPE
   SYNTAX      Counter64
   MAX-ACCESS  read-only
   STATUS      current
   DESCRIPTION
      "Path: atm.performance.pvcTable.mibCounters.d7Performance.ifOutDiscardsNoArp

       64 bit unsigned wrappable counter."
   ::= {pr1645v2ATMPerMCD7PEntry 369098752}

pr1645v2ATMPerMCD7POutDropFilter OBJECT-TYPE
   SYNTAX      Counter64
   MAX-ACCESS  read-only
   STATUS      current
   DESCRIPTION
      "Path: atm.performance.pvcTable.mibCounters.d7Performance.ifOutDiscardsFilter

       64 bit unsigned wrappable counter."
   ::= {pr1645v2ATMPerMCD7PEntry 402653184}

pr1645v2ATMPerMCD7PIfOutBandwidth OBJECT-TYPE
   SYNTAX      Integer32
   MAX-ACCESS  read-only
   STATUS      current
   DESCRIPTION
      "Path: atm.performance.pvcTable.mibCounters.d7Performance.ifOutBandwidth

       unit name = bps
       formula = 8 * ; 8 /"
   ::= {pr1645v2ATMPerMCD7PEntry 285212672}

pr1645v2ATMPerMCD7PIfErrSec OBJECT-TYPE
   SYNTAX      Counter32
   MAX-ACCESS  read-only
   STATUS      current
   DESCRIPTION
      "Path: atm.performance.pvcTable.mibCounters.d7Performance.ifErrSec

       32 bit unsigned wrappable counter."
   ::= {pr1645v2ATMPerMCD7PEntry 251658240}

pr1645v2ATMPerInPQs OBJECT-TYPE
   SYNTAX      SEQUENCE OF Pr1645v2ATMPerInPQsEntry
   MAX-ACCESS  not-accessible
   STATUS      current
   DESCRIPTION
      ""
   ::= {pr1645v2ATMPer 100663296}

pr1645v2ATMPerInPQsEntry OBJECT-TYPE
   SYNTAX      Pr1645v2ATMPerInPQsEntry
   MAX-ACCESS  not-accessible
   STATUS      current
   DESCRIPTION
      ""
   INDEX      { pr1645v2ATMPerTableIx,
                pr1645v2ATMPerInPQsTableIx }
   ::= {pr1645v2ATMPerInPQs 1}

Pr1645v2ATMPerInPQsEntry ::=
   SEQUENCE
      {
      pr1645v2ATMPerInPQsTableIx
         TableIndex,
      pr1645v2ATMPerInPQsName
         INTEGER,
      pr1645v2ATMPerInPQsLength
         Integer32,
      pr1645v2ATMPerInPQsOctetLength
         Integer32,
      pr1645v2ATMPerInPQsRedLength
         Integer32,
      pr1645v2ATMPerInPQsPacketsTotal
         Counter64,
      pr1645v2ATMPerInPQsPacketsDirectTx
         Counter64,
      pr1645v2ATMPerInPQsPacketsQueued
         Counter64,
      pr1645v2ATMPerInPQsPacketsDropped
         Counter64,
      pr1645v2ATMPerInPQsPacketsRedDropped
         Counter64,
      pr1645v2ATMPerInPQsPacketsCirTx
         Counter64,
      pr1645v2ATMPerInPQsPacketsEirTx
         Counter64,
      pr1645v2ATMPerInPQsPacketsViolateTx
         Counter64,
      pr1645v2ATMPerInPQsOctetsTotal
         Counter64,
      pr1645v2ATMPerInPQsOctetsDirectTx
         Counter64,
      pr1645v2ATMPerInPQsOctetsQueued
         Counter64,
      pr1645v2ATMPerInPQsOctetsDropped
         Counter64,
      pr1645v2ATMPerInPQsOctetsRedDropped
         Counter64,
      pr1645v2ATMPerInPQsOctetsCirTx
         Counter64,
      pr1645v2ATMPerInPQsOctetsEirTx
         Counter64,
      pr1645v2ATMPerInPQsOctetsViolateTx
         Counter64,
      pr1645v2ATMPerInPQsOctetsBandwidth15sec
         Integer32,
      pr1645v2ATMPerInPQsOctetsBandwidth30sec
         Integer32,
      pr1645v2ATMPerInPQsOctetsBandwidth1min
         Integer32,
      pr1645v2ATMPerInPQsOctetsBandwidth2min
         Integer32,
      pr1645v2ATMPerInPQsOctetsBandwidth5min
         Integer32
      }

pr1645v2ATMPerInPQsTableIx OBJECT-TYPE
   SYNTAX      TableIndex
   MAX-ACCESS  not-accessible
   STATUS      current
   DESCRIPTION
      ""
   ::= {pr1645v2ATMPerInPQsEntry 11}

pr1645v2ATMPerInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2ATMPerInPQsEntry 16777216}

pr1645v2ATMPerInPQsLength OBJECT-TYPE
   SYNTAX      Integer32
   MAX-ACCESS  read-only
   STATUS      current
   DESCRIPTION
      "Path: atm.performance.pvcTable.inPriorityQueues.length"
   ::= {pr1645v2ATMPerInPQsEntry 33554432}

pr1645v2ATMPerInPQsOctetLength OBJECT-TYPE
   SYNTAX      Integer32
   MAX-ACCESS  read-only
   STATUS      current
   DESCRIPTION
      "Path: atm.performance.pvcTable.inPriorityQueues.octetLength"
   ::= {pr1645v2ATMPerInPQsEntry 150994944}

pr1645v2ATMPerInPQsRedLength OBJECT-TYPE
   SYNTAX      Integer32
   MAX-ACCESS  read-only
   STATUS      current
   DESCRIPTION
      "Path: atm.performance.pvcTable.inPriorityQueues.redLength"
   ::= {pr1645v2ATMPerInPQsEntry 134217728}

pr1645v2ATMPerInPQsPacketsTotal OBJECT-TYPE
   SYNTAX      Counter64
   MAX-ACCESS  read-only
   STATUS      current
   DESCRIPTION
      "Path: atm.performance.pvcTable.inPriorityQueues.packets.total

       64 bit unsigned wrappable counter."
   ::= {pr1645v2ATMPerInPQsEntry 50790400}

pr1645v2ATMPerInPQsPacketsDirectTx OBJECT-TYPE
   SYNTAX      Counter64
   MAX-ACCESS  read-only
   STATUS      current
   DESCRIPTION
      "Path: atm.performance.pvcTable.inPriorityQueues.packets.directTx

       64 bit unsigned wrappable counter."
   ::= {pr1645v2ATMPerInPQsEntry 50397184}

pr1645v2ATMPerInPQsPacketsQueued OBJECT-TYPE
   SYNTAX      Counter64
   MAX-ACCESS  read-only
   STATUS      current
   DESCRIPTION
      "Path: atm.performance.pvcTable.inPriorityQueues.packets.queued

       64 bit unsigned wrappable counter."
   ::= {pr1645v2ATMPerInPQsEntry 50462720}

pr1645v2ATMPerInPQsPacketsDropped OBJECT-TYPE
   SYNTAX      Counter64
   MAX-ACCESS  read-only
   STATUS      current
   DESCRIPTION
      "Path: atm.performance.pvcTable.inPriorityQueues.packets.dropped

       64 bit unsigned wrappable counter."
   ::= {pr1645v2ATMPerInPQsEntry 50528256}

pr1645v2ATMPerInPQsPacketsRedDropped OBJECT-TYPE
   SYNTAX      Counter64
   MAX-ACCESS  read-only
   STATUS      current
   DESCRIPTION
      "Path: atm.performance.pvcTable.inPriorityQueues.packets.redDropped

       64 bit unsigned wrappable counter."
   ::= {pr1645v2ATMPerInPQsEntry 50724864}

pr1645v2ATMPerInPQsPacketsCirTx OBJECT-TYPE
   SYNTAX      Counter64
   MAX-ACCESS  read-only
   STATUS      current
   DESCRIPTION
      "Path: atm.performance.pvcTable.inPriorityQueues.packets.cirTx

       64 bit unsigned wrappable counter."
   ::= {pr1645v2ATMPerInPQsEntry 50593792}

pr1645v2ATMPerInPQsPacketsEirTx OBJECT-TYPE
   SYNTAX      Counter64
   MAX-ACCESS  read-only
   STATUS      current
   DESCRIPTION
      "Path: atm.performance.pvcTable.inPriorityQueues.packets.eirTx

       64 bit unsigned wrappable counter."
   ::= {pr1645v2ATMPerInPQsEntry 50659328}

pr1645v2ATMPerInPQsPacketsViolateTx OBJECT-TYPE
   SYNTAX      Counter64
   MAX-ACCESS  read-only
   STATUS      current
   DESCRIPTION
      "Path: atm.performance.pvcTable.inPriorityQueues.packets.violateTx

       64 bit unsigned wrappable counter."
   ::= {pr1645v2ATMPerInPQsEntry 50855936}

pr1645v2ATMPerInPQsOctetsTotal OBJECT-TYPE
   SYNTAX      Counter64
   MAX-ACCESS  read-only
   STATUS      current
   DESCRIPTION
      "Path: atm.performance.pvcTable.inPriorityQueues.octets.total

       64 bit unsigned wrappable counter."
   ::= {pr1645v2ATMPerInPQsEntry 67567616}

pr1645v2ATMPerInPQsOctetsDirectTx OBJECT-TYPE
   SYNTAX      Counter64
   MAX-ACCESS  read-only
   STATUS      current
   DESCRIPTION
      "Path: atm.performance.pvcTable.inPriorityQueues.octets.directTx

       64 bit unsigned wrappable counter."
   ::= {pr1645v2ATMPerInPQsEntry 67174400}

pr1645v2ATMPerInPQsOctetsQueued OBJECT-TYPE
   SYNTAX      Counter64
   MAX-ACCESS  read-only
   STATUS      current
   DESCRIPTION
      "Path: atm.performance.pvcTable.inPriorityQueues.octets.queued

       64 bit unsigned wrappable counter."
   ::= {pr1645v2ATMPerInPQsEntry 67239936}

pr1645v2ATMPerInPQsOctetsDropped OBJECT-TYPE
   SYNTAX      Counter64
   MAX-ACCESS  read-only
   STATUS      current
   DESCRIPTION
      "Path: atm.performance.pvcTable.inPriorityQueues.octets.dropped

       64 bit unsigned wrappable counter."
   ::= {pr1645v2ATMPerInPQsEntry 67305472}

pr1645v2ATMPerInPQsOctetsRedDropped OBJECT-TYPE
   SYNTAX      Counter64
   MAX-ACCESS  read-only
   STATUS      current
   DESCRIPTION
      "Path: atm.performance.pvcTable.inPriorityQueues.octets.redDropped

       64 bit unsigned wrappable counter."
   ::= {pr1645v2ATMPerInPQsEntry 67502080}

pr1645v2ATMPerInPQsOctetsCirTx OBJECT-TYPE
   SYNTAX      Counter64
   MAX-ACCESS  read-only
   STATUS      current
   DESCRIPTION
      "Path: atm.performance.pvcTable.inPriorityQueues.octets.cirTx

       64 bit unsigned wrappable counter."
   ::= {pr1645v2ATMPerInPQsEntry 67371008}

pr1645v2ATMPerInPQsOctetsEirTx OBJECT-TYPE
   SYNTAX      Counter64
   MAX-ACCESS  read-only
   STATUS      current
   DESCRIPTION
      "Path: atm.performance.pvcTable.inPriorityQueues.octets.eirTx

       64 bit unsigned wrappable counter."
   ::= {pr1645v2ATMPerInPQsEntry 67436544}

pr1645v2ATMPerInPQsOctetsViolateTx OBJECT-TYPE
   SYNTAX      Counter64
   MAX-ACCESS  read-only
   STATUS      current
   DESCRIPTION
      "Path: atm.performance.pvcTable.inPriorityQueues.octets.violateTx

       64 bit unsigned wrappable counter."
   ::= {pr1645v2ATMPerInPQsEntry 67633152}

pr1645v2ATMPerInPQsOctetsBandwidth15sec OBJECT-TYPE
   SYNTAX      Integer32
   MAX-ACCESS  read-only
   STATUS      current
   DESCRIPTION
      "Path: atm.performance.pvcTable.inPriorityQueues.octets.bandwidth.15sec

       unit name = bps
       formula = 8 * ; 8 /"
   ::= {pr1645v2ATMPerInPQsEntry 70386944}

pr1645v2ATMPerInPQsOctetsBandwidth30sec OBJECT-TYPE
   SYNTAX      Integer32
   MAX-ACCESS  read-only
   STATUS      current
   DESCRIPTION
      "Path: atm.performance.pvcTable.inPriorityQueues.octets.bandwidth.30sec

       unit name = bps
       formula = 8 * ; 8 /"
   ::= {pr1645v2ATMPerInPQsEntry 70388224}

pr1645v2ATMPerInPQsOctetsBandwidth1min OBJECT-TYPE
   SYNTAX      Integer32
   MAX-ACCESS  read-only
   STATUS      current
   DESCRIPTION
      "Path: atm.performance.pvcTable.inPriorityQueues.octets.bandwidth.1min

       unit name = bps
       formula = 8 * ; 8 /"
   ::= {pr1645v2ATMPerInPQsEntry 70390784}

pr1645v2ATMPerInPQsOctetsBandwidth2min OBJECT-TYPE
   SYNTAX      Integer32
   MAX-ACCESS  read-only
   STATUS      current
   DESCRIPTION
      "Path: atm.performance.pvcTable.inPriorityQueues.octets.bandwidth.2min

       unit name = bps
       formula = 8 * ; 8 /"
   ::= {pr1645v2ATMPerInPQsEntry 70395904}

pr1645v2ATMPerInPQsOctetsBandwidth5min OBJECT-TYPE
   SYNTAX      Integer32
   MAX-ACCESS  read-only
   STATUS      current
   DESCRIPTION
      "Path: atm.performance.pvcTable.inPriorityQueues.octets.bandwidth.5min

       unit name = bps
       formula = 8 * ; 8 /"
   ::= {pr1645v2ATMPerInPQsEntry 70411264}

pr1645v2ATMPerInPQsH2Performance OBJECT-TYPE
   SYNTAX      SEQUENCE OF Pr1645v2ATMPerInPQsH2PerformanceEntry
   MAX-ACCESS  not-accessible
   STATUS      current
   DESCRIPTION
      ""
   ::= {pr1645v2ATMPer 100990976}

pr1645v2ATMPerInPQsH2PerformanceEntry OBJECT-TYPE
   SYNTAX      Pr1645v2ATMPerInPQsH2PerformanceEntry
   MAX-ACCESS  not-accessible
   STATUS      current
   DESCRIPTION
      ""
   INDEX      { pr1645v2ATMPerTableIx,
                pr1645v2ATMPerInPQsTableIx,
                pr1645v2ATMPerInPQsH2PerformanceTableIx }
   ::= {pr1645v2ATMPerInPQsH2Performance 1}

Pr1645v2ATMPerInPQsH2PerformanceEntry ::=
   SEQUENCE
      {
      pr1645v2ATMPerInPQsH2PerformanceTableIx
         TableIndex,
      pr1645v2ATMPerInPQsH2PerformanceSysUpTime
         TimeTicks,
      pr1645v2ATMPerInPQsH2PerformanceTotPkts
         Counter64,
      pr1645v2ATMPerInPQsH2PerformanceDirTxPkts
         Counter64,
      pr1645v2ATMPerInPQsH2PerformanceQdPkts
         Counter64,
      pr1645v2ATMPerInPQsH2PerformanceDropPkts
         Counter64,
      pr1645v2ATMPerInPQsH2PerformanceRDropPkts
         Counter64,
      pr1645v2ATMPerInPQsH2PerformanceCirTxPkts
         Counter64,
      pr1645v2ATMPerInPQsH2PerformanceEirTxPkts
         Counter64,
      pr1645v2ATMPerInPQsH2PerformanceViolTxPkts
         Counter64,
      pr1645v2ATMPerInPQsH2PerformanceTotOcts
         Counter64,
      pr1645v2ATMPerInPQsH2PerformanceDirTxOcts
         Counter64,
      pr1645v2ATMPerInPQsH2PerformanceQdOcts
         Counter64,
      pr1645v2ATMPerInPQsH2PerformanceDropOcts
         Counter64,
      pr1645v2ATMPerInPQsH2PerformanceRDropOcts
         Counter64,
      pr1645v2ATMPerInPQsH2PerformanceCirTxOcts
         Counter64,
      pr1645v2ATMPerInPQsH2PerformanceEirTxOcts
         Counter64,
      pr1645v2ATMPerInPQsH2PerformanceViolTxOcts
         Counter64,
      pr1645v2ATMPerInPQsH2PerformanceBandwidth
         Integer32
      }

pr1645v2ATMPerInPQsH2PerformanceTableIx OBJECT-TYPE
   SYNTAX      TableIndex
   MAX-ACCESS  not-accessible
   STATUS      current
   DESCRIPTION
      ""
   ::= {pr1645v2ATMPerInPQsH2PerformanceEntry 11}

pr1645v2ATMPerInPQsH2PerformanceSysUpTime OBJECT-TYPE
   SYNTAX      TimeTicks
   MAX-ACCESS  read-only
   STATUS      current
   DESCRIPTION
      "Path: atm.performance.pvcTable.inPriorityQueues.h2Performance.sysUpTime

       Time in centi-second."
   ::= {pr1645v2ATMPerInPQsH2PerformanceEntry 16777216}

pr1645v2ATMPerInPQsH2PerformanceTotPkts OBJECT-TYPE
   SYNTAX      Counter64
   MAX-ACCESS  read-only
   STATUS      current
   DESCRIPTION
      "Path: atm.performance.pvcTable.inPriorityQueues.h2Performance.totalPkts

       64 bit unsigned wrappable counter."
   ::= {pr1645v2ATMPerInPQsH2PerformanceEntry 234881024}

pr1645v2ATMPerInPQsH2PerformanceDirTxPkts OBJECT-TYPE
   SYNTAX      Counter64
   MAX-ACCESS  read-only
   STATUS      current
   DESCRIPTION
      "Path: atm.performance.pvcTable.inPriorityQueues.h2Performance.directTxPkts

       64 bit unsigned wrappable counter."
   ::= {pr1645v2ATMPerInPQsH2PerformanceEntry 33554432}

pr1645v2ATMPerInPQsH2PerformanceQdPkts OBJECT-TYPE
   SYNTAX      Counter64
   MAX-ACCESS  read-only
   STATUS      current
   DESCRIPTION
      "Path: atm.performance.pvcTable.inPriorityQueues.h2Performance.queuedPkts

       64 bit unsigned wrappable counter."
   ::= {pr1645v2ATMPerInPQsH2PerformanceEntry 50331648}

pr1645v2ATMPerInPQsH2PerformanceDropPkts OBJECT-TYPE
   SYNTAX      Counter64
   MAX-ACCESS  read-only
   STATUS      current
   DESCRIPTION
      "Path: atm.performance.pvcTable.inPriorityQueues.h2Performance.droppedPkts

       64 bit unsigned wrappable counter."
   ::= {pr1645v2ATMPerInPQsH2PerformanceEntry 67108864}

pr1645v2ATMPerInPQsH2PerformanceRDropPkts OBJECT-TYPE
   SYNTAX      Counter64
   MAX-ACCESS  read-only
   STATUS      current
   DESCRIPTION
      "Path: atm.performance.pvcTable.inPriorityQueues.h2Performance.redDroppedPkts

       64 bit unsigned wrappable counter."
   ::= {pr1645v2ATMPerInPQsH2PerformanceEntry 201326592}

pr1645v2ATMPerInPQsH2PerformanceCirTxPkts OBJECT-TYPE
   SYNTAX      Counter64
   MAX-ACCESS  read-only
   STATUS      current
   DESCRIPTION
      "Path: atm.performance.pvcTable.inPriorityQueues.h2Performance.cirTxPkts

       64 bit unsigned wrappable counter."
   ::= {pr1645v2ATMPerInPQsH2PerformanceEntry 83886080}

pr1645v2ATMPerInPQsH2PerformanceEirTxPkts OBJECT-TYPE
   SYNTAX      Counter64
   MAX-ACCESS  read-only
   STATUS      current
   DESCRIPTION
      "Path: atm.performance.pvcTable.inPriorityQueues.h2Performance.eirTxPkts

       64 bit unsigned wrappable counter."
   ::= {pr1645v2ATMPerInPQsH2PerformanceEntry 100663296}

pr1645v2ATMPerInPQsH2PerformanceViolTxPkts OBJECT-TYPE
   SYNTAX      Counter64
   MAX-ACCESS  read-only
   STATUS      current
   DESCRIPTION
      "Path: atm.performance.pvcTable.inPriorityQueues.h2Performance.violateTxPkts

       64 bit unsigned wrappable counter."
   ::= {pr1645v2ATMPerInPQsH2PerformanceEntry 301989888}

pr1645v2ATMPerInPQsH2PerformanceTotOcts OBJECT-TYPE
   SYNTAX      Counter64
   MAX-ACCESS  read-only
   STATUS      current
   DESCRIPTION
      "Path: atm.performance.pvcTable.inPriorityQueues.h2Performance.totalOctets

       64 bit unsigned wrappable counter."
   ::= {pr1645v2ATMPerInPQsH2PerformanceEntry 251658240}

pr1645v2ATMPerInPQsH2PerformanceDirTxOcts OBJECT-TYPE
   SYNTAX      Counter64
   MAX-ACCESS  read-only
   STATUS      current
   DESCRIPTION
      "Path: atm.performance.pvcTable.inPriorityQueues.h2Performance.directTxOctets

       64 bit unsigned wrappable counter."
   ::= {pr1645v2ATMPerInPQsH2PerformanceEntry 117440512}

pr1645v2ATMPerInPQsH2PerformanceQdOcts OBJECT-TYPE
   SYNTAX      Counter64
   MAX-ACCESS  read-only
   STATUS      current
   DESCRIPTION
      "Path: atm.performance.pvcTable.inPriorityQueues.h2Performance.queuedOctets

       64 bit unsigned wrappable counter."
   ::= {pr1645v2ATMPerInPQsH2PerformanceEntry 134217728}

pr1645v2ATMPerInPQsH2PerformanceDropOcts OBJECT-TYPE
   SYNTAX      Counter64
   MAX-ACCESS  read-only
   STATUS      current
   DESCRIPTION
      "Path: atm.performance.pvcTable.inPriorityQueues.h2Performance.droppedOctets

       64 bit unsigned wrappable counter."
   ::= {pr1645v2ATMPerInPQsH2PerformanceEntry 150994944}

pr1645v2ATMPerInPQsH2PerformanceRDropOcts OBJECT-TYPE
   SYNTAX      Counter64
   MAX-ACCESS  read-only
   STATUS      current
   DESCRIPTION
      "Path: atm.performance.pvcTable.inPriorityQueues.h2Performance.redDroppedOctets

       64 bit unsigned wrappable counter."
   ::= {pr1645v2ATMPerInPQsH2PerformanceEntry 218103808}

pr1645v2ATMPerInPQsH2PerformanceCirTxOcts OBJECT-TYPE
   SYNTAX      Counter64
   MAX-ACCESS  read-only
   STATUS      current
   DESCRIPTION
      "Path: atm.performance.pvcTable.inPriorityQueues.h2Performance.cirTxOctets

       64 bit unsigned wrappable counter."
   ::= {pr1645v2ATMPerInPQsH2PerformanceEntry 167772160}

pr1645v2ATMPerInPQsH2PerformanceEirTxOcts OBJECT-TYPE
   SYNTAX      Counter64
   MAX-ACCESS  read-only
   STATUS      current
   DESCRIPTION
      "Path: atm.performance.pvcTable.inPriorityQueues.h2Performance.eirTxOctets

       64 bit unsigned wrappable counter."
   ::= {pr1645v2ATMPerInPQsH2PerformanceEntry 184549376}

pr1645v2ATMPerInPQsH2PerformanceViolTxOcts OBJECT-TYPE
   SYNTAX      Counter64
   MAX-ACCESS  read-only
   STATUS      current
   DESCRIPTION
      "Path: atm.performance.pvcTable.inPriorityQueues.h2Performance.violateTxOctets

       64 bit unsigned wrappable counter."
   ::= {pr1645v2ATMPerInPQsH2PerformanceEntry 318767104}

pr1645v2ATMPerInPQsH2PerformanceBandwidth OBJECT-TYPE
   SYNTAX      Integer32
   MAX-ACCESS  read-only
   STATUS      current
   DESCRIPTION
      "Path: atm.performance.pvcTable.inPriorityQueues.h2Performance.bandwidth

       unit name = bps
       formula = 8 * ; 8 /"
   ::= {pr1645v2ATMPerInPQsH2PerformanceEntry 268435456}

pr1645v2ATMPerInPQsH24Performance OBJECT-TYPE
   SYNTAX      SEQUENCE OF Pr1645v2ATMPerInPQsH24PerformanceEntry
   MAX-ACCESS  not-accessible
   STATUS      current
   DESCRIPTION
      ""
   ::= {pr1645v2ATMPer 101056512}

pr1645v2ATMPerInPQsH24PerformanceEntry OBJECT-TYPE
   SYNTAX      Pr1645v2ATMPerInPQsH24PerformanceEntry
   MAX-ACCESS  not-accessible
   STATUS      current
   DESCRIPTION
      ""
   INDEX      { pr1645v2ATMPerTableIx,
                pr1645v2ATMPerInPQsTableIx,
                pr1645v2ATMPerInPQsH24PerformanceTableIx }
   ::= {pr1645v2ATMPerInPQsH24Performance 1}

Pr1645v2ATMPerInPQsH24PerformanceEntry ::=
   SEQUENCE
      {
      pr1645v2ATMPerInPQsH24PerformanceTableIx
         TableIndex,
      pr1645v2ATMPerInPQsH24PerformanceSysUpTime
         TimeTicks,
      pr1645v2ATMPerInPQsH24PerformanceTotPkts
         Counter64,
      pr1645v2ATMPerInPQsH24PerformanceDirTxPkts
         Counter64,
      pr1645v2ATMPerInPQsH24PerformanceQdPkts
         Counter64,
      pr1645v2ATMPerInPQsH24PerformanceDropPkts
         Counter64,
      pr1645v2ATMPerInPQsH24PerformanceRDropPkts
         Counter64,
      pr1645v2ATMPerInPQsH24PerformanceCirTxPkts
         Counter64,
      pr1645v2ATMPerInPQsH24PerformanceEirTxPkts
         Counter64,
      pr1645v2ATMPerInPQsH24PerformanceViolTxPkts
         Counter64,
      pr1645v2ATMPerInPQsH24PerformanceTotOcts
         Counter64,
      pr1645v2ATMPerInPQsH24PerformanceDirTxOcts
         Counter64,
      pr1645v2ATMPerInPQsH24PerformanceQdOcts
         Counter64,
      pr1645v2ATMPerInPQsH24PerformanceDropOcts
         Counter64,
      pr1645v2ATMPerInPQsH24PerformanceRDropOcts
         Counter64,
      pr1645v2ATMPerInPQsH24PerformanceCirTxOcts
         Counter64,
      pr1645v2ATMPerInPQsH24PerformanceEirTxOcts
         Counter64,
      pr1645v2ATMPerInPQsH24PerformanceViolTxOcts
         Counter64,
      pr1645v2ATMPerInPQsH24PerformanceBandwidth
         Integer32
      }

pr1645v2ATMPerInPQsH24PerformanceTableIx OBJECT-TYPE
   SYNTAX      TableIndex
   MAX-ACCESS  not-accessible
   STATUS      current
   DESCRIPTION
      ""
   ::= {pr1645v2ATMPerInPQsH24PerformanceEntry 11}

pr1645v2ATMPerInPQsH24PerformanceSysUpTime OBJECT-TYPE
   SYNTAX      TimeTicks
   MAX-ACCESS  read-only
   STATUS      current
   DESCRIPTION
      "Path: atm.performance.pvcTable.inPriorityQueues.h24Performance.sysUpTime

       Time in centi-second."
   ::= {pr1645v2ATMPerInPQsH24PerformanceEntry 16777216}

pr1645v2ATMPerInPQsH24PerformanceTotPkts OBJECT-TYPE
   SYNTAX      Counter64
   MAX-ACCESS  read-only
   STATUS      current
   DESCRIPTION
      "Path: atm.performance.pvcTable.inPriorityQueues.h24Performance.totalPkts

       64 bit unsigned wrappable counter."
   ::= {pr1645v2ATMPerInPQsH24PerformanceEntry 234881024}

pr1645v2ATMPerInPQsH24PerformanceDirTxPkts OBJECT-TYPE
   SYNTAX      Counter64
   MAX-ACCESS  read-only
   STATUS      current
   DESCRIPTION
      "Path: atm.performance.pvcTable.inPriorityQueues.h24Performance.directTxPkts

       64 bit unsigned wrappable counter."
   ::= {pr1645v2ATMPerInPQsH24PerformanceEntry 33554432}

pr1645v2ATMPerInPQsH24PerformanceQdPkts OBJECT-TYPE
   SYNTAX      Counter64
   MAX-ACCESS  read-only
   STATUS      current
   DESCRIPTION
      "Path: atm.performance.pvcTable.inPriorityQueues.h24Performance.queuedPkts

       64 bit unsigned wrappable counter."
   ::= {pr1645v2ATMPerInPQsH24PerformanceEntry 50331648}

pr1645v2ATMPerInPQsH24PerformanceDropPkts OBJECT-TYPE
   SYNTAX      Counter64
   MAX-ACCESS  read-only
   STATUS      current
   DESCRIPTION
      "Path: atm.performance.pvcTable.inPriorityQueues.h24Performance.droppedPkts

       64 bit unsigned wrappable counter."
   ::= {pr1645v2ATMPerInPQsH24PerformanceEntry 67108864}

pr1645v2ATMPerInPQsH24PerformanceRDropPkts OBJECT-TYPE
   SYNTAX      Counter64
   MAX-ACCESS  read-only
   STATUS      current
   DESCRIPTION
      "Path: atm.performance.pvcTable.inPriorityQueues.h24Performance.redDroppedPkts

       64 bit unsigned wrappable counter."
   ::= {pr1645v2ATMPerInPQsH24PerformanceEntry 201326592}

pr1645v2ATMPerInPQsH24PerformanceCirTxPkts OBJECT-TYPE
   SYNTAX      Counter64
   MAX-ACCESS  read-only
   STATUS      current
   DESCRIPTION
      "Path: atm.performance.pvcTable.inPriorityQueues.h24Performance.cirTxPkts

       64 bit unsigned wrappable counter."
   ::= {pr1645v2ATMPerInPQsH24PerformanceEntry 83886080}

pr1645v2ATMPerInPQsH24PerformanceEirTxPkts OBJECT-TYPE
   SYNTAX      Counter64
   MAX-ACCESS  read-only
   STATUS      current
   DESCRIPTION
      "Path: atm.performance.pvcTable.inPriorityQueues.h24Performance.eirTxPkts

       64 bit unsigned wrappable counter."
   ::= {pr1645v2ATMPerInPQsH24PerformanceEntry 100663296}

pr1645v2ATMPerInPQsH24PerformanceViolTxPkts OBJECT-TYPE
   SYNTAX      Counter64
   MAX-ACCESS  read-only
   STATUS      current
   DESCRIPTION
      "Path: atm.performance.pvcTable.inPriorityQueues.h24Performance.violateTxPkts

       64 bit unsigned wrappable counter."
   ::= {pr1645v2ATMPerInPQsH24PerformanceEntry 301989888}

pr1645v2ATMPerInPQsH24PerformanceTotOcts OBJECT-TYPE
   SYNTAX      Counter64
   MAX-ACCESS  read-only
   STATUS      current
   DESCRIPTION
      "Path: atm.performance.pvcTable.inPriorityQueues.h24Performance.totalOctets

       64 bit unsigned wrappable counter."
   ::= {pr1645v2ATMPerInPQsH24PerformanceEntry 251658240}

pr1645v2ATMPerInPQsH24PerformanceDirTxOcts OBJECT-TYPE
   SYNTAX      Counter64
   MAX-ACCESS  read-only
   STATUS      current
   DESCRIPTION
      "Path: atm.performance.pvcTable.inPriorityQueues.h24Performance.directTxOctets

       64 bit unsigned wrappable counter."
   ::= {pr1645v2ATMPerInPQsH24PerformanceEntry 117440512}

pr1645v2ATMPerInPQsH24PerformanceQdOcts OBJECT-TYPE
   SYNTAX      Counter64
   MAX-ACCESS  read-only
   STATUS      current
   DESCRIPTION
      "Path: atm.performance.pvcTable.inPriorityQueues.h24Performance.queuedOctets

       64 bit unsigned wrappable counter."
   ::= {pr1645v2ATMPerInPQsH24PerformanceEntry 134217728}

pr1645v2ATMPerInPQsH24PerformanceDropOcts OBJECT-TYPE
   SYNTAX      Counter64
   MAX-ACCESS  read-only
   STATUS      current
   DESCRIPTION
      "Path: atm.performance.pvcTable.inPriorityQueues.h24Performance.droppedOctets

       64 bit unsigned wrappable counter."
   ::= {pr1645v2ATMPerInPQsH24PerformanceEntry 150994944}

pr1645v2ATMPerInPQsH24PerformanceRDropOcts OBJECT-TYPE
   SYNTAX      Counter64
   MAX-ACCESS  read-only
   STATUS      current
   DESCRIPTION
      "Path: atm.performance.pvcTable.inPriorityQueues.h24Performance.redDroppedOctets

       64 bit unsigned wrappable counter."
   ::= {pr1645v2ATMPerInPQsH24PerformanceEntry 218103808}

pr1645v2ATMPerInPQsH24PerformanceCirTxOcts OBJECT-TYPE
   SYNTAX      Counter64
   MAX-ACCESS  read-only
   STATUS      current
   DESCRIPTION
      "Path: atm.performance.pvcTable.inPriorityQueues.h24Performance.cirTxOctets

       64 bit unsigned wrappable counter."
   ::= {pr1645v2ATMPerInPQsH24PerformanceEntry 167772160}

pr1645v2ATMPerInPQsH24PerformanceEirTxOcts OBJECT-TYPE
   SYNTAX      Counter64
   MAX-ACCESS  read-only
   STATUS      current
   DESCRIPTION
      "Path: atm.performance.pvcTable.inPriorityQueues.h24Performance.eirTxOctets

       64 bit unsigned wrappable counter."
   ::= {pr1645v2ATMPerInPQsH24PerformanceEntry 184549376}

pr1645v2ATMPerInPQsH24PerformanceViolTxOcts OBJECT-TYPE
   SYNTAX      Counter64
   MAX-ACCESS  read-only
   STATUS      current
   DESCRIPTION
      "Path: atm.performance.pvcTable.inPriorityQueues.h24Performance.violateTxOctets

       64 bit unsigned wrappable counter."
   ::= {pr1645v2ATMPerInPQsH24PerformanceEntry 318767104}

pr1645v2ATMPerInPQsH24PerformanceBandwidth OBJECT-TYPE
   SYNTAX      Integer32
   MAX-ACCESS  read-only
   STATUS      current
   DESCRIPTION
      "Path: atm.performance.pvcTable.inPriorityQueues.h24Performance.bandwidth

       unit name = bps
       formula = 8 * ; 8 /"
   ::= {pr1645v2ATMPerInPQsH24PerformanceEntry 268435456}

pr1645v2ATMPerInPQsD7Performance OBJECT-TYPE
   SYNTAX      SEQUENCE OF Pr1645v2ATMPerInPQsD7PerformanceEntry
   MAX-ACCESS  not-accessible
   STATUS      current
   DESCRIPTION
      ""
   ::= {pr1645v2ATMPer 101122048}

pr1645v2ATMPerInPQsD7PerformanceEntry OBJECT-TYPE
   SYNTAX      Pr1645v2ATMPerInPQsD7PerformanceEntry
   MAX-ACCESS  not-accessible
   STATUS      current
   DESCRIPTION
      ""
   INDEX      { pr1645v2ATMPerTableIx,
                pr1645v2ATMPerInPQsTableIx,
                pr1645v2ATMPerInPQsD7PerformanceTableIx }
   ::= {pr1645v2ATMPerInPQsD7Performance 1}

Pr1645v2ATMPerInPQsD7PerformanceEntry ::=
   SEQUENCE
      {
      pr1645v2ATMPerInPQsD7PerformanceTableIx
         TableIndex,
      pr1645v2ATMPerInPQsD7PerformanceSysUpTime
         TimeTicks,
      pr1645v2ATMPerInPQsD7PerformanceTotPkts
         Counter64,
      pr1645v2ATMPerInPQsD7PerformanceDirTxPkts
         Counter64,
      pr1645v2ATMPerInPQsD7PerformanceQdPkts
         Counter64,
      pr1645v2ATMPerInPQsD7PerformanceDropPkts
         Counter64,
      pr1645v2ATMPerInPQsD7PerformanceRDropPkts
         Counter64,
      pr1645v2ATMPerInPQsD7PerformanceCirTxPkts
         Counter64,
      pr1645v2ATMPerInPQsD7PerformanceEirTxPkts
         Counter64,
      pr1645v2ATMPerInPQsD7PerformanceViolTxPkts
         Counter64,
      pr1645v2ATMPerInPQsD7PerformanceTotOcts
         Counter64,
      pr1645v2ATMPerInPQsD7PerformanceDirTxOcts
         Counter64,
      pr1645v2ATMPerInPQsD7PerformanceQdOcts
         Counter64,
      pr1645v2ATMPerInPQsD7PerformanceDropOcts
         Counter64,
      pr1645v2ATMPerInPQsD7PerformanceRDropOcts
         Counter64,
      pr1645v2ATMPerInPQsD7PerformanceCirTxOcts
         Counter64,
      pr1645v2ATMPerInPQsD7PerformanceEirTxOcts
         Counter64,
      pr1645v2ATMPerInPQsD7PerformanceViolTxOcts
         Counter64,
      pr1645v2ATMPerInPQsD7PerformanceBandwidth
         Integer32
      }

pr1645v2ATMPerInPQsD7PerformanceTableIx OBJECT-TYPE
   SYNTAX      TableIndex
   MAX-ACCESS  not-accessible
   STATUS      current
   DESCRIPTION
      ""
   ::= {pr1645v2ATMPerInPQsD7PerformanceEntry 11}

pr1645v2ATMPerInPQsD7PerformanceSysUpTime OBJECT-TYPE
   SYNTAX      TimeTicks
   MAX-ACCESS  read-only
   STATUS      current
   DESCRIPTION
      "Path: atm.performance.pvcTable.inPriorityQueues.d7Performance.sysUpTime

       Time in centi-second."
   ::= {pr1645v2ATMPerInPQsD7PerformanceEntry 16777216}

pr1645v2ATMPerInPQsD7PerformanceTotPkts OBJECT-TYPE
   SYNTAX      Counter64
   MAX-ACCESS  read-only
   STATUS      current
   DESCRIPTION
      "Path: atm.performance.pvcTable.inPriorityQueues.d7Performance.totalPkts

       64 bit unsigned wrappable counter."
   ::= {pr1645v2ATMPerInPQsD7PerformanceEntry 234881024}

pr1645v2ATMPerInPQsD7PerformanceDirTxPkts OBJECT-TYPE
   SYNTAX      Counter64
   MAX-ACCESS  read-only
   STATUS      current
   DESCRIPTION
      "Path: atm.performance.pvcTable.inPriorityQueues.d7Performance.directTxPkts

       64 bit unsigned wrappable counter."
   ::= {pr1645v2ATMPerInPQsD7PerformanceEntry 33554432}

pr1645v2ATMPerInPQsD7PerformanceQdPkts OBJECT-TYPE
   SYNTAX      Counter64
   MAX-ACCESS  read-only
   STATUS      current
   DESCRIPTION
      "Path: atm.performance.pvcTable.inPriorityQueues.d7Performance.queuedPkts

       64 bit unsigned wrappable counter."
   ::= {pr1645v2ATMPerInPQsD7PerformanceEntry 50331648}

pr1645v2ATMPerInPQsD7PerformanceDropPkts OBJECT-TYPE
   SYNTAX      Counter64
   MAX-ACCESS  read-only
   STATUS      current
   DESCRIPTION
      "Path: atm.performance.pvcTable.inPriorityQueues.d7Performance.droppedPkts

       64 bit unsigned wrappable counter."
   ::= {pr1645v2ATMPerInPQsD7PerformanceEntry 67108864}

pr1645v2ATMPerInPQsD7PerformanceRDropPkts OBJECT-TYPE
   SYNTAX      Counter64
   MAX-ACCESS  read-only
   STATUS      current
   DESCRIPTION
      "Path: atm.performance.pvcTable.inPriorityQueues.d7Performance.redDroppedPkts

       64 bit unsigned wrappable counter."
   ::= {pr1645v2ATMPerInPQsD7PerformanceEntry 201326592}

pr1645v2ATMPerInPQsD7PerformanceCirTxPkts OBJECT-TYPE
   SYNTAX      Counter64
   MAX-ACCESS  read-only
   STATUS      current
   DESCRIPTION
      "Path: atm.performance.pvcTable.inPriorityQueues.d7Performance.cirTxPkts

       64 bit unsigned wrappable counter."
   ::= {pr1645v2ATMPerInPQsD7PerformanceEntry 83886080}

pr1645v2ATMPerInPQsD7PerformanceEirTxPkts OBJECT-TYPE
   SYNTAX      Counter64
   MAX-ACCESS  read-only
   STATUS      current
   DESCRIPTION
      "Path: atm.performance.pvcTable.inPriorityQueues.d7Performance.eirTxPkts

       64 bit unsigned wrappable counter."
   ::= {pr1645v2ATMPerInPQsD7PerformanceEntry 100663296}

pr1645v2ATMPerInPQsD7PerformanceViolTxPkts OBJECT-TYPE
   SYNTAX      Counter64
   MAX-ACCESS  read-only
   STATUS      current
   DESCRIPTION
      "Path: atm.performance.pvcTable.inPriorityQueues.d7Performance.violateTxPkts

       64 bit unsigned wrappable counter."
   ::= {pr1645v2ATMPerInPQsD7PerformanceEntry 301989888}

pr1645v2ATMPerInPQsD7PerformanceTotOcts OBJECT-TYPE
   SYNTAX      Counter64
   MAX-ACCESS  read-only
   STATUS      current
   DESCRIPTION
      "Path: atm.performance.pvcTable.inPriorityQueues.d7Performance.totalOctets

       64 bit unsigned wrappable counter."
   ::= {pr1645v2ATMPerInPQsD7PerformanceEntry 251658240}

pr1645v2ATMPerInPQsD7PerformanceDirTxOcts OBJECT-TYPE
   SYNTAX      Counter64
   MAX-ACCESS  read-only
   STATUS      current
   DESCRIPTION
      "Path: atm.performance.pvcTable.inPriorityQueues.d7Performance.directTxOctets

       64 bit unsigned wrappable counter."
   ::= {pr1645v2ATMPerInPQsD7PerformanceEntry 117440512}

pr1645v2ATMPerInPQsD7PerformanceQdOcts OBJECT-TYPE
   SYNTAX      Counter64
   MAX-ACCESS  read-only
   STATUS      current
   DESCRIPTION
      "Path: atm.performance.pvcTable.inPriorityQueues.d7Performance.queuedOctets

       64 bit unsigned wrappable counter."
   ::= {pr1645v2ATMPerInPQsD7PerformanceEntry 134217728}

pr1645v2ATMPerInPQsD7PerformanceDropOcts OBJECT-TYPE
   SYNTAX      Counter64
   MAX-ACCESS  read-only
   STATUS      current
   DESCRIPTION
      "Path: atm.performance.pvcTable.inPriorityQueues.d7Performance.droppedOctets

       64 bit unsigned wrappable counter."
   ::= {pr1645v2ATMPerInPQsD7PerformanceEntry 150994944}

pr1645v2ATMPerInPQsD7PerformanceRDropOcts OBJECT-TYPE
   SYNTAX      Counter64
   MAX-ACCESS  read-only
   STATUS      current
   DESCRIPTION
      "Path: atm.performance.pvcTable.inPriorityQueues.d7Performance.redDroppedOctets

       64 bit unsigned wrappable counter."
   ::= {pr1645v2ATMPerInPQsD7PerformanceEntry 218103808}

pr1645v2ATMPerInPQsD7PerformanceCirTxOcts OBJECT-TYPE
   SYNTAX      Counter64
   MAX-ACCESS  read-only
   STATUS      current
   DESCRIPTION
      "Path: atm.performance.pvcTable.inPriorityQueues.d7Performance.cirTxOctets

       64 bit unsigned wrappable counter."
   ::= {pr1645v2ATMPerInPQsD7PerformanceEntry 167772160}

pr1645v2ATMPerInPQsD7PerformanceEirTxOcts OBJECT-TYPE
   SYNTAX      Counter64
   MAX-ACCESS  read-only
   STATUS      current
   DESCRIPTION
      "Path: atm.performance.pvcTable.inPriorityQueues.d7Performance.eirTxOctets

       64 bit unsigned wrappable counter."
   ::= {pr1645v2ATMPerInPQsD7PerformanceEntry 184549376}

pr1645v2ATMPerInPQsD7PerformanceViolTxOcts OBJECT-TYPE
   SYNTAX      Counter64
   MAX-ACCESS  read-only
   STATUS      current
   DESCRIPTION
      "Path: atm.performance.pvcTable.inPriorityQueues.d7Performance.violateTxOctets

       64 bit unsigned wrappable counter."
   ::= {pr1645v2ATMPerInPQsD7PerformanceEntry 318767104}

pr1645v2ATMPerInPQsD7PerformanceBandwidth OBJECT-TYPE
   SYNTAX      Integer32
   MAX-ACCESS  read-only
   STATUS      current
   DESCRIPTION
      "Path: atm.performance.pvcTable.inPriorityQueues.d7Performance.bandwidth

       unit name = bps
       formula = 8 * ; 8 /"
   ::= {pr1645v2ATMPerInPQsD7PerformanceEntry 268435456}

pr1645v2ATMPerOutPQs OBJECT-TYPE
   SYNTAX      SEQUENCE OF Pr1645v2ATMPerOutPQsEntry
   MAX-ACCESS  not-accessible
   STATUS      current
   DESCRIPTION
      ""
   ::= {pr1645v2ATMPer 83886080}

pr1645v2ATMPerOutPQsEntry OBJECT-TYPE
   SYNTAX      Pr1645v2ATMPerOutPQsEntry
   MAX-ACCESS  not-accessible
   STATUS      current
   DESCRIPTION
      ""
   INDEX      { pr1645v2ATMPerTableIx,
                pr1645v2ATMPerOutPQsTableIx }
   ::= {pr1645v2ATMPerOutPQs 1}

Pr1645v2ATMPerOutPQsEntry ::=
   SEQUENCE
      {
      pr1645v2ATMPerOutPQsTableIx
         TableIndex,
      pr1645v2ATMPerOutPQsName
         INTEGER,
      pr1645v2ATMPerOutPQsLength
         Integer32,
      pr1645v2ATMPerOutPQsOctetLength
         Integer32,
      pr1645v2ATMPerOutPQsRedLength
         Integer32,
      pr1645v2ATMPerOutPQsPacketsTotal
         Counter64,
      pr1645v2ATMPerOutPQsPacketsDirectTx
         Counter64,
      pr1645v2ATMPerOutPQsPacketsQueued
         Counter64,
      pr1645v2ATMPerOutPQsPacketsDropped
         Counter64,
      pr1645v2ATMPerOutPQsPacketsRedDropped
         Counter64,
      pr1645v2ATMPerOutPQsPacketsCirTx
         Counter64,
      pr1645v2ATMPerOutPQsPacketsEirTx
         Counter64,
      pr1645v2ATMPerOutPQsPacketsViolateTx
         Counter64,
      pr1645v2ATMPerOutPQsOctetsTotal
         Counter64,
      pr1645v2ATMPerOutPQsOctetsDirectTx
         Counter64,
      pr1645v2ATMPerOutPQsOctetsQueued
         Counter64,
      pr1645v2ATMPerOutPQsOctetsDropped
         Counter64,
      pr1645v2ATMPerOutPQsOctetsRedDropped
         Counter64,
      pr1645v2ATMPerOutPQsOctetsCirTx
         Counter64,
      pr1645v2ATMPerOutPQsOctetsEirTx
         Counter64,
      pr1645v2ATMPerOutPQsOctetsViolateTx
         Counter64,
      pr1645v2ATMPerOutPQsOctetsBandwidth15sec
         Integer32,
      pr1645v2ATMPerOutPQsOctetsBandwidth30sec
         Integer32,
      pr1645v2ATMPerOutPQsOctetsBandwidth1min
         Integer32,
      pr1645v2ATMPerOutPQsOctetsBandwidth2min
         Integer32,
      pr1645v2ATMPerOutPQsOctetsBandwidth5min
         Integer32
      }

pr1645v2ATMPerOutPQsTableIx OBJECT-TYPE
   SYNTAX      TableIndex
   MAX-ACCESS  not-accessible
   STATUS      current
   DESCRIPTION
      ""
   ::= {pr1645v2ATMPerOutPQsEntry 11}

pr1645v2ATMPerOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2ATMPerOutPQsEntry 16777216}

pr1645v2ATMPerOutPQsLength OBJECT-TYPE
   SYNTAX      Integer32
   MAX-ACCESS  read-only
   STATUS      current
   DESCRIPTION
      "Path: atm.performance.pvcTable.outPriorityQueues.length"
   ::= {pr1645v2ATMPerOutPQsEntry 33554432}

pr1645v2ATMPerOutPQsOctetLength OBJECT-TYPE
   SYNTAX      Integer32
   MAX-ACCESS  read-only
   STATUS      current
   DESCRIPTION
      "Path: atm.performance.pvcTable.outPriorityQueues.octetLength"
   ::= {pr1645v2ATMPerOutPQsEntry 150994944}

pr1645v2ATMPerOutPQsRedLength OBJECT-TYPE
   SYNTAX      Integer32
   MAX-ACCESS  read-only
   STATUS      current
   DESCRIPTION
      "Path: atm.performance.pvcTable.outPriorityQueues.redLength"
   ::= {pr1645v2ATMPerOutPQsEntry 134217728}

pr1645v2ATMPerOutPQsPacketsTotal OBJECT-TYPE
   SYNTAX      Counter64
   MAX-ACCESS  read-only
   STATUS      current
   DESCRIPTION
      "Path: atm.performance.pvcTable.outPriorityQueues.packets.total

       64 bit unsigned wrappable counter."
   ::= {pr1645v2ATMPerOutPQsEntry 50790400}

pr1645v2ATMPerOutPQsPacketsDirectTx OBJECT-TYPE
   SYNTAX      Counter64
   MAX-ACCESS  read-only
   STATUS      current
   DESCRIPTION
      "Path: atm.performance.pvcTable.outPriorityQueues.packets.directTx

       64 bit unsigned wrappable counter."
   ::= {pr1645v2ATMPerOutPQsEntry 50397184}

pr1645v2ATMPerOutPQsPacketsQueued OBJECT-TYPE
   SYNTAX      Counter64
   MAX-ACCESS  read-only
   STATUS      current
   DESCRIPTION
      "Path: atm.performance.pvcTable.outPriorityQueues.packets.queued

       64 bit unsigned wrappable counter."
   ::= {pr1645v2ATMPerOutPQsEntry 50462720}

pr1645v2ATMPerOutPQsPacketsDropped OBJECT-TYPE
   SYNTAX      Counter64
   MAX-ACCESS  read-only
   STATUS      current
   DESCRIPTION
      "Path: atm.performance.pvcTable.outPriorityQueues.packets.dropped

       64 bit unsigned wrappable counter."
   ::= {pr1645v2ATMPerOutPQsEntry 50528256}

pr1645v2ATMPerOutPQsPacketsRedDropped OBJECT-TYPE
   SYNTAX      Counter64
   MAX-ACCESS  read-only
   STATUS      current
   DESCRIPTION
      "Path: atm.performance.pvcTable.outPriorityQueues.packets.redDropped

       64 bit unsigned wrappable counter."
   ::= {pr1645v2ATMPerOutPQsEntry 50724864}

pr1645v2ATMPerOutPQsPacketsCirTx OBJECT-TYPE
   SYNTAX      Counter64
   MAX-ACCESS  read-only
   STATUS      current
   DESCRIPTION
      "Path: atm.performance.pvcTable.outPriorityQueues.packets.cirTx

       64 bit unsigned wrappable counter."
   ::= {pr1645v2ATMPerOutPQsEntry 50593792}

pr1645v2ATMPerOutPQsPacketsEirTx OBJECT-TYPE
   SYNTAX      Counter64
   MAX-ACCESS  read-only
   STATUS      current
   DESCRIPTION
      "Path: atm.performance.pvcTable.outPriorityQueues.packets.eirTx

       64 bit unsigned wrappable counter."
   ::= {pr1645v2ATMPerOutPQsEntry 50659328}

pr1645v2ATMPerOutPQsPacketsViolateTx OBJECT-TYPE
   SYNTAX      Counter64
   MAX-ACCESS  read-only
   STATUS      current
   DESCRIPTION
      "Path: atm.performance.pvcTable.outPriorityQueues.packets.violateTx

       64 bit unsigned wrappable counter."
   ::= {pr1645v2ATMPerOutPQsEntry 50855936}

pr1645v2ATMPerOutPQsOctetsTotal OBJECT-TYPE
   SYNTAX      Counter64
   MAX-ACCESS  read-only
   STATUS      current
   DESCRIPTION
      "Path: atm.performance.pvcTable.outPriorityQueues.octets.total

       64 bit unsigned wrappable counter."
   ::= {pr1645v2ATMPerOutPQsEntry 67567616}

pr1645v2ATMPerOutPQsOctetsDirectTx OBJECT-TYPE
   SYNTAX      Counter64
   MAX-ACCESS  read-only
   STATUS      current
   DESCRIPTION
      "Path: atm.performance.pvcTable.outPriorityQueues.octets.directTx

       64 bit unsigned wrappable counter."
   ::= {pr1645v2ATMPerOutPQsEntry 67174400}

pr1645v2ATMPerOutPQsOctetsQueued OBJECT-TYPE
   SYNTAX      Counter64
   MAX-ACCESS  read-only
   STATUS      current
   DESCRIPTION
      "Path: atm.performance.pvcTable.outPriorityQueues.octets.queued

       64 bit unsigned wrappable counter."
   ::= {pr1645v2ATMPerOutPQsEntry 67239936}

pr1645v2ATMPerOutPQsOctetsDropped OBJECT-TYPE
   SYNTAX      Counter64
   MAX-ACCESS  read-only
   STATUS      current
   DESCRIPTION
      "Path: atm.performance.pvcTable.outPriorityQueues.octets.dropped

       64 bit unsigned wrappable counter."
   ::= {pr1645v2ATMPerOutPQsEntry 67305472}

pr1645v2ATMPerOutPQsOctetsRedDropped OBJECT-TYPE
   SYNTAX      Counter64
   MAX-ACCESS  read-only
   STATUS      current
   DESCRIPTION
      "Path: atm.performance.pvcTable.outPriorityQueues.octets.redDropped

       64 bit unsigned wrappable counter."
   ::= {pr1645v2ATMPerOutPQsEntry 67502080}

pr1645v2ATMPerOutPQsOctetsCirTx OBJECT-TYPE
   SYNTAX      Counter64
   MAX-ACCESS  read-only
   STATUS      current
   DESCRIPTION
      "Path: atm.performance.pvcTable.outPriorityQueues.octets.cirTx

       64 bit unsigned wrappable counter."
   ::= {pr1645v2ATMPerOutPQsEntry 67371008}

pr1645v2ATMPerOutPQsOctetsEirTx OBJECT-TYPE
   SYNTAX      Counter64
   MAX-ACCESS  read-only
   STATUS      current
   DESCRIPTION
      "Path: atm.performance.pvcTable.outPriorityQueues.octets.eirTx

       64 bit unsigned wrappable counter."
   ::= {pr1645v2ATMPerOutPQsEntry 67436544}

pr1645v2ATMPerOutPQsOctetsViolateTx OBJECT-TYPE
   SYNTAX      Counter64
   MAX-ACCESS  read-only
   STATUS      current
   DESCRIPTION
      "Path: atm.performance.pvcTable.outPriorityQueues.octets.violateTx

       64 bit unsigned wrappable counter."
   ::= {pr1645v2ATMPerOutPQsEntry 67633152}

pr1645v2ATMPerOutPQsOctetsBandwidth15sec OBJECT-TYPE
   SYNTAX      Integer32
   MAX-ACCESS  read-only
   STATUS      current
   DESCRIPTION
      "Path: atm.performance.pvcTable.outPriorityQueues.octets.bandwidth.15sec

       unit name = bps
       formula = 8 * ; 8 /"
   ::= {pr1645v2ATMPerOutPQsEntry 70386944}

pr1645v2ATMPerOutPQsOctetsBandwidth30sec OBJECT-TYPE
   SYNTAX      Integer32
   MAX-ACCESS  read-only
   STATUS      current
   DESCRIPTION
      "Path: atm.performance.pvcTable.outPriorityQueues.octets.bandwidth.30sec

       unit name = bps
       formula = 8 * ; 8 /"
   ::= {pr1645v2ATMPerOutPQsEntry 70388224}

pr1645v2ATMPerOutPQsOctetsBandwidth1min OBJECT-TYPE
   SYNTAX      Integer32
   MAX-ACCESS  read-only
   STATUS      current
   DESCRIPTION
      "Path: atm.performance.pvcTable.outPriorityQueues.octets.bandwidth.1min

       unit name = bps
       formula = 8 * ; 8 /"
   ::= {pr1645v2ATMPerOutPQsEntry 70390784}

pr1645v2ATMPerOutPQsOctetsBandwidth2min OBJECT-TYPE
   SYNTAX      Integer32
   MAX-ACCESS  read-only
   STATUS      current
   DESCRIPTION
      "Path: atm.performance.pvcTable.outPriorityQueues.octets.bandwidth.2min

       unit name = bps
       formula = 8 * ; 8 /"
   ::= {pr1645v2ATMPerOutPQsEntry 70395904}

pr1645v2ATMPerOutPQsOctetsBandwidth5min OBJECT-TYPE
   SYNTAX      Integer32
   MAX-ACCESS  read-only
   STATUS      current
   DESCRIPTION
      "Path: atm.performance.pvcTable.outPriorityQueues.octets.bandwidth.5min

       unit name = bps
       formula = 8 * ; 8 /"
   ::= {pr1645v2ATMPerOutPQsEntry 70411264}

pr1645v2ATMPerOutPQsH2Performance OBJECT-TYPE
   SYNTAX      SEQUENCE OF Pr1645v2ATMPerOutPQsH2PerformanceEntry
   MAX-ACCESS  not-accessible
   STATUS      current
   DESCRIPTION
      ""
   ::= {pr1645v2ATMPer 84213760}

pr1645v2ATMPerOutPQsH2PerformanceEntry OBJECT-TYPE
   SYNTAX      Pr1645v2ATMPerOutPQsH2PerformanceEntry
   MAX-ACCESS  not-accessible
   STATUS      current
   DESCRIPTION
      ""
   INDEX      { pr1645v2ATMPerTableIx,
                pr1645v2ATMPerOutPQsTableIx,
                pr1645v2ATMPerOutPQsH2PerformanceTableIx }
   ::= {pr1645v2ATMPerOutPQsH2Performance 1}

Pr1645v2ATMPerOutPQsH2PerformanceEntry ::=
   SEQUENCE
      {
      pr1645v2ATMPerOutPQsH2PerformanceTableIx
         TableIndex,
      pr1645v2ATMPerOutPQsH2PerformanceSysUpTime
         TimeTicks,
      pr1645v2ATMPerOutPQsH2PerformanceTotPkts
         Counter64,
      pr1645v2ATMPerOutPQsH2PerformanceDirTxPkts
         Counter64,
      pr1645v2ATMPerOutPQsH2PerformanceQdPkts
         Counter64,
      pr1645v2ATMPerOutPQsH2PerformanceDropPkts
         Counter64,
      pr1645v2ATMPerOutPQsH2PerformanceRDropPkts
         Counter64,
      pr1645v2ATMPerOutPQsH2PerformanceCirTxPkts
         Counter64,
      pr1645v2ATMPerOutPQsH2PerformanceEirTxPkts
         Counter64,
      pr1645v2ATMPerOutPQsH2PerformanceViolTxPkts
         Counter64,
      pr1645v2ATMPerOutPQsH2PerformanceTotOcts
         Counter64,
      pr1645v2ATMPerOutPQsH2PerformanceDirTxOcts
         Counter64,
      pr1645v2ATMPerOutPQsH2PerformanceQdOcts
         Counter64,
      pr1645v2ATMPerOutPQsH2PerformanceDropOcts
         Counter64,
      pr1645v2ATMPerOutPQsH2PerformanceRDropOcts
         Counter64,
      pr1645v2ATMPerOutPQsH2PerformanceCirTxOcts
         Counter64,
      pr1645v2ATMPerOutPQsH2PerformanceEirTxOcts
         Counter64,
      pr1645v2ATMPerOutPQsH2PerformanceViolTxOcts
         Counter64,
      pr1645v2ATMPerOutPQsH2PerformanceBandwidth
         Integer32
      }

pr1645v2ATMPerOutPQsH2PerformanceTableIx OBJECT-TYPE
   SYNTAX      TableIndex
   MAX-ACCESS  not-accessible
   STATUS      current
   DESCRIPTION
      ""
   ::= {pr1645v2ATMPerOutPQsH2PerformanceEntry 11}

pr1645v2ATMPerOutPQsH2PerformanceSysUpTime OBJECT-TYPE
   SYNTAX      TimeTicks
   MAX-ACCESS  read-only
   STATUS      current
   DESCRIPTION
      "Path: atm.performance.pvcTable.outPriorityQueues.h2Performance.sysUpTime

       Time in centi-second."
   ::= {pr1645v2ATMPerOutPQsH2PerformanceEntry 16777216}

pr1645v2ATMPerOutPQsH2PerformanceTotPkts OBJECT-TYPE
   SYNTAX      Counter64
   MAX-ACCESS  read-only
   STATUS      current
   DESCRIPTION
      "Path: atm.performance.pvcTable.outPriorityQueues.h2Performance.totalPkts

       64 bit unsigned wrappable counter."
   ::= {pr1645v2ATMPerOutPQsH2PerformanceEntry 234881024}

pr1645v2ATMPerOutPQsH2PerformanceDirTxPkts OBJECT-TYPE
   SYNTAX      Counter64
   MAX-ACCESS  read-only
   STATUS      current
   DESCRIPTION
      "Path: atm.performance.pvcTable.outPriorityQueues.h2Performance.directTxPkts

       64 bit unsigned wrappable counter."
   ::= {pr1645v2ATMPerOutPQsH2PerformanceEntry 33554432}

pr1645v2ATMPerOutPQsH2PerformanceQdPkts OBJECT-TYPE
   SYNTAX      Counter64
   MAX-ACCESS  read-only
   STATUS      current
   DESCRIPTION
      "Path: atm.performance.pvcTable.outPriorityQueues.h2Performance.queuedPkts

       64 bit unsigned wrappable counter."
   ::= {pr1645v2ATMPerOutPQsH2PerformanceEntry 50331648}

pr1645v2ATMPerOutPQsH2PerformanceDropPkts OBJECT-TYPE
   SYNTAX      Counter64
   MAX-ACCESS  read-only
   STATUS      current
   DESCRIPTION
      "Path: atm.performance.pvcTable.outPriorityQueues.h2Performance.droppedPkts

       64 bit unsigned wrappable counter."
   ::= {pr1645v2ATMPerOutPQsH2PerformanceEntry 67108864}

pr1645v2ATMPerOutPQsH2PerformanceRDropPkts OBJECT-TYPE
   SYNTAX      Counter64
   MAX-ACCESS  read-only
   STATUS      current
   DESCRIPTION
      "Path: atm.performance.pvcTable.outPriorityQueues.h2Performance.redDroppedPkts

       64 bit unsigned wrappable counter."
   ::= {pr1645v2ATMPerOutPQsH2PerformanceEntry 201326592}

pr1645v2ATMPerOutPQsH2PerformanceCirTxPkts OBJECT-TYPE
   SYNTAX      Counter64
   MAX-ACCESS  read-only
   STATUS      current
   DESCRIPTION
      "Path: atm.performance.pvcTable.outPriorityQueues.h2Performance.cirTxPkts

       64 bit unsigned wrappable counter."
   ::= {pr1645v2ATMPerOutPQsH2PerformanceEntry 83886080}

pr1645v2ATMPerOutPQsH2PerformanceEirTxPkts OBJECT-TYPE
   SYNTAX      Counter64
   MAX-ACCESS  read-only
   STATUS      current
   DESCRIPTION
      "Path: atm.performance.pvcTable.outPriorityQueues.h2Performance.eirTxPkts

       64 bit unsigned wrappable counter."
   ::= {pr1645v2ATMPerOutPQsH2PerformanceEntry 100663296}

pr1645v2ATMPerOutPQsH2PerformanceViolTxPkts OBJECT-TYPE
   SYNTAX      Counter64
   MAX-ACCESS  read-only
   STATUS      current
   DESCRIPTION
      "Path: atm.performance.pvcTable.outPriorityQueues.h2Performance.violateTxPkts

       64 bit unsigned wrappable counter."
   ::= {pr1645v2ATMPerOutPQsH2PerformanceEntry 301989888}

pr1645v2ATMPerOutPQsH2PerformanceTotOcts OBJECT-TYPE
   SYNTAX      Counter64
   MAX-ACCESS  read-only
   STATUS      current
   DESCRIPTION
      "Path: atm.performance.pvcTable.outPriorityQueues.h2Performance.totalOctets

       64 bit unsigned wrappable counter."
   ::= {pr1645v2ATMPerOutPQsH2PerformanceEntry 251658240}

pr1645v2ATMPerOutPQsH2PerformanceDirTxOcts OBJECT-TYPE
   SYNTAX      Counter64
   MAX-ACCESS  read-only
   STATUS      current
   DESCRIPTION
      "Path: atm.performance.pvcTable.outPriorityQueues.h2Performance.directTxOctets

       64 bit unsigned wrappable counter."
   ::= {pr1645v2ATMPerOutPQsH2PerformanceEntry 117440512}

pr1645v2ATMPerOutPQsH2PerformanceQdOcts OBJECT-TYPE
   SYNTAX      Counter64
   MAX-ACCESS  read-only
   STATUS      current
   DESCRIPTION
      "Path: atm.performance.pvcTable.outPriorityQueues.h2Performance.queuedOctets

       64 bit unsigned wrappable counter."
   ::= {pr1645v2ATMPerOutPQsH2PerformanceEntry 134217728}

pr1645v2ATMPerOutPQsH2PerformanceDropOcts OBJECT-TYPE
   SYNTAX      Counter64
   MAX-ACCESS  read-only
   STATUS      current
   DESCRIPTION
      "Path: atm.performance.pvcTable.outPriorityQueues.h2Performance.droppedOctets

       64 bit unsigned wrappable counter."
   ::= {pr1645v2ATMPerOutPQsH2PerformanceEntry 150994944}

pr1645v2ATMPerOutPQsH2PerformanceRDropOcts OBJECT-TYPE
   SYNTAX      Counter64
   MAX-ACCESS  read-only
   STATUS      current
   DESCRIPTION
      "Path: atm.performance.pvcTable.outPriorityQueues.h2Performance.redDroppedOctets

       64 bit unsigned wrappable counter."
   ::= {pr1645v2ATMPerOutPQsH2PerformanceEntry 218103808}

pr1645v2ATMPerOutPQsH2PerformanceCirTxOcts OBJECT-TYPE
   SYNTAX      Counter64
   MAX-ACCESS  read-only
   STATUS      current
   DESCRIPTION
      "Path: atm.performance.pvcTable.outPriorityQueues.h2Performance.cirTxOctets

       64 bit unsigned wrappable counter."
   ::= {pr1645v2ATMPerOutPQsH2PerformanceEntry 167772160}

pr1645v2ATMPerOutPQsH2PerformanceEirTxOcts OBJECT-TYPE
   SYNTAX      Counter64
   MAX-ACCESS  read-only
   STATUS      current
   DESCRIPTION
      "Path: atm.performance.pvcTable.outPriorityQueues.h2Performance.eirTxOctets

       64 bit unsigned wrappable counter."
   ::= {pr1645v2ATMPerOutPQsH2PerformanceEntry 184549376}

pr1645v2ATMPerOutPQsH2PerformanceViolTxOcts OBJECT-TYPE
   SYNTAX      Counter64
   MAX-ACCESS  read-only
   STATUS      current
   DESCRIPTION
      "Path: atm.performance.pvcTable.outPriorityQueues.h2Performance.violateTxOctets

       64 bit unsigned wrappable counter."
   ::= {pr1645v2ATMPerOutPQsH2PerformanceEntry 318767104}

pr1645v2ATMPerOutPQsH2PerformanceBandwidth OBJECT-TYPE
   SYNTAX      Integer32
   MAX-ACCESS  read-only
   STATUS      current
   DESCRIPTION
      "Path: atm.performance.pvcTable.outPriorityQueues.h2Performance.bandwidth

       unit name = bps
       formula = 8 * ; 8 /"
   ::= {pr1645v2ATMPerOutPQsH2PerformanceEntry 268435456}

pr1645v2ATMPerOutPQsH24Performance OBJECT-TYPE
   SYNTAX      SEQUENCE OF Pr1645v2ATMPerOutPQsH24PerformanceEntry
   MAX-ACCESS  not-accessible
   STATUS      current
   DESCRIPTION
      ""
   ::= {pr1645v2ATMPer 84279296}

pr1645v2ATMPerOutPQsH24PerformanceEntry OBJECT-TYPE
   SYNTAX      Pr1645v2ATMPerOutPQsH24PerformanceEntry
   MAX-ACCESS  not-accessible
   STATUS      current
   DESCRIPTION
      ""
   INDEX      { pr1645v2ATMPerTableIx,
                pr1645v2ATMPerOutPQsTableIx,
                pr1645v2ATMPerOutPQsH24PerformanceTableIx }
   ::= {pr1645v2ATMPerOutPQsH24Performance 1}

Pr1645v2ATMPerOutPQsH24PerformanceEntry ::=
   SEQUENCE
      {
      pr1645v2ATMPerOutPQsH24PerformanceTableIx
         TableIndex,
      pr1645v2ATMPerOutPQsH24PerformanceSysUpTime
         TimeTicks,
      pr1645v2ATMPerOutPQsH24PerformanceTotPkts
         Counter64,
      pr1645v2ATMPerOutPQsH24PerformanceDirTxPkts
         Counter64,
      pr1645v2ATMPerOutPQsH24PerformanceQdPkts
         Counter64,
      pr1645v2ATMPerOutPQsH24PerformanceDropPkts
         Counter64,
      pr1645v2ATMPerOutPQsH24PerformanceRDropPkts
         Counter64,
      pr1645v2ATMPerOutPQsH24PerformanceCirTxPkts
         Counter64,
      pr1645v2ATMPerOutPQsH24PerformanceEirTxPkts
         Counter64,
      pr1645v2ATMPerOutPQsH24PerformanceViolTxPkts
         Counter64,
      pr1645v2ATMPerOutPQsH24PerformanceTotOcts
         Counter64,
      pr1645v2ATMPerOutPQsH24PerformanceDirTxOcts
         Counter64,
      pr1645v2ATMPerOutPQsH24PerformanceQdOcts
         Counter64,
      pr1645v2ATMPerOutPQsH24PerformanceDropOcts
         Counter64,
      pr1645v2ATMPerOutPQsH24PerformanceRDropOcts
         Counter64,
      pr1645v2ATMPerOutPQsH24PerformanceCirTxOcts
         Counter64,
      pr1645v2ATMPerOutPQsH24PerformanceEirTxOcts
         Counter64,
      pr1645v2ATMPerOutPQsH24PerformanceViolTxOcts
         Counter64,
      pr1645v2ATMPerOutPQsH24PerformanceBandwidth
         Integer32
      }

pr1645v2ATMPerOutPQsH24PerformanceTableIx OBJECT-TYPE
   SYNTAX      TableIndex
   MAX-ACCESS  not-accessible
   STATUS      current
   DESCRIPTION
      ""
   ::= {pr1645v2ATMPerOutPQsH24PerformanceEntry 11}

pr1645v2ATMPerOutPQsH24PerformanceSysUpTime OBJECT-TYPE
   SYNTAX      TimeTicks
   MAX-ACCESS  read-only
   STATUS      current
   DESCRIPTION
      "Path: atm.performance.pvcTable.outPriorityQueues.h24Performance.sysUpTime

       Time in centi-second."
   ::= {pr1645v2ATMPerOutPQsH24PerformanceEntry 16777216}

pr1645v2ATMPerOutPQsH24PerformanceTotPkts OBJECT-TYPE
   SYNTAX      Counter64
   MAX-ACCESS  read-only
   STATUS      current
   DESCRIPTION
      "Path: atm.performance.pvcTable.outPriorityQueues.h24Performance.totalPkts

       64 bit unsigned wrappable counter."
   ::= {pr1645v2ATMPerOutPQsH24PerformanceEntry 234881024}

pr1645v2ATMPerOutPQsH24PerformanceDirTxPkts OBJECT-TYPE
   SYNTAX      Counter64
   MAX-ACCESS  read-only
   STATUS      current
   DESCRIPTION
      "Path: atm.performance.pvcTable.outPriorityQueues.h24Performance.directTxPkts

       64 bit unsigned wrappable counter."
   ::= {pr1645v2ATMPerOutPQsH24PerformanceEntry 33554432}

pr1645v2ATMPerOutPQsH24PerformanceQdPkts OBJECT-TYPE
   SYNTAX      Counter64
   MAX-ACCESS  read-only
   STATUS      current
   DESCRIPTION
      "Path: atm.performance.pvcTable.outPriorityQueues.h24Performance.queuedPkts

       64 bit unsigned wrappable counter."
   ::= {pr1645v2ATMPerOutPQsH24PerformanceEntry 50331648}

pr1645v2ATMPerOutPQsH24PerformanceDropPkts OBJECT-TYPE
   SYNTAX      Counter64
   MAX-ACCESS  read-only
   STATUS      current
   DESCRIPTION
      "Path: atm.performance.pvcTable.outPriorityQueues.h24Performance.droppedPkts

       64 bit unsigned wrappable counter."
   ::= {pr1645v2ATMPerOutPQsH24PerformanceEntry 67108864}

pr1645v2ATMPerOutPQsH24PerformanceRDropPkts OBJECT-TYPE
   SYNTAX      Counter64
   MAX-ACCESS  read-only
   STATUS      current
   DESCRIPTION
      "Path: atm.performance.pvcTable.outPriorityQueues.h24Performance.redDroppedPkts

       64 bit unsigned wrappable counter."
   ::= {pr1645v2ATMPerOutPQsH24PerformanceEntry 201326592}

pr1645v2ATMPerOutPQsH24PerformanceCirTxPkts OBJECT-TYPE
   SYNTAX      Counter64
   MAX-ACCESS  read-only
   STATUS      current
   DESCRIPTION
      "Path: atm.performance.pvcTable.outPriorityQueues.h24Performance.cirTxPkts

       64 bit unsigned wrappable counter."
   ::= {pr1645v2ATMPerOutPQsH24PerformanceEntry 83886080}

pr1645v2ATMPerOutPQsH24PerformanceEirTxPkts OBJECT-TYPE
   SYNTAX      Counter64
   MAX-ACCESS  read-only
   STATUS      current
   DESCRIPTION
      "Path: atm.performance.pvcTable.outPriorityQueues.h24Performance.eirTxPkts

       64 bit unsigned wrappable counter."
   ::= {pr1645v2ATMPerOutPQsH24PerformanceEntry 100663296}

pr1645v2ATMPerOutPQsH24PerformanceViolTxPkts OBJECT-TYPE
   SYNTAX      Counter64
   MAX-ACCESS  read-only
   STATUS      current
   DESCRIPTION
      "Path: atm.performance.pvcTable.outPriorityQueues.h24Performance.violateTxPkts

       64 bit unsigned wrappable counter."
   ::= {pr1645v2ATMPerOutPQsH24PerformanceEntry 301989888}

pr1645v2ATMPerOutPQsH24PerformanceTotOcts OBJECT-TYPE
   SYNTAX      Counter64
   MAX-ACCESS  read-only
   STATUS      current
   DESCRIPTION
      "Path: atm.performance.pvcTable.outPriorityQueues.h24Performance.totalOctets

       64 bit unsigned wrappable counter."
   ::= {pr1645v2ATMPerOutPQsH24PerformanceEntry 251658240}

pr1645v2ATMPerOutPQsH24PerformanceDirTxOcts OBJECT-TYPE
   SYNTAX      Counter64
   MAX-ACCESS  read-only
   STATUS      current
   DESCRIPTION
      "Path: atm.performance.pvcTable.outPriorityQueues.h24Performance.directTxOctets

       64 bit unsigned wrappable counter."
   ::= {pr1645v2ATMPerOutPQsH24PerformanceEntry 117440512}

pr1645v2ATMPerOutPQsH24PerformanceQdOcts OBJECT-TYPE
   SYNTAX      Counter64
   MAX-ACCESS  read-only
   STATUS      current
   DESCRIPTION
      "Path: atm.performance.pvcTable.outPriorityQueues.h24Performance.queuedOctets

       64 bit unsigned wrappable counter."
   ::= {pr1645v2ATMPerOutPQsH24PerformanceEntry 134217728}

pr1645v2ATMPerOutPQsH24PerformanceDropOcts OBJECT-TYPE
   SYNTAX      Counter64
   MAX-ACCESS  read-only
   STATUS      current
   DESCRIPTION
      "Path: atm.performance.pvcTable.outPriorityQueues.h24Performance.droppedOctets

       64 bit unsigned wrappable counter."
   ::= {pr1645v2ATMPerOutPQsH24PerformanceEntry 150994944}

pr1645v2ATMPerOutPQsH24PerformanceRDropOcts OBJECT-TYPE
   SYNTAX      Counter64
   MAX-ACCESS  read-only
   STATUS      current
   DESCRIPTION
      "Path: atm.performance.pvcTable.outPriorityQueues.h24Performance.redDroppedOctets

       64 bit unsigned wrappable counter."
   ::= {pr1645v2ATMPerOutPQsH24PerformanceEntry 218103808}

pr1645v2ATMPerOutPQsH24PerformanceCirTxOcts OBJECT-TYPE
   SYNTAX      Counter64
   MAX-ACCESS  read-only
   STATUS      current
   DESCRIPTION
      "Path: atm.performance.pvcTable.outPriorityQueues.h24Performance.cirTxOctets

       64 bit unsigned wrappable counter."
   ::= {pr1645v2ATMPerOutPQsH24PerformanceEntry 167772160}

pr1645v2ATMPerOutPQsH24PerformanceEirTxOcts OBJECT-TYPE
   SYNTAX      Counter64
   MAX-ACCESS  read-only
   STATUS      current
   DESCRIPTION
      "Path: atm.performance.pvcTable.outPriorityQueues.h24Performance.eirTxOctets

       64 bit unsigned wrappable counter."
   ::= {pr1645v2ATMPerOutPQsH24PerformanceEntry 184549376}

pr1645v2ATMPerOutPQsH24PerformanceViolTxOcts OBJECT-TYPE
   SYNTAX      Counter64
   MAX-ACCESS  read-only
   STATUS      current
   DESCRIPTION
      "Path: atm.performance.pvcTable.outPriorityQueues.h24Performance.violateTxOctets

       64 bit unsigned wrappable counter."
   ::= {pr1645v2ATMPerOutPQsH24PerformanceEntry 318767104}

pr1645v2ATMPerOutPQsH24PerformanceBandwidth OBJECT-TYPE
   SYNTAX      Integer32
   MAX-ACCESS  read-only
   STATUS      current
   DESCRIPTION
      "Path: atm.performance.pvcTable.outPriorityQueues.h24Performance.bandwidth

       unit name = bps
       formula = 8 * ; 8 /"
   ::= {pr1645v2ATMPerOutPQsH24PerformanceEntry 268435456}

pr1645v2ATMPerOutPQsD7Performance OBJECT-TYPE
   SYNTAX      SEQUENCE OF Pr1645v2ATMPerOutPQsD7PerformanceEntry
   MAX-ACCESS  not-accessible
   STATUS      current
   DESCRIPTION
      ""
   ::= {pr1645v2ATMPer 84344832}

pr1645v2ATMPerOutPQsD7PerformanceEntry OBJECT-TYPE
   SYNTAX      Pr1645v2ATMPerOutPQsD7PerformanceEntry
   MAX-ACCESS  not-accessible
   STATUS      current
   DESCRIPTION
      ""
   INDEX      { pr1645v2ATMPerTableIx,
                pr1645v2ATMPerOutPQsTableIx,
                pr1645v2ATMPerOutPQsD7PerformanceTableIx }
   ::= {pr1645v2ATMPerOutPQsD7Performance 1}

Pr1645v2ATMPerOutPQsD7PerformanceEntry ::=
   SEQUENCE
      {
      pr1645v2ATMPerOutPQsD7PerformanceTableIx
         TableIndex,
      pr1645v2ATMPerOutPQsD7PerformanceSysUpTime
         TimeTicks,
      pr1645v2ATMPerOutPQsD7PerformanceTotPkts
         Counter64,
      pr1645v2ATMPerOutPQsD7PerformanceDirTxPkts
         Counter64,
      pr1645v2ATMPerOutPQsD7PerformanceQdPkts
         Counter64,
      pr1645v2ATMPerOutPQsD7PerformanceDropPkts
         Counter64,
      pr1645v2ATMPerOutPQsD7PerformanceRDropPkts
         Counter64,
      pr1645v2ATMPerOutPQsD7PerformanceCirTxPkts
         Counter64,
      pr1645v2ATMPerOutPQsD7PerformanceEirTxPkts
         Counter64,
      pr1645v2ATMPerOutPQsD7PerformanceViolTxPkts
         Counter64,
      pr1645v2ATMPerOutPQsD7PerformanceTotOcts
         Counter64,
      pr1645v2ATMPerOutPQsD7PerformanceDirTxOcts
         Counter64,
      pr1645v2ATMPerOutPQsD7PerformanceQdOcts
         Counter64,
      pr1645v2ATMPerOutPQsD7PerformanceDropOcts
         Counter64,
      pr1645v2ATMPerOutPQsD7PerformanceRDropOcts
         Counter64,
      pr1645v2ATMPerOutPQsD7PerformanceCirTxOcts
         Counter64,
      pr1645v2ATMPerOutPQsD7PerformanceEirTxOcts
         Counter64,
      pr1645v2ATMPerOutPQsD7PerformanceViolTxOcts
         Counter64,
      pr1645v2ATMPerOutPQsD7PerformanceBandwidth
         Integer32
      }

pr1645v2ATMPerOutPQsD7PerformanceTableIx OBJECT-TYPE
   SYNTAX      TableIndex
   MAX-ACCESS  not-accessible
   STATUS      current
   DESCRIPTION
      ""
   ::= {pr1645v2ATMPerOutPQsD7PerformanceEntry 11}

pr1645v2ATMPerOutPQsD7PerformanceSysUpTime OBJECT-TYPE
   SYNTAX      TimeTicks
   MAX-ACCESS  read-only
   STATUS      current
   DESCRIPTION
      "Path: atm.performance.pvcTable.outPriorityQueues.d7Performance.sysUpTime

       Time in centi-second."
   ::= {pr1645v2ATMPerOutPQsD7PerformanceEntry 16777216}

pr1645v2ATMPerOutPQsD7PerformanceTotPkts OBJECT-TYPE
   SYNTAX      Counter64
   MAX-ACCESS  read-only
   STATUS      current
   DESCRIPTION
      "Path: atm.performance.pvcTable.outPriorityQueues.d7Performance.totalPkts

       64 bit unsigned wrappable counter."
   ::= {pr1645v2ATMPerOutPQsD7PerformanceEntry 234881024}

pr1645v2ATMPerOutPQsD7PerformanceDirTxPkts OBJECT-TYPE
   SYNTAX      Counter64
   MAX-ACCESS  read-only
   STATUS      current
   DESCRIPTION
      "Path: atm.performance.pvcTable.outPriorityQueues.d7Performance.directTxPkts

       64 bit unsigned wrappable counter."
   ::= {pr1645v2ATMPerOutPQsD7PerformanceEntry 33554432}

pr1645v2ATMPerOutPQsD7PerformanceQdPkts OBJECT-TYPE
   SYNTAX      Counter64
   MAX-ACCESS  read-only
   STATUS      current
   DESCRIPTION
      "Path: atm.performance.pvcTable.outPriorityQueues.d7Performance.queuedPkts

       64 bit unsigned wrappable counter."
   ::= {pr1645v2ATMPerOutPQsD7PerformanceEntry 50331648}

pr1645v2ATMPerOutPQsD7PerformanceDropPkts OBJECT-TYPE
   SYNTAX      Counter64
   MAX-ACCESS  read-only
   STATUS      current
   DESCRIPTION
      "Path: atm.performance.pvcTable.outPriorityQueues.d7Performance.droppedPkts

       64 bit unsigned wrappable counter."
   ::= {pr1645v2ATMPerOutPQsD7PerformanceEntry 67108864}

pr1645v2ATMPerOutPQsD7PerformanceRDropPkts OBJECT-TYPE
   SYNTAX      Counter64
   MAX-ACCESS  read-only
   STATUS      current
   DESCRIPTION
      "Path: atm.performance.pvcTable.outPriorityQueues.d7Performance.redDroppedPkts

       64 bit unsigned wrappable counter."
   ::= {pr1645v2ATMPerOutPQsD7PerformanceEntry 201326592}

pr1645v2ATMPerOutPQsD7PerformanceCirTxPkts OBJECT-TYPE
   SYNTAX      Counter64
   MAX-ACCESS  read-only
   STATUS      current
   DESCRIPTION
      "Path: atm.performance.pvcTable.outPriorityQueues.d7Performance.cirTxPkts

       64 bit unsigned wrappable counter."
   ::= {pr1645v2ATMPerOutPQsD7PerformanceEntry 83886080}

pr1645v2ATMPerOutPQsD7PerformanceEirTxPkts OBJECT-TYPE
   SYNTAX      Counter64
   MAX-ACCESS  read-only
   STATUS      current
   DESCRIPTION
      "Path: atm.performance.pvcTable.outPriorityQueues.d7Performance.eirTxPkts

       64 bit unsigned wrappable counter."
   ::= {pr1645v2ATMPerOutPQsD7PerformanceEntry 100663296}

pr1645v2ATMPerOutPQsD7PerformanceViolTxPkts OBJECT-TYPE
   SYNTAX      Counter64
   MAX-ACCESS  read-only
   STATUS      current
   DESCRIPTION
      "Path: atm.performance.pvcTable.outPriorityQueues.d7Performance.violateTxPkts

       64 bit unsigned wrappable counter."
   ::= {pr1645v2ATMPerOutPQsD7PerformanceEntry 301989888}

pr1645v2ATMPerOutPQsD7PerformanceTotOcts OBJECT-TYPE
   SYNTAX      Counter64
   MAX-ACCESS  read-only
   STATUS      current
   DESCRIPTION
      "Path: atm.performance.pvcTable.outPriorityQueues.d7Performance.totalOctets

       64 bit unsigned wrappable counter."
   ::= {pr1645v2ATMPerOutPQsD7PerformanceEntry 251658240}

pr1645v2ATMPerOutPQsD7PerformanceDirTxOcts OBJECT-TYPE
   SYNTAX      Counter64
   MAX-ACCESS  read-only
   STATUS      current
   DESCRIPTION
      "Path: atm.performance.pvcTable.outPriorityQueues.d7Performance.directTxOctets

       64 bit unsigned wrappable counter."
   ::= {pr1645v2ATMPerOutPQsD7PerformanceEntry 117440512}

pr1645v2ATMPerOutPQsD7PerformanceQdOcts OBJECT-TYPE
   SYNTAX      Counter64
   MAX-ACCESS  read-only
   STATUS      current
   DESCRIPTION
      "Path: atm.performance.pvcTable.outPriorityQueues.d7Performance.queuedOctets

       64 bit unsigned wrappable counter."
   ::= {pr1645v2ATMPerOutPQsD7PerformanceEntry 134217728}

pr1645v2ATMPerOutPQsD7PerformanceDropOcts OBJECT-TYPE
   SYNTAX      Counter64
   MAX-ACCESS  read-only
   STATUS      current
   DESCRIPTION
      "Path: atm.performance.pvcTable.outPriorityQueues.d7Performance.droppedOctets

       64 bit unsigned wrappable counter."
   ::= {pr1645v2ATMPerOutPQsD7PerformanceEntry 150994944}

pr1645v2ATMPerOutPQsD7PerformanceRDropOcts OBJECT-TYPE
   SYNTAX      Counter64
   MAX-ACCESS  read-only
   STATUS      current
   DESCRIPTION
      "Path: atm.performance.pvcTable.outPriorityQueues.d7Performance.redDroppedOctets

       64 bit unsigned wrappable counter."
   ::= {pr1645v2ATMPerOutPQsD7PerformanceEntry 218103808}

pr1645v2ATMPerOutPQsD7PerformanceCirTxOcts OBJECT-TYPE
   SYNTAX      Counter64
   MAX-ACCESS  read-only
   STATUS      current
   DESCRIPTION
      "Path: atm.performance.pvcTable.outPriorityQueues.d7Performance.cirTxOctets

       64 bit unsigned wrappable counter."
   ::= {pr1645v2ATMPerOutPQsD7PerformanceEntry 167772160}

pr1645v2ATMPerOutPQsD7PerformanceEirTxOcts OBJECT-TYPE
   SYNTAX      Counter64
   MAX-ACCESS  read-only
   STATUS      current
   DESCRIPTION
      "Path: atm.performance.pvcTable.outPriorityQueues.d7Performance.eirTxOctets

       64 bit unsigned wrappable counter."
   ::= {pr1645v2ATMPerOutPQsD7PerformanceEntry 184549376}

pr1645v2ATMPerOutPQsD7PerformanceViolTxOcts OBJECT-TYPE
   SYNTAX      Counter64
   MAX-ACCESS  read-only
   STATUS      current
   DESCRIPTION
      "Path: atm.performance.pvcTable.outPriorityQueues.d7Performance.violateTxOctets

       64 bit unsigned wrappable counter."
   ::= {pr1645v2ATMPerOutPQsD7PerformanceEntry 318767104}

pr1645v2ATMPerOutPQsD7PerformanceBandwidth OBJECT-TYPE
   SYNTAX      Integer32
   MAX-ACCESS  read-only
   STATUS      current
   DESCRIPTION
      "Path: atm.performance.pvcTable.outPriorityQueues.d7Performance.bandwidth

       unit name = bps
       formula = 8 * ; 8 /"
   ::= {pr1645v2ATMPerOutPQsD7PerformanceEntry 268435456}


pr1645v2ATMUniSt OBJECT IDENTIFIER ::= {pr1645v2ATM 44}

pr1645v2ATMUniStSSC OBJECT IDENTIFIER ::= {pr1645v2ATMUniSt 1}

pr1645v2ATMUniStEntry OBJECT IDENTIFIER ::= {pr1645v2ATMUniStSSC 1}

pr1645v2ATMUniStRxCells OBJECT-TYPE
   SYNTAX      Counter32
   MAX-ACCESS  read-only
   STATUS      current
   DESCRIPTION
      "Path: atm.performance.uniStatistics.rxCells

       32 bit unsigned wrappable counter."
   ::= {pr1645v2ATMUniStEntry 16777216}

pr1645v2ATMUniStTxCells OBJECT-TYPE
   SYNTAX      Counter32
   MAX-ACCESS  read-only
   STATUS      current
   DESCRIPTION
      "Path: atm.performance.uniStatistics.txCells

       32 bit unsigned wrappable counter."
   ::= {pr1645v2ATMUniStEntry 33554432}

pr1645v2ATMUniStUnknownCells OBJECT-TYPE
   SYNTAX      Counter32
   MAX-ACCESS  read-only
   STATUS      current
   DESCRIPTION
      "Path: atm.performance.uniStatistics.unknownCells

       32 bit unsigned wrappable counter."
   ::= {pr1645v2ATMUniStEntry 67108864}

pr1645v2ATMUniStHecErrors OBJECT-TYPE
   SYNTAX      Counter32
   MAX-ACCESS  read-only
   STATUS      current
   DESCRIPTION
      "Path: atm.performance.uniStatistics.hecErrors

       32 bit unsigned wrappable counter."
   ::= {pr1645v2ATMUniStEntry 83886080}


pr1645v2ATMVp OBJECT IDENTIFIER ::= {pr1645v2ATM 94}

pr1645v2ATMVpSSCTable OBJECT-TYPE
   SYNTAX      SEQUENCE OF Pr1645v2ATMVpEntry
   MAX-ACCESS  not-accessible
   STATUS      current
   DESCRIPTION
      ""
   ::= {pr1645v2ATMVp 1}

pr1645v2ATMVpEntry OBJECT-TYPE
   SYNTAX      Pr1645v2ATMVpEntry
   MAX-ACCESS  not-accessible
   STATUS      current
   DESCRIPTION
      ""
   INDEX      { pr1645v2ATMVpTableIx }
   ::= {pr1645v2ATMVpSSCTable 1}

Pr1645v2ATMVpEntry ::=
   SEQUENCE
      {
      pr1645v2ATMVpTableIx
         TableIndex,
      pr1645v2ATMVpVpi
         Integer32,
      pr1645v2ATMVpOamF4SegLbRx
         Gauge32,
      pr1645v2ATMVpOamF4SegLbTx
         Gauge32,
      pr1645v2ATMVpOamF4SegCcRx
         Gauge32,
      pr1645v2ATMVpOamF4SegCcTx
         Gauge32,
      pr1645v2ATMVpOamF4SegFpmRx
         Gauge32,
      pr1645v2ATMVpOamF4SegFpmTx
         Gauge32,
      pr1645v2ATMVpOamF4SegBrRx
         Gauge32,
      pr1645v2ATMVpOamF4SegBrTx
         Gauge32,
      pr1645v2ATMVpOamF4SegAdRx
         Gauge32,
      pr1645v2ATMVpOamF4SegAdTx
         Gauge32,
      pr1645v2ATMVpOamF4SegAisRx
         Gauge32,
      pr1645v2ATMVpOamF4SegAisTx
         Gauge32,
      pr1645v2ATMVpOamF4SegRdiRx
         Gauge32,
      pr1645v2ATMVpOamF4SegRdiTx
         Gauge32,
      pr1645v2ATMVpOamF4EteLbRx
         Gauge32,
      pr1645v2ATMVpOamF4EteLbTx
         Gauge32,
      pr1645v2ATMVpOamF4EteCcRx
         Gauge32,
      pr1645v2ATMVpOamF4EteCcTx
         Gauge32,
      pr1645v2ATMVpOamF4EteFpmRx
         Gauge32,
      pr1645v2ATMVpOamF4EteFpmTx
         Gauge32,
      pr1645v2ATMVpOamF4EteBrRx
         Gauge32,
      pr1645v2ATMVpOamF4EteBrTx
         Gauge32,
      pr1645v2ATMVpOamF4EteAdRx
         Gauge32,
      pr1645v2ATMVpOamF4EteAdTx
         Gauge32,
      pr1645v2ATMVpOamF4EteAisRx
         Gauge32,
      pr1645v2ATMVpOamF4EteAisTx
         Gauge32,
      pr1645v2ATMVpOamF4EteRdiRx
         Gauge32,
      pr1645v2ATMVpOamF4EteRdiTx
         Gauge32
      }

pr1645v2ATMVpTableIx OBJECT-TYPE
   SYNTAX      TableIndex
   MAX-ACCESS  not-accessible
   STATUS      current
   DESCRIPTION
      ""
   ::= {pr1645v2ATMVpEntry 11}

pr1645v2ATMVpVpi OBJECT-TYPE
   SYNTAX      Integer32
   MAX-ACCESS  read-only
   STATUS      current
   DESCRIPTION
      "Path: atm.performance.vp.vpi"
   ::= {pr1645v2ATMVpEntry 268435456}

pr1645v2ATMVpOamF4SegLbRx OBJECT-TYPE
   SYNTAX      Gauge32
   MAX-ACCESS  read-only
   STATUS      current
   DESCRIPTION
      "Path: atm.performance.vp.oamF4.segment.lbRx

       32 bit unsigned gauge value."
   ::= {pr1645v2ATMVpEntry 571473920}

pr1645v2ATMVpOamF4SegLbTx OBJECT-TYPE
   SYNTAX      Gauge32
   MAX-ACCESS  read-only
   STATUS      current
   DESCRIPTION
      "Path: atm.performance.vp.oamF4.segment.lbTx

       32 bit unsigned gauge value."
   ::= {pr1645v2ATMVpEntry 572522496}

pr1645v2ATMVpOamF4SegCcRx OBJECT-TYPE
   SYNTAX      Gauge32
   MAX-ACCESS  read-only
   STATUS      current
   DESCRIPTION
      "Path: atm.performance.vp.oamF4.segment.ccRx

       32 bit unsigned gauge value."
   ::= {pr1645v2ATMVpEntry 573571072}

pr1645v2ATMVpOamF4SegCcTx OBJECT-TYPE
   SYNTAX      Gauge32
   MAX-ACCESS  read-only
   STATUS      current
   DESCRIPTION
      "Path: atm.performance.vp.oamF4.segment.ccTx

       32 bit unsigned gauge value."
   ::= {pr1645v2ATMVpEntry 574619648}

pr1645v2ATMVpOamF4SegFpmRx OBJECT-TYPE
   SYNTAX      Gauge32
   MAX-ACCESS  read-only
   STATUS      current
   DESCRIPTION
      "Path: atm.performance.vp.oamF4.segment.fpmRx

       32 bit unsigned gauge value."
   ::= {pr1645v2ATMVpEntry 575668224}

pr1645v2ATMVpOamF4SegFpmTx OBJECT-TYPE
   SYNTAX      Gauge32
   MAX-ACCESS  read-only
   STATUS      current
   DESCRIPTION
      "Path: atm.performance.vp.oamF4.segment.fpmTx

       32 bit unsigned gauge value."
   ::= {pr1645v2ATMVpEntry 576716800}

pr1645v2ATMVpOamF4SegBrRx OBJECT-TYPE
   SYNTAX      Gauge32
   MAX-ACCESS  read-only
   STATUS      current
   DESCRIPTION
      "Path: atm.performance.vp.oamF4.segment.brRx

       32 bit unsigned gauge value."
   ::= {pr1645v2ATMVpEntry 577765376}

pr1645v2ATMVpOamF4SegBrTx OBJECT-TYPE
   SYNTAX      Gauge32
   MAX-ACCESS  read-only
   STATUS      current
   DESCRIPTION
      "Path: atm.performance.vp.oamF4.segment.brTx

       32 bit unsigned gauge value."
   ::= {pr1645v2ATMVpEntry 578813952}

pr1645v2ATMVpOamF4SegAdRx OBJECT-TYPE
   SYNTAX      Gauge32
   MAX-ACCESS  read-only
   STATUS      current
   DESCRIPTION
      "Path: atm.performance.vp.oamF4.segment.actDeactRx

       32 bit unsigned gauge value."
   ::= {pr1645v2ATMVpEntry 579862528}

pr1645v2ATMVpOamF4SegAdTx OBJECT-TYPE
   SYNTAX      Gauge32
   MAX-ACCESS  read-only
   STATUS      current
   DESCRIPTION
      "Path: atm.performance.vp.oamF4.segment.actDeactTx

       32 bit unsigned gauge value."
   ::= {pr1645v2ATMVpEntry 580911104}

pr1645v2ATMVpOamF4SegAisRx OBJECT-TYPE
   SYNTAX      Gauge32
   MAX-ACCESS  read-only
   STATUS      current
   DESCRIPTION
      "Path: atm.performance.vp.oamF4.segment.aisRx

       32 bit unsigned gauge value."
   ::= {pr1645v2ATMVpEntry 581959680}

pr1645v2ATMVpOamF4SegAisTx OBJECT-TYPE
   SYNTAX      Gauge32
   MAX-ACCESS  read-only
   STATUS      current
   DESCRIPTION
      "Path: atm.performance.vp.oamF4.segment.aisTx

       32 bit unsigned gauge value."
   ::= {pr1645v2ATMVpEntry 583008256}

pr1645v2ATMVpOamF4SegRdiRx OBJECT-TYPE
   SYNTAX      Gauge32
   MAX-ACCESS  read-only
   STATUS      current
   DESCRIPTION
      "Path: atm.performance.vp.oamF4.segment.rdiRx

       32 bit unsigned gauge value."
   ::= {pr1645v2ATMVpEntry 584056832}

pr1645v2ATMVpOamF4SegRdiTx OBJECT-TYPE
   SYNTAX      Gauge32
   MAX-ACCESS  read-only
   STATUS      current
   DESCRIPTION
      "Path: atm.performance.vp.oamF4.segment.rdiTx

       32 bit unsigned gauge value."
   ::= {pr1645v2ATMVpEntry 585105408}

pr1645v2ATMVpOamF4EteLbRx OBJECT-TYPE
   SYNTAX      Gauge32
   MAX-ACCESS  read-only
   STATUS      current
   DESCRIPTION
      "Path: atm.performance.vp.oamF4.endToEnd.lbRx

       32 bit unsigned gauge value."
   ::= {pr1645v2ATMVpEntry 605028352}

pr1645v2ATMVpOamF4EteLbTx OBJECT-TYPE
   SYNTAX      Gauge32
   MAX-ACCESS  read-only
   STATUS      current
   DESCRIPTION
      "Path: atm.performance.vp.oamF4.endToEnd.lbTx

       32 bit unsigned gauge value."
   ::= {pr1645v2ATMVpEntry 606076928}

pr1645v2ATMVpOamF4EteCcRx OBJECT-TYPE
   SYNTAX      Gauge32
   MAX-ACCESS  read-only
   STATUS      current
   DESCRIPTION
      "Path: atm.performance.vp.oamF4.endToEnd.ccRx

       32 bit unsigned gauge value."
   ::= {pr1645v2ATMVpEntry 607125504}

pr1645v2ATMVpOamF4EteCcTx OBJECT-TYPE
   SYNTAX      Gauge32
   MAX-ACCESS  read-only
   STATUS      current
   DESCRIPTION
      "Path: atm.performance.vp.oamF4.endToEnd.ccTx

       32 bit unsigned gauge value."
   ::= {pr1645v2ATMVpEntry 608174080}

pr1645v2ATMVpOamF4EteFpmRx OBJECT-TYPE
   SYNTAX      Gauge32
   MAX-ACCESS  read-only
   STATUS      current
   DESCRIPTION
      "Path: atm.performance.vp.oamF4.endToEnd.fpmRx

       32 bit unsigned gauge value."
   ::= {pr1645v2ATMVpEntry 609222656}

pr1645v2ATMVpOamF4EteFpmTx OBJECT-TYPE
   SYNTAX      Gauge32
   MAX-ACCESS  read-only
   STATUS      current
   DESCRIPTION
      "Path: atm.performance.vp.oamF4.endToEnd.fpmTx

       32 bit unsigned gauge value."
   ::= {pr1645v2ATMVpEntry 610271232}

pr1645v2ATMVpOamF4EteBrRx OBJECT-TYPE
   SYNTAX      Gauge32
   MAX-ACCESS  read-only
   STATUS      current
   DESCRIPTION
      "Path: atm.performance.vp.oamF4.endToEnd.brRx

       32 bit unsigned gauge value."
   ::= {pr1645v2ATMVpEntry 611319808}

pr1645v2ATMVpOamF4EteBrTx OBJECT-TYPE
   SYNTAX      Gauge32
   MAX-ACCESS  read-only
   STATUS      current
   DESCRIPTION
      "Path: atm.performance.vp.oamF4.endToEnd.brTx

       32 bit unsigned gauge value."
   ::= {pr1645v2ATMVpEntry 612368384}

pr1645v2ATMVpOamF4EteAdRx OBJECT-TYPE
   SYNTAX      Gauge32
   MAX-ACCESS  read-only
   STATUS      current
   DESCRIPTION
      "Path: atm.performance.vp.oamF4.endToEnd.actDeactRx

       32 bit unsigned gauge value."
   ::= {pr1645v2ATMVpEntry 613416960}

pr1645v2ATMVpOamF4EteAdTx OBJECT-TYPE
   SYNTAX      Gauge32
   MAX-ACCESS  read-only
   STATUS      current
   DESCRIPTION
      "Path: atm.performance.vp.oamF4.endToEnd.actDeactTx

       32 bit unsigned gauge value."
   ::= {pr1645v2ATMVpEntry 614465536}

pr1645v2ATMVpOamF4EteAisRx OBJECT-TYPE
   SYNTAX      Gauge32
   MAX-ACCESS  read-only
   STATUS      current
   DESCRIPTION
      "Path: atm.performance.vp.oamF4.endToEnd.aisRx

       32 bit unsigned gauge value."
   ::= {pr1645v2ATMVpEntry 615514112}

pr1645v2ATMVpOamF4EteAisTx OBJECT-TYPE
   SYNTAX      Gauge32
   MAX-ACCESS  read-only
   STATUS      current
   DESCRIPTION
      "Path: atm.performance.vp.oamF4.endToEnd.aisTx

       32 bit unsigned gauge value."
   ::= {pr1645v2ATMVpEntry 616562688}

pr1645v2ATMVpOamF4EteRdiRx OBJECT-TYPE
   SYNTAX      Gauge32
   MAX-ACCESS  read-only
   STATUS      current
   DESCRIPTION
      "Path: atm.performance.vp.oamF4.endToEnd.rdiRx

       32 bit unsigned gauge value."
   ::= {pr1645v2ATMVpEntry 617611264}

pr1645v2ATMVpOamF4EteRdiTx OBJECT-TYPE
   SYNTAX      Gauge32
   MAX-ACCESS  read-only
   STATUS      current
   DESCRIPTION
      "Path: atm.performance.vp.oamF4.endToEnd.rdiTx

       32 bit unsigned gauge value."
   ::= {pr1645v2ATMVpEntry 618659840}



END
