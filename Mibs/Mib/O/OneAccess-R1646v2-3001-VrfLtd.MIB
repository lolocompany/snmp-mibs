OneAccess-R1646v2-3001-VrfLtd DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2VrfLtd OBJECT IDENTIFIER ::= {r1646Rootv2 3001}

r1646v2VrfLtdMOProp OBJECT-TYPE
   SYNTAX      SEQUENCE OF R1646v2VrfLtdMOPropEntry
   MAX-ACCESS  not-accessible
   STATUS      current
   DESCRIPTION
      ""
   ::= {r1646v2VrfLtd 1}

r1646v2VrfLtdMOPropEntry OBJECT-TYPE
   SYNTAX      R1646v2VrfLtdMOPropEntry
   MAX-ACCESS  not-accessible
   STATUS      current
   DESCRIPTION
      ""
   INDEX      { r1646v2VrfLtdMOPropGlobalIx }
   ::= {r1646v2VrfLtdMOProp 1}

R1646v2VrfLtdMOPropEntry ::=
   SEQUENCE
      {
      r1646v2VrfLtdMOPropPath
         ContainmentPath,
      r1646v2VrfLtdMOPropRev
         ObjectRevision,
      r1646v2VrfLtdMOPropGlobalIx
         GlobalIndex
      }

r1646v2VrfLtdMOPropPath OBJECT-TYPE
   SYNTAX      ContainmentPath
   MAX-ACCESS  read-only
   STATUS      current
   DESCRIPTION
      "Textual description of the containment tree from the instance of
       the root object down to the instance of the current object."
   ::= {r1646v2VrfLtdMOPropEntry 3}

r1646v2VrfLtdMOPropRev OBJECT-TYPE
   SYNTAX      ObjectRevision
   MAX-ACCESS  read-only
   STATUS      current
   DESCRIPTION
      "This value corresponds with the revision of the MANAGED OBJECT."
   ::= {r1646v2VrfLtdMOPropEntry 4}

r1646v2VrfLtdMOPropGlobalIx OBJECT-TYPE
   SYNTAX      GlobalIndex
   MAX-ACCESS  read-only
   STATUS      current
   DESCRIPTION
      "The value of the tlsCntTreeGlobalIndex of the MANAGED OBJECT."
   ::= {r1646v2VrfLtdMOPropEntry 10}



er1646v2VrfLtd OBJECT IDENTIFIER ::= {r1646v2VrfLtd 11}


er1646v2VrfLtdSnmpIndexOffset OBJECT IDENTIFIER ::= {er1646v2VrfLtd 268}

er1646v2VrfLtdSnmpIndexOffsetTable OBJECT-TYPE
   SYNTAX      SEQUENCE OF Er1646v2VrfLtdSnmpIndexOffsetEntry
   MAX-ACCESS  not-accessible
   STATUS      current
   DESCRIPTION
      "Preferred offset in the range of SNMP indices for this SWinst, 0 means automatic"
   ::= {er1646v2VrfLtdSnmpIndexOffset 1}

er1646v2VrfLtdSnmpIndexOffsetEntry OBJECT-TYPE
   SYNTAX      Er1646v2VrfLtdSnmpIndexOffsetEntry
   MAX-ACCESS  not-accessible
   STATUS      current
   DESCRIPTION
      ""
   INDEX      { er1646v2VrfLtdSnmpIndexOffsetGlobalIx }
   ::= {er1646v2VrfLtdSnmpIndexOffsetTable 1}

Er1646v2VrfLtdSnmpIndexOffsetEntry ::=
   SEQUENCE
      {
      er1646v2VrfLtdSnmpIndexOffsetGlobalIx
         GlobalIndex,
      er1646v2VrfLtdSnmpIndexOffsetValue
         Integer32
      }

er1646v2VrfLtdSnmpIndexOffsetGlobalIx OBJECT-TYPE
   SYNTAX      GlobalIndex
   MAX-ACCESS  not-accessible
   STATUS      current
   DESCRIPTION
      "The value of the tlsCntTreeGlobalIndex of the MANAGED OBJECT."
   ::= {er1646v2VrfLtdSnmpIndexOffsetEntry 10}

er1646v2VrfLtdSnmpIndexOffsetValue OBJECT-TYPE
   SYNTAX      Integer32
   MAX-ACCESS  read-write
   STATUS      current
   DESCRIPTION
      "Path: vrfRouterLtd.editConf.snmpIndexOffset"
   ::= {er1646v2VrfLtdSnmpIndexOffsetEntry 2147483648}


er1646v2VrfLtdDefaultRoute OBJECT IDENTIFIER ::= {er1646v2VrfLtd 13}

er1646v2VrfLtdDefaultRouteSSCTable OBJECT-TYPE
   SYNTAX      SEQUENCE OF Er1646v2VrfLtdDefaultRouteEntry
   MAX-ACCESS  not-accessible
   STATUS      current
   DESCRIPTION
      "defaultRoute"
   ::= {er1646v2VrfLtdDefaultRoute 1}

er1646v2VrfLtdDefaultRouteEntry OBJECT-TYPE
   SYNTAX      Er1646v2VrfLtdDefaultRouteEntry
   MAX-ACCESS  not-accessible
   STATUS      current
   DESCRIPTION
      ""
   INDEX      { er1646v2VrfLtdDefaultRouteGlobalIx }
   ::= {er1646v2VrfLtdDefaultRouteSSCTable 1}

Er1646v2VrfLtdDefaultRouteEntry ::=
   SEQUENCE
      {
      er1646v2VrfLtdDefaultRouteGlobalIx
         GlobalIndex,
      er1646v2VrfLtdDefaultRouteGateway
         IpAddress,
      er1646v2VrfLtdDefaultRouteInterface
         DisplayString,
      er1646v2VrfLtdDefaultRoutePreference
         Integer32,
      er1646v2VrfLtdDefaultRouteMetric
         Integer32
      }

er1646v2VrfLtdDefaultRouteGlobalIx OBJECT-TYPE
   SYNTAX      GlobalIndex
   MAX-ACCESS  not-accessible
   STATUS      current
   DESCRIPTION
      "The value of the tlsCntTreeGlobalIndex of the MANAGED OBJECT."
   ::= {er1646v2VrfLtdDefaultRouteEntry 10}

er1646v2VrfLtdDefaultRouteGateway OBJECT-TYPE
   SYNTAX      IpAddress
   MAX-ACCESS  read-write
   STATUS      current
   DESCRIPTION
      "Path: vrfRouterLtd.editConf.defaultRoute.gateway"
   ::= {er1646v2VrfLtdDefaultRouteEntry 16777216}

er1646v2VrfLtdDefaultRouteInterface OBJECT-TYPE
   SYNTAX      DisplayString
   MAX-ACCESS  read-write
   STATUS      current
   DESCRIPTION
      "Path: vrfRouterLtd.editConf.defaultRoute.interface"
   ::= {er1646v2VrfLtdDefaultRouteEntry 33554432}

er1646v2VrfLtdDefaultRoutePreference OBJECT-TYPE
   SYNTAX      Integer32
   MAX-ACCESS  read-write
   STATUS      current
   DESCRIPTION
      "Path: vrfRouterLtd.editConf.defaultRoute.preference"
   ::= {er1646v2VrfLtdDefaultRouteEntry 50331648}

er1646v2VrfLtdDefaultRouteMetric OBJECT-TYPE
   SYNTAX      Integer32
   MAX-ACCESS  read-write
   STATUS      current
   DESCRIPTION
      "Path: vrfRouterLtd.editConf.defaultRoute.metric"
   ::= {er1646v2VrfLtdDefaultRouteEntry 67108864}


er1646v2VrfLtdRoutingTable OBJECT IDENTIFIER ::= {er1646v2VrfLtd 14}

er1646v2VrfLtdRoutingTableSSCTable OBJECT-TYPE
   SYNTAX      SEQUENCE OF Er1646v2VrfLtdRoutingTableEntry
   MAX-ACCESS  not-accessible
   STATUS      current
   DESCRIPTION
      "routingTable"
   ::= {er1646v2VrfLtdRoutingTable 1}

er1646v2VrfLtdRoutingTableEntry OBJECT-TYPE
   SYNTAX      Er1646v2VrfLtdRoutingTableEntry
   MAX-ACCESS  not-accessible
   STATUS      current
   DESCRIPTION
      ""
   INDEX      { er1646v2VrfLtdRoutingTableGlobalIx,
                er1646v2VrfLtdRoutingTableTableIx }
   ::= {er1646v2VrfLtdRoutingTableSSCTable 1}

Er1646v2VrfLtdRoutingTableEntry ::=
   SEQUENCE
      {
      er1646v2VrfLtdRoutingTableActions
         VariableLengthTableActions,
      er1646v2VrfLtdRoutingTableGlobalIx
         GlobalIndex,
      er1646v2VrfLtdRoutingTableTableIx
         TableIndex,
      er1646v2VrfLtdRoutingTableRemark
         DisplayString,
      er1646v2VrfLtdRoutingTableNetwork
         IpAddress,
      er1646v2VrfLtdRoutingTableMask
         IpAddress,
      er1646v2VrfLtdRoutingTableGateway
         IpAddress,
      er1646v2VrfLtdRoutingTableIf
         DisplayString,
      er1646v2VrfLtdRoutingTablePref
         Integer32,
      er1646v2VrfLtdRoutingTableMetric
         Integer32,
      er1646v2VrfLtdRoutingTableProxyArp
         INTEGER,
      er1646v2VrfLtdRoutingTableTimeWindow
         DisplayString,
      er1646v2VrfLtdRoutingTablePermanent
         INTEGER,
      er1646v2VrfLtdRoutingTableTrack
         INTEGER,
      er1646v2VrfLtdRoutingTableTag
         DisplayString
      }

er1646v2VrfLtdRoutingTableActions OBJECT-TYPE
   SYNTAX      VariableLengthTableActions
   MAX-ACCESS  read-write
   STATUS      current
   DESCRIPTION
      "By way of this field, some manipulations
       on this table may be performed."
   ::= {er1646v2VrfLtdRoutingTableEntry 2}

er1646v2VrfLtdRoutingTableGlobalIx OBJECT-TYPE
   SYNTAX      GlobalIndex
   MAX-ACCESS  not-accessible
   STATUS      current
   DESCRIPTION
      "The value of the tlsCntTreeGlobalIndex of the MANAGED OBJECT."
   ::= {er1646v2VrfLtdRoutingTableEntry 10}

er1646v2VrfLtdRoutingTableTableIx OBJECT-TYPE
   SYNTAX      TableIndex
   MAX-ACCESS  not-accessible
   STATUS      current
   DESCRIPTION
      ""
   ::= {er1646v2VrfLtdRoutingTableEntry 11}

er1646v2VrfLtdRoutingTableRemark OBJECT-TYPE
   SYNTAX      DisplayString
   MAX-ACCESS  read-write
   STATUS      current
   DESCRIPTION
      "Path: vrfRouterLtd.editConf.routingTable.remark"
   ::= {er1646v2VrfLtdRoutingTableEntry 117440512}

er1646v2VrfLtdRoutingTableNetwork OBJECT-TYPE
   SYNTAX      IpAddress
   MAX-ACCESS  read-write
   STATUS      current
   DESCRIPTION
      "Path: vrfRouterLtd.editConf.routingTable.network"
   ::= {er1646v2VrfLtdRoutingTableEntry 16777216}

er1646v2VrfLtdRoutingTableMask OBJECT-TYPE
   SYNTAX      IpAddress
   MAX-ACCESS  read-write
   STATUS      current
   DESCRIPTION
      "Path: vrfRouterLtd.editConf.routingTable.mask"
   ::= {er1646v2VrfLtdRoutingTableEntry 33554432}

er1646v2VrfLtdRoutingTableGateway OBJECT-TYPE
   SYNTAX      IpAddress
   MAX-ACCESS  read-write
   STATUS      current
   DESCRIPTION
      "Path: vrfRouterLtd.editConf.routingTable.gateway"
   ::= {er1646v2VrfLtdRoutingTableEntry 50331648}

er1646v2VrfLtdRoutingTableIf OBJECT-TYPE
   SYNTAX      DisplayString
   MAX-ACCESS  read-write
   STATUS      current
   DESCRIPTION
      "Path: vrfRouterLtd.editConf.routingTable.interface"
   ::= {er1646v2VrfLtdRoutingTableEntry 67108864}

er1646v2VrfLtdRoutingTablePref OBJECT-TYPE
   SYNTAX      Integer32
   MAX-ACCESS  read-write
   STATUS      current
   DESCRIPTION
      "Path: vrfRouterLtd.editConf.routingTable.preference"
   ::= {er1646v2VrfLtdRoutingTableEntry 83886080}

er1646v2VrfLtdRoutingTableMetric OBJECT-TYPE
   SYNTAX      Integer32
   MAX-ACCESS  read-write
   STATUS      current
   DESCRIPTION
      "Path: vrfRouterLtd.editConf.routingTable.metric"
   ::= {er1646v2VrfLtdRoutingTableEntry 100663296}

er1646v2VrfLtdRoutingTableProxyArp OBJECT-TYPE
   SYNTAX      INTEGER
               {
               disabled (0),
               enabled (1)
               }
   MAX-ACCESS  read-write
   STATUS      current
   DESCRIPTION
      "Path: vrfRouterLtd.editConf.routingTable.proxyArp

       Possibilities:
               disabled   (0)
               enabled   (1)"
   ::= {er1646v2VrfLtdRoutingTableEntry 134217728}

er1646v2VrfLtdRoutingTableTimeWindow OBJECT-TYPE
   SYNTAX      DisplayString
   MAX-ACCESS  read-write
   STATUS      current
   DESCRIPTION
      "Path: vrfRouterLtd.editConf.routingTable.timeWindow"
   ::= {er1646v2VrfLtdRoutingTableEntry 150994944}

er1646v2VrfLtdRoutingTablePermanent OBJECT-TYPE
   SYNTAX      INTEGER
               {
               disabled (0),
               enabled (1)
               }
   MAX-ACCESS  read-write
   STATUS      current
   DESCRIPTION
      "Path: vrfRouterLtd.editConf.routingTable.permanent

       Possibilities:
               disabled   (0)
               enabled   (1)"
   ::= {er1646v2VrfLtdRoutingTableEntry 184549376}

er1646v2VrfLtdRoutingTableTrack OBJECT-TYPE
   SYNTAX      INTEGER
               {
               disabled (0)
               }
   MAX-ACCESS  read-write
   STATUS      current
   DESCRIPTION
      "Path: vrfRouterLtd.editConf.routingTable.track

       Possibilities:
               disabled   (0)"
   ::= {er1646v2VrfLtdRoutingTableEntry 167772160}

er1646v2VrfLtdRoutingTableTag OBJECT-TYPE
   SYNTAX      DisplayString
   MAX-ACCESS  read-write
   STATUS      current
   DESCRIPTION
      "Path: vrfRouterLtd.editConf.routingTable.tag"
   ::= {er1646v2VrfLtdRoutingTableEntry 201326592}


er1646v2VrfLtdSendTtlExceeded OBJECT IDENTIFIER ::= {er1646v2VrfLtd 30}

er1646v2VrfLtdSendTtlExceededTable OBJECT-TYPE
   SYNTAX      SEQUENCE OF Er1646v2VrfLtdSendTtlExceededEntry
   MAX-ACCESS  not-accessible
   STATUS      current
   DESCRIPTION
      "indicates if a ICMP TTL exceeded must be returned to a packet's spurce if the TTL reaches 0 "
   ::= {er1646v2VrfLtdSendTtlExceeded 1}

er1646v2VrfLtdSendTtlExceededEntry OBJECT-TYPE
   SYNTAX      Er1646v2VrfLtdSendTtlExceededEntry
   MAX-ACCESS  not-accessible
   STATUS      current
   DESCRIPTION
      ""
   INDEX      { er1646v2VrfLtdSendTtlExceededGlobalIx }
   ::= {er1646v2VrfLtdSendTtlExceededTable 1}

Er1646v2VrfLtdSendTtlExceededEntry ::=
   SEQUENCE
      {
      er1646v2VrfLtdSendTtlExceededGlobalIx
         GlobalIndex,
      er1646v2VrfLtdSendTtlExceededValue
         INTEGER
      }

er1646v2VrfLtdSendTtlExceededGlobalIx OBJECT-TYPE
   SYNTAX      GlobalIndex
   MAX-ACCESS  not-accessible
   STATUS      current
   DESCRIPTION
      "The value of the tlsCntTreeGlobalIndex of the MANAGED OBJECT."
   ::= {er1646v2VrfLtdSendTtlExceededEntry 10}

er1646v2VrfLtdSendTtlExceededValue OBJECT-TYPE
   SYNTAX      INTEGER
               {
               disabled (0),
               enabled (1)
               }
   MAX-ACCESS  read-write
   STATUS      current
   DESCRIPTION
      "Path: vrfRouterLtd.editConf.sendTtlExceeded

       Possibilities:
               disabled   (0)
               enabled   (1)"
   ::= {er1646v2VrfLtdSendTtlExceededEntry 2147483648}


er1646v2VrfLtdSendPortUnreachable OBJECT IDENTIFIER ::= {er1646v2VrfLtd 31}

er1646v2VrfLtdSendPortUnreachableTable OBJECT-TYPE
   SYNTAX      SEQUENCE OF Er1646v2VrfLtdSendPortUnreachableEntry
   MAX-ACCESS  not-accessible
   STATUS      current
   DESCRIPTION
      "indicates if a ICMP Port Unreachable must be returned to a packet's source if
                        the destination port is unknown"
   ::= {er1646v2VrfLtdSendPortUnreachable 1}

er1646v2VrfLtdSendPortUnreachableEntry OBJECT-TYPE
   SYNTAX      Er1646v2VrfLtdSendPortUnreachableEntry
   MAX-ACCESS  not-accessible
   STATUS      current
   DESCRIPTION
      ""
   INDEX      { er1646v2VrfLtdSendPortUnreachableGlobalIx }
   ::= {er1646v2VrfLtdSendPortUnreachableTable 1}

Er1646v2VrfLtdSendPortUnreachableEntry ::=
   SEQUENCE
      {
      er1646v2VrfLtdSendPortUnreachableGlobalIx
         GlobalIndex,
      er1646v2VrfLtdSendPortUnreachableValue
         INTEGER
      }

er1646v2VrfLtdSendPortUnreachableGlobalIx OBJECT-TYPE
   SYNTAX      GlobalIndex
   MAX-ACCESS  not-accessible
   STATUS      current
   DESCRIPTION
      "The value of the tlsCntTreeGlobalIndex of the MANAGED OBJECT."
   ::= {er1646v2VrfLtdSendPortUnreachableEntry 10}

er1646v2VrfLtdSendPortUnreachableValue OBJECT-TYPE
   SYNTAX      INTEGER
               {
               disabled (0),
               enabled (1)
               }
   MAX-ACCESS  read-write
   STATUS      current
   DESCRIPTION
      "Path: vrfRouterLtd.editConf.sendPortUnreachable

       Possibilities:
               disabled   (0)
               enabled   (1)"
   ::= {er1646v2VrfLtdSendPortUnreachableEntry 2147483648}


er1646v2VrfLtdSendAdminUnreachable OBJECT IDENTIFIER ::= {er1646v2VrfLtd 56}

er1646v2VrfLtdSendAdminUnreachableTable OBJECT-TYPE
   SYNTAX      SEQUENCE OF Er1646v2VrfLtdSendAdminUnreachableEntry
   MAX-ACCESS  not-accessible
   STATUS      current
   DESCRIPTION
      "indicates if an ICMP can be returned to a packet's source if
                        the packet is discarded"
   ::= {er1646v2VrfLtdSendAdminUnreachable 1}

er1646v2VrfLtdSendAdminUnreachableEntry OBJECT-TYPE
   SYNTAX      Er1646v2VrfLtdSendAdminUnreachableEntry
   MAX-ACCESS  not-accessible
   STATUS      current
   DESCRIPTION
      ""
   INDEX      { er1646v2VrfLtdSendAdminUnreachableGlobalIx }
   ::= {er1646v2VrfLtdSendAdminUnreachableTable 1}

Er1646v2VrfLtdSendAdminUnreachableEntry ::=
   SEQUENCE
      {
      er1646v2VrfLtdSendAdminUnreachableGlobalIx
         GlobalIndex,
      er1646v2VrfLtdSendAdminUnreachableValue
         INTEGER
      }

er1646v2VrfLtdSendAdminUnreachableGlobalIx OBJECT-TYPE
   SYNTAX      GlobalIndex
   MAX-ACCESS  not-accessible
   STATUS      current
   DESCRIPTION
      "The value of the tlsCntTreeGlobalIndex of the MANAGED OBJECT."
   ::= {er1646v2VrfLtdSendAdminUnreachableEntry 10}

er1646v2VrfLtdSendAdminUnreachableValue OBJECT-TYPE
   SYNTAX      INTEGER
               {
               disabled (0),
               enabled (1)
               }
   MAX-ACCESS  read-write
   STATUS      current
   DESCRIPTION
      "Path: vrfRouterLtd.editConf.sendAdminUnreachable

       Possibilities:
               disabled   (0)
               enabled   (1)"
   ::= {er1646v2VrfLtdSendAdminUnreachableEntry 2147483648}


er1646v2VrfLtdSendHostUnreachable OBJECT IDENTIFIER ::= {er1646v2VrfLtd 36}

er1646v2VrfLtdSendHostUnreachableTable OBJECT-TYPE
   SYNTAX      SEQUENCE OF Er1646v2VrfLtdSendHostUnreachableEntry
   MAX-ACCESS  not-accessible
   STATUS      current
   DESCRIPTION
      "indicates if a ICMP Host Unreachable must be returned to a packet's source if
                        the destination host is unknown"
   ::= {er1646v2VrfLtdSendHostUnreachable 1}

er1646v2VrfLtdSendHostUnreachableEntry OBJECT-TYPE
   SYNTAX      Er1646v2VrfLtdSendHostUnreachableEntry
   MAX-ACCESS  not-accessible
   STATUS      current
   DESCRIPTION
      ""
   INDEX      { er1646v2VrfLtdSendHostUnreachableGlobalIx }
   ::= {er1646v2VrfLtdSendHostUnreachableTable 1}

Er1646v2VrfLtdSendHostUnreachableEntry ::=
   SEQUENCE
      {
      er1646v2VrfLtdSendHostUnreachableGlobalIx
         GlobalIndex,
      er1646v2VrfLtdSendHostUnreachableValue
         INTEGER
      }

er1646v2VrfLtdSendHostUnreachableGlobalIx OBJECT-TYPE
   SYNTAX      GlobalIndex
   MAX-ACCESS  not-accessible
   STATUS      current
   DESCRIPTION
      "The value of the tlsCntTreeGlobalIndex of the MANAGED OBJECT."
   ::= {er1646v2VrfLtdSendHostUnreachableEntry 10}

er1646v2VrfLtdSendHostUnreachableValue OBJECT-TYPE
   SYNTAX      INTEGER
               {
               disabled (0),
               enabled (1)
               }
   MAX-ACCESS  read-write
   STATUS      current
   DESCRIPTION
      "Path: vrfRouterLtd.editConf.sendHostUnreachable

       Possibilities:
               disabled   (0)
               enabled   (1)"
   ::= {er1646v2VrfLtdSendHostUnreachableEntry 2147483648}


er1646v2VrfLtdAlternativeRoutes OBJECT IDENTIFIER ::= {er1646v2VrfLtd 57}

er1646v2VrfLtdAlternativeRoutesTable OBJECT-TYPE
   SYNTAX      SEQUENCE OF Er1646v2VrfLtdAlternativeRoutesEntry
   MAX-ACCESS  not-accessible
   STATUS      current
   DESCRIPTION
      "indicates if load balancing has to be applied whenever multiple
                        routes are available"
   ::= {er1646v2VrfLtdAlternativeRoutes 1}

er1646v2VrfLtdAlternativeRoutesEntry OBJECT-TYPE
   SYNTAX      Er1646v2VrfLtdAlternativeRoutesEntry
   MAX-ACCESS  not-accessible
   STATUS      current
   DESCRIPTION
      ""
   INDEX      { er1646v2VrfLtdAlternativeRoutesGlobalIx }
   ::= {er1646v2VrfLtdAlternativeRoutesTable 1}

Er1646v2VrfLtdAlternativeRoutesEntry ::=
   SEQUENCE
      {
      er1646v2VrfLtdAlternativeRoutesGlobalIx
         GlobalIndex,
      er1646v2VrfLtdAlternativeRoutesValue
         INTEGER
      }

er1646v2VrfLtdAlternativeRoutesGlobalIx OBJECT-TYPE
   SYNTAX      GlobalIndex
   MAX-ACCESS  not-accessible
   STATUS      current
   DESCRIPTION
      "The value of the tlsCntTreeGlobalIndex of the MANAGED OBJECT."
   ::= {er1646v2VrfLtdAlternativeRoutesEntry 10}

er1646v2VrfLtdAlternativeRoutesValue OBJECT-TYPE
   SYNTAX      INTEGER
               {
               backup (0),
               roundRobin (1)
               }
   MAX-ACCESS  read-write
   STATUS      current
   DESCRIPTION
      "Path: vrfRouterLtd.editConf.alternativeRoutes

       Possibilities:
               backup   (0)
               roundRobin   (1)"
   ::= {er1646v2VrfLtdAlternativeRoutesEntry 2147483648}


er1646v2VrfLtdRoutingProtocol OBJECT IDENTIFIER ::= {er1646v2VrfLtd 34}

er1646v2VrfLtdRoutingProtocolTable OBJECT-TYPE
   SYNTAX      SEQUENCE OF Er1646v2VrfLtdRoutingProtocolEntry
   MAX-ACCESS  not-accessible
   STATUS      current
   DESCRIPTION
      "indicates which dynamic routing protocol should be used"
   ::= {er1646v2VrfLtdRoutingProtocol 1}

er1646v2VrfLtdRoutingProtocolEntry OBJECT-TYPE
   SYNTAX      Er1646v2VrfLtdRoutingProtocolEntry
   MAX-ACCESS  not-accessible
   STATUS      current
   DESCRIPTION
      ""
   INDEX      { er1646v2VrfLtdRoutingProtocolGlobalIx }
   ::= {er1646v2VrfLtdRoutingProtocolTable 1}

Er1646v2VrfLtdRoutingProtocolEntry ::=
   SEQUENCE
      {
      er1646v2VrfLtdRoutingProtocolGlobalIx
         GlobalIndex,
      er1646v2VrfLtdRoutingProtocolValue
         INTEGER
      }

er1646v2VrfLtdRoutingProtocolGlobalIx OBJECT-TYPE
   SYNTAX      GlobalIndex
   MAX-ACCESS  not-accessible
   STATUS      current
   DESCRIPTION
      "The value of the tlsCntTreeGlobalIndex of the MANAGED OBJECT."
   ::= {er1646v2VrfLtdRoutingProtocolEntry 10}

er1646v2VrfLtdRoutingProtocolValue OBJECT-TYPE
   SYNTAX      INTEGER
               {
               none (0),
               rip2 (1)
               }
   MAX-ACCESS  read-write
   STATUS      current
   DESCRIPTION
      "Path: vrfRouterLtd.editConf.routingProtocol

       Possibilities:
               none   (0)
               rip2   (1)"
   ::= {er1646v2VrfLtdRoutingProtocolEntry 2147483648}


er1646v2VrfLtdRipUpInt OBJECT IDENTIFIER ::= {er1646v2VrfLtd 35}

er1646v2VrfLtdRipUpIntTable OBJECT-TYPE
   SYNTAX      SEQUENCE OF Er1646v2VrfLtdRipUpIntEntry
   MAX-ACCESS  not-accessible
   STATUS      current
   DESCRIPTION
      "delay between RIP updates sent"
   ::= {er1646v2VrfLtdRipUpInt 1}

er1646v2VrfLtdRipUpIntEntry OBJECT-TYPE
   SYNTAX      Er1646v2VrfLtdRipUpIntEntry
   MAX-ACCESS  not-accessible
   STATUS      current
   DESCRIPTION
      ""
   INDEX      { er1646v2VrfLtdRipUpIntGlobalIx }
   ::= {er1646v2VrfLtdRipUpIntTable 1}

Er1646v2VrfLtdRipUpIntEntry ::=
   SEQUENCE
      {
      er1646v2VrfLtdRipUpIntGlobalIx
         GlobalIndex,
      er1646v2VrfLtdRipUpIntValue
         TimeTicks
      }

er1646v2VrfLtdRipUpIntGlobalIx OBJECT-TYPE
   SYNTAX      GlobalIndex
   MAX-ACCESS  not-accessible
   STATUS      current
   DESCRIPTION
      "The value of the tlsCntTreeGlobalIndex of the MANAGED OBJECT."
   ::= {er1646v2VrfLtdRipUpIntEntry 10}

er1646v2VrfLtdRipUpIntValue OBJECT-TYPE
   SYNTAX      TimeTicks
   MAX-ACCESS  read-write
   STATUS      current
   DESCRIPTION
      "Path: vrfRouterLtd.editConf.ripUpdateInterval

       Time in centi-second."
   ::= {er1646v2VrfLtdRipUpIntEntry 2147483648}


er1646v2VrfLtdRipHoldDownTime OBJECT IDENTIFIER ::= {er1646v2VrfLtd 78}

er1646v2VrfLtdRipHoldDownTimeTable OBJECT-TYPE
   SYNTAX      SEQUENCE OF Er1646v2VrfLtdRipHoldDownTimeEntry
   MAX-ACCESS  not-accessible
   STATUS      current
   DESCRIPTION
      "Time to wait before accepting better routes in order to prevent instable route-flapping"
   ::= {er1646v2VrfLtdRipHoldDownTime 1}

er1646v2VrfLtdRipHoldDownTimeEntry OBJECT-TYPE
   SYNTAX      Er1646v2VrfLtdRipHoldDownTimeEntry
   MAX-ACCESS  not-accessible
   STATUS      current
   DESCRIPTION
      ""
   INDEX      { er1646v2VrfLtdRipHoldDownTimeGlobalIx }
   ::= {er1646v2VrfLtdRipHoldDownTimeTable 1}

Er1646v2VrfLtdRipHoldDownTimeEntry ::=
   SEQUENCE
      {
      er1646v2VrfLtdRipHoldDownTimeGlobalIx
         GlobalIndex,
      er1646v2VrfLtdRipHoldDownTimeValue
         TimeTicks
      }

er1646v2VrfLtdRipHoldDownTimeGlobalIx OBJECT-TYPE
   SYNTAX      GlobalIndex
   MAX-ACCESS  not-accessible
   STATUS      current
   DESCRIPTION
      "The value of the tlsCntTreeGlobalIndex of the MANAGED OBJECT."
   ::= {er1646v2VrfLtdRipHoldDownTimeEntry 10}

er1646v2VrfLtdRipHoldDownTimeValue OBJECT-TYPE
   SYNTAX      TimeTicks
   MAX-ACCESS  read-write
   STATUS      current
   DESCRIPTION
      "Path: vrfRouterLtd.editConf.ripHoldDownTime

       Time in centi-second."
   ::= {er1646v2VrfLtdRipHoldDownTimeEntry 2147483648}


er1646v2VrfLtdR2ScrtTbl OBJECT IDENTIFIER ::= {er1646v2VrfLtd 42}

er1646v2VrfLtdR2ScrtTblSSCTable OBJECT-TYPE
   SYNTAX      SEQUENCE OF Er1646v2VrfLtdR2ScrtTblEntry
   MAX-ACCESS  not-accessible
   STATUS      current
   DESCRIPTION
      "table to store secret values for RIPv2 authentication"
   ::= {er1646v2VrfLtdR2ScrtTbl 1}

er1646v2VrfLtdR2ScrtTblEntry OBJECT-TYPE
   SYNTAX      Er1646v2VrfLtdR2ScrtTblEntry
   MAX-ACCESS  not-accessible
   STATUS      current
   DESCRIPTION
      ""
   INDEX      { er1646v2VrfLtdR2ScrtTblGlobalIx,
                er1646v2VrfLtdR2ScrtTblTableIx }
   ::= {er1646v2VrfLtdR2ScrtTblSSCTable 1}

Er1646v2VrfLtdR2ScrtTblEntry ::=
   SEQUENCE
      {
      er1646v2VrfLtdR2ScrtTblActions
         VariableLengthTableActions,
      er1646v2VrfLtdR2ScrtTblGlobalIx
         GlobalIndex,
      er1646v2VrfLtdR2ScrtTblTableIx
         TableIndex,
      er1646v2VrfLtdR2ScrtTblKeyId
         Integer32,
      er1646v2VrfLtdR2ScrtTblSecret
         DisplayString,
      er1646v2VrfLtdR2ScrtTblIf
         DisplayString
      }

er1646v2VrfLtdR2ScrtTblActions OBJECT-TYPE
   SYNTAX      VariableLengthTableActions
   MAX-ACCESS  read-write
   STATUS      current
   DESCRIPTION
      "By way of this field, some manipulations
       on this table may be performed."
   ::= {er1646v2VrfLtdR2ScrtTblEntry 2}

er1646v2VrfLtdR2ScrtTblGlobalIx OBJECT-TYPE
   SYNTAX      GlobalIndex
   MAX-ACCESS  not-accessible
   STATUS      current
   DESCRIPTION
      "The value of the tlsCntTreeGlobalIndex of the MANAGED OBJECT."
   ::= {er1646v2VrfLtdR2ScrtTblEntry 10}

er1646v2VrfLtdR2ScrtTblTableIx OBJECT-TYPE
   SYNTAX      TableIndex
   MAX-ACCESS  not-accessible
   STATUS      current
   DESCRIPTION
      ""
   ::= {er1646v2VrfLtdR2ScrtTblEntry 11}

er1646v2VrfLtdR2ScrtTblKeyId OBJECT-TYPE
   SYNTAX      Integer32
   MAX-ACCESS  read-write
   STATUS      current
   DESCRIPTION
      "Path: vrfRouterLtd.editConf.ripv2SecretTable.keyId"
   ::= {er1646v2VrfLtdR2ScrtTblEntry 16777216}

er1646v2VrfLtdR2ScrtTblSecret OBJECT-TYPE
   SYNTAX      DisplayString
   MAX-ACCESS  read-write
   STATUS      current
   DESCRIPTION
      "Path: vrfRouterLtd.editConf.ripv2SecretTable.secret"
   ::= {er1646v2VrfLtdR2ScrtTblEntry 33554432}

er1646v2VrfLtdR2ScrtTblIf OBJECT-TYPE
   SYNTAX      DisplayString
   MAX-ACCESS  read-write
   STATUS      current
   DESCRIPTION
      "Path: vrfRouterLtd.editConf.ripv2SecretTable.interface"
   ::= {er1646v2VrfLtdR2ScrtTblEntry 50331648}


er1646v2VrfLtdRipPreference OBJECT IDENTIFIER ::= {er1646v2VrfLtd 83}

er1646v2VrfLtdRipPreferenceTable OBJECT-TYPE
   SYNTAX      SEQUENCE OF Er1646v2VrfLtdRipPreferenceEntry
   MAX-ACCESS  not-accessible
   STATUS      current
   DESCRIPTION
      "preference"
   ::= {er1646v2VrfLtdRipPreference 1}

er1646v2VrfLtdRipPreferenceEntry OBJECT-TYPE
   SYNTAX      Er1646v2VrfLtdRipPreferenceEntry
   MAX-ACCESS  not-accessible
   STATUS      current
   DESCRIPTION
      ""
   INDEX      { er1646v2VrfLtdRipPreferenceGlobalIx }
   ::= {er1646v2VrfLtdRipPreferenceTable 1}

Er1646v2VrfLtdRipPreferenceEntry ::=
   SEQUENCE
      {
      er1646v2VrfLtdRipPreferenceGlobalIx
         GlobalIndex,
      er1646v2VrfLtdRipPreferenceValue
         Gauge32
      }

er1646v2VrfLtdRipPreferenceGlobalIx OBJECT-TYPE
   SYNTAX      GlobalIndex
   MAX-ACCESS  not-accessible
   STATUS      current
   DESCRIPTION
      "The value of the tlsCntTreeGlobalIndex of the MANAGED OBJECT."
   ::= {er1646v2VrfLtdRipPreferenceEntry 10}

er1646v2VrfLtdRipPreferenceValue OBJECT-TYPE
   SYNTAX      Gauge32
   MAX-ACCESS  read-write
   STATUS      current
   DESCRIPTION
      "Path: vrfRouterLtd.editConf.ripPreference

       32 bit unsigned gauge value."
   ::= {er1646v2VrfLtdRipPreferenceEntry 2147483648}


er1646v2VrfLtdRipNeighbors OBJECT IDENTIFIER ::= {er1646v2VrfLtd 50}

er1646v2VrfLtdRipNeighborsSSCTable OBJECT-TYPE
   SYNTAX      SEQUENCE OF Er1646v2VrfLtdRipNeighborsEntry
   MAX-ACCESS  not-accessible
   STATUS      current
   DESCRIPTION
      "rip neighbor table"
   ::= {er1646v2VrfLtdRipNeighbors 1}

er1646v2VrfLtdRipNeighborsEntry OBJECT-TYPE
   SYNTAX      Er1646v2VrfLtdRipNeighborsEntry
   MAX-ACCESS  not-accessible
   STATUS      current
   DESCRIPTION
      ""
   INDEX      { er1646v2VrfLtdRipNeighborsGlobalIx,
                er1646v2VrfLtdRipNeighborsTableIx }
   ::= {er1646v2VrfLtdRipNeighborsSSCTable 1}

Er1646v2VrfLtdRipNeighborsEntry ::=
   SEQUENCE
      {
      er1646v2VrfLtdRipNeighborsActions
         VariableLengthTableActions,
      er1646v2VrfLtdRipNeighborsGlobalIx
         GlobalIndex,
      er1646v2VrfLtdRipNeighborsTableIx
         TableIndex,
      er1646v2VrfLtdRipNeighborsIpAddress
         IpAddress
      }

er1646v2VrfLtdRipNeighborsActions OBJECT-TYPE
   SYNTAX      VariableLengthTableActions
   MAX-ACCESS  read-write
   STATUS      current
   DESCRIPTION
      "By way of this field, some manipulations
       on this table may be performed."
   ::= {er1646v2VrfLtdRipNeighborsEntry 2}

er1646v2VrfLtdRipNeighborsGlobalIx OBJECT-TYPE
   SYNTAX      GlobalIndex
   MAX-ACCESS  not-accessible
   STATUS      current
   DESCRIPTION
      "The value of the tlsCntTreeGlobalIndex of the MANAGED OBJECT."
   ::= {er1646v2VrfLtdRipNeighborsEntry 10}

er1646v2VrfLtdRipNeighborsTableIx OBJECT-TYPE
   SYNTAX      TableIndex
   MAX-ACCESS  not-accessible
   STATUS      current
   DESCRIPTION
      ""
   ::= {er1646v2VrfLtdRipNeighborsEntry 11}

er1646v2VrfLtdRipNeighborsIpAddress OBJECT-TYPE
   SYNTAX      IpAddress
   MAX-ACCESS  read-write
   STATUS      current
   DESCRIPTION
      "Path: vrfRouterLtd.editConf.ripNeighbors.ipAddress"
   ::= {er1646v2VrfLtdRipNeighborsEntry 67108864}


er1646v2VrfLtdMulticastRouting OBJECT IDENTIFIER ::= {er1646v2VrfLtd 17}

er1646v2VrfLtdMulticastRoutingTable OBJECT-TYPE
   SYNTAX      SEQUENCE OF Er1646v2VrfLtdMulticastRoutingEntry
   MAX-ACCESS  not-accessible
   STATUS      current
   DESCRIPTION
      "indicates if multicast routing (PIM/IGMP) is supported"
   ::= {er1646v2VrfLtdMulticastRouting 1}

er1646v2VrfLtdMulticastRoutingEntry OBJECT-TYPE
   SYNTAX      Er1646v2VrfLtdMulticastRoutingEntry
   MAX-ACCESS  not-accessible
   STATUS      current
   DESCRIPTION
      ""
   INDEX      { er1646v2VrfLtdMulticastRoutingGlobalIx }
   ::= {er1646v2VrfLtdMulticastRoutingTable 1}

Er1646v2VrfLtdMulticastRoutingEntry ::=
   SEQUENCE
      {
      er1646v2VrfLtdMulticastRoutingGlobalIx
         GlobalIndex,
      er1646v2VrfLtdMulticastRoutingValue
         INTEGER
      }

er1646v2VrfLtdMulticastRoutingGlobalIx OBJECT-TYPE
   SYNTAX      GlobalIndex
   MAX-ACCESS  not-accessible
   STATUS      current
   DESCRIPTION
      "The value of the tlsCntTreeGlobalIndex of the MANAGED OBJECT."
   ::= {er1646v2VrfLtdMulticastRoutingEntry 10}

er1646v2VrfLtdMulticastRoutingValue OBJECT-TYPE
   SYNTAX      INTEGER
               {
               disabled (0),
               enabled (1)
               }
   MAX-ACCESS  read-write
   STATUS      current
   DESCRIPTION
      "Path: vrfRouterLtd.editConf.multicastRouting

       Possibilities:
               disabled   (0)
               enabled   (1)"
   ::= {er1646v2VrfLtdMulticastRoutingEntry 2147483648}


er1646v2VrfLtdDhcpStat OBJECT IDENTIFIER ::= {er1646v2VrfLtd 51}

er1646v2VrfLtdDhcpStatSSCTable OBJECT-TYPE
   SYNTAX      SEQUENCE OF Er1646v2VrfLtdDhcpStatEntry
   MAX-ACCESS  not-accessible
   STATUS      current
   DESCRIPTION
      "Initialisation DHCP server"
   ::= {er1646v2VrfLtdDhcpStat 1}

er1646v2VrfLtdDhcpStatEntry OBJECT-TYPE
   SYNTAX      Er1646v2VrfLtdDhcpStatEntry
   MAX-ACCESS  not-accessible
   STATUS      current
   DESCRIPTION
      ""
   INDEX      { er1646v2VrfLtdDhcpStatGlobalIx,
                er1646v2VrfLtdDhcpStatTableIx }
   ::= {er1646v2VrfLtdDhcpStatSSCTable 1}

Er1646v2VrfLtdDhcpStatEntry ::=
   SEQUENCE
      {
      er1646v2VrfLtdDhcpStatActions
         VariableLengthTableActions,
      er1646v2VrfLtdDhcpStatGlobalIx
         GlobalIndex,
      er1646v2VrfLtdDhcpStatTableIx
         TableIndex,
      er1646v2VrfLtdDhcpStatIpAddress
         IpAddress,
      er1646v2VrfLtdDhcpStatMask
         IpAddress,
      er1646v2VrfLtdDhcpStatGateway
         IpAddress,
      er1646v2VrfLtdDhcpStatInterface
         DisplayString,
      er1646v2VrfLtdDhcpStatDnsSetting
         INTEGER,
      er1646v2VrfLtdDhcpStatNameServer
         IpAddress,
      er1646v2VrfLtdDhcpStatNameServer2
         IpAddress,
      er1646v2VrfLtdDhcpStatTftpServer
         IpAddress,
      er1646v2VrfLtdDhcpStatTftpServerOption
         DisplayString,
      er1646v2VrfLtdDhcpStatMacAddress
         OCTET STRING,
      er1646v2VrfLtdDhcpStatBootFile
         DisplayString,
      er1646v2VrfLtdDhcpStatBootFileOption
         DisplayString,
      er1646v2VrfLtdDhcpStatHostName
         DisplayString,
      er1646v2VrfLtdDhcpStatDomainName
         DisplayString,
      er1646v2VrfLtdDhcpStatNetbiosNS
         IpAddress,
      er1646v2VrfLtdDhcpStatNetbiosNS2
         IpAddress,
      er1646v2VrfLtdDhcpStatNetbiosNT
         INTEGER
      }

er1646v2VrfLtdDhcpStatActions OBJECT-TYPE
   SYNTAX      VariableLengthTableActions
   MAX-ACCESS  read-write
   STATUS      current
   DESCRIPTION
      "By way of this field, some manipulations
       on this table may be performed."
   ::= {er1646v2VrfLtdDhcpStatEntry 2}

er1646v2VrfLtdDhcpStatGlobalIx OBJECT-TYPE
   SYNTAX      GlobalIndex
   MAX-ACCESS  not-accessible
   STATUS      current
   DESCRIPTION
      "The value of the tlsCntTreeGlobalIndex of the MANAGED OBJECT."
   ::= {er1646v2VrfLtdDhcpStatEntry 10}

er1646v2VrfLtdDhcpStatTableIx OBJECT-TYPE
   SYNTAX      TableIndex
   MAX-ACCESS  not-accessible
   STATUS      current
   DESCRIPTION
      ""
   ::= {er1646v2VrfLtdDhcpStatEntry 11}

er1646v2VrfLtdDhcpStatIpAddress OBJECT-TYPE
   SYNTAX      IpAddress
   MAX-ACCESS  read-write
   STATUS      current
   DESCRIPTION
      "Path: vrfRouterLtd.editConf.dhcpStatic.ipAddress"
   ::= {er1646v2VrfLtdDhcpStatEntry 16777216}

er1646v2VrfLtdDhcpStatMask OBJECT-TYPE
   SYNTAX      IpAddress
   MAX-ACCESS  read-write
   STATUS      current
   DESCRIPTION
      "Path: vrfRouterLtd.editConf.dhcpStatic.mask"
   ::= {er1646v2VrfLtdDhcpStatEntry 33554432}

er1646v2VrfLtdDhcpStatGateway OBJECT-TYPE
   SYNTAX      IpAddress
   MAX-ACCESS  read-write
   STATUS      current
   DESCRIPTION
      "Path: vrfRouterLtd.editConf.dhcpStatic.gateway"
   ::= {er1646v2VrfLtdDhcpStatEntry 50331648}

er1646v2VrfLtdDhcpStatInterface OBJECT-TYPE
   SYNTAX      DisplayString
   MAX-ACCESS  read-write
   STATUS      current
   DESCRIPTION
      "Path: vrfRouterLtd.editConf.dhcpStatic.interface"
   ::= {er1646v2VrfLtdDhcpStatEntry 268435456}

er1646v2VrfLtdDhcpStatDnsSetting OBJECT-TYPE
   SYNTAX      INTEGER
               {
               configured (0),
               learned (1),
               relay (2)
               }
   MAX-ACCESS  read-write
   STATUS      current
   DESCRIPTION
      "Path: vrfRouterLtd.editConf.dhcpStatic.dnsSetting

       Possibilities:
               configured   (0)
               learned   (1)
               relay   (2)"
   ::= {er1646v2VrfLtdDhcpStatEntry 285212672}

er1646v2VrfLtdDhcpStatNameServer OBJECT-TYPE
   SYNTAX      IpAddress
   MAX-ACCESS  read-write
   STATUS      current
   DESCRIPTION
      "Path: vrfRouterLtd.editConf.dhcpStatic.nameServer"
   ::= {er1646v2VrfLtdDhcpStatEntry 67108864}

er1646v2VrfLtdDhcpStatNameServer2 OBJECT-TYPE
   SYNTAX      IpAddress
   MAX-ACCESS  read-write
   STATUS      current
   DESCRIPTION
      "Path: vrfRouterLtd.editConf.dhcpStatic.nameServer2"
   ::= {er1646v2VrfLtdDhcpStatEntry 234881024}

er1646v2VrfLtdDhcpStatTftpServer OBJECT-TYPE
   SYNTAX      IpAddress
   MAX-ACCESS  read-write
   STATUS      current
   DESCRIPTION
      "Path: vrfRouterLtd.editConf.dhcpStatic.tftpServer"
   ::= {er1646v2VrfLtdDhcpStatEntry 83886080}

er1646v2VrfLtdDhcpStatTftpServerOption OBJECT-TYPE
   SYNTAX      DisplayString
   MAX-ACCESS  read-write
   STATUS      current
   DESCRIPTION
      "Path: vrfRouterLtd.editConf.dhcpStatic.tftpServerOption"
   ::= {er1646v2VrfLtdDhcpStatEntry 335544320}

er1646v2VrfLtdDhcpStatMacAddress OBJECT-TYPE
   SYNTAX      OCTET STRING
   MAX-ACCESS  read-write
   STATUS      current
   DESCRIPTION
      "Path: vrfRouterLtd.editConf.dhcpStatic.macAddress

       MAC address."
   ::= {er1646v2VrfLtdDhcpStatEntry 100663296}

er1646v2VrfLtdDhcpStatBootFile OBJECT-TYPE
   SYNTAX      DisplayString
   MAX-ACCESS  read-write
   STATUS      current
   DESCRIPTION
      "Path: vrfRouterLtd.editConf.dhcpStatic.bootFile"
   ::= {er1646v2VrfLtdDhcpStatEntry 117440512}

er1646v2VrfLtdDhcpStatBootFileOption OBJECT-TYPE
   SYNTAX      DisplayString
   MAX-ACCESS  read-write
   STATUS      current
   DESCRIPTION
      "Path: vrfRouterLtd.editConf.dhcpStatic.bootFileOption"
   ::= {er1646v2VrfLtdDhcpStatEntry 352321536}

er1646v2VrfLtdDhcpStatHostName OBJECT-TYPE
   SYNTAX      DisplayString
   MAX-ACCESS  read-write
   STATUS      current
   DESCRIPTION
      "Path: vrfRouterLtd.editConf.dhcpStatic.hostName"
   ::= {er1646v2VrfLtdDhcpStatEntry 134217728}

er1646v2VrfLtdDhcpStatDomainName OBJECT-TYPE
   SYNTAX      DisplayString
   MAX-ACCESS  read-write
   STATUS      current
   DESCRIPTION
      "Path: vrfRouterLtd.editConf.dhcpStatic.domainName"
   ::= {er1646v2VrfLtdDhcpStatEntry 150994944}

er1646v2VrfLtdDhcpStatNetbiosNS OBJECT-TYPE
   SYNTAX      IpAddress
   MAX-ACCESS  read-write
   STATUS      current
   DESCRIPTION
      "Path: vrfRouterLtd.editConf.dhcpStatic.netbiosNameServer"
   ::= {er1646v2VrfLtdDhcpStatEntry 167772160}

er1646v2VrfLtdDhcpStatNetbiosNS2 OBJECT-TYPE
   SYNTAX      IpAddress
   MAX-ACCESS  read-write
   STATUS      current
   DESCRIPTION
      "Path: vrfRouterLtd.editConf.dhcpStatic.netbiosNameServer2"
   ::= {er1646v2VrfLtdDhcpStatEntry 251658240}

er1646v2VrfLtdDhcpStatNetbiosNT OBJECT-TYPE
   SYNTAX      INTEGER
               {
               nomnode (0),
               bmnode (1),
               pmnode (2),
               mmnode (4),
               hmnode (8)
               }
   MAX-ACCESS  read-write
   STATUS      current
   DESCRIPTION
      "Path: vrfRouterLtd.editConf.dhcpStatic.netbiosNodeType

       Possibilities:
               no-node   (0)
               B-node   (1)
               P-node   (2)
               M-node   (4)
               H-node   (8)"
   ::= {er1646v2VrfLtdDhcpStatEntry 184549376}

er1646v2VrfLtdDhcpStatOptions OBJECT-TYPE
   SYNTAX      SEQUENCE OF Er1646v2VrfLtdDhcpStatOptionsEntry
   MAX-ACCESS  not-accessible
   STATUS      current
   DESCRIPTION
      ""
   ::= {er1646v2VrfLtdDhcpStat 402653184}

er1646v2VrfLtdDhcpStatOptionsEntry OBJECT-TYPE
   SYNTAX      Er1646v2VrfLtdDhcpStatOptionsEntry
   MAX-ACCESS  not-accessible
   STATUS      current
   DESCRIPTION
      ""
   INDEX      { er1646v2VrfLtdDhcpStatOptionsGlobalIx,
                er1646v2VrfLtdDhcpStatTableIx,
                er1646v2VrfLtdDhcpStatOptionsTableIx }
   ::= {er1646v2VrfLtdDhcpStatOptions 1}

Er1646v2VrfLtdDhcpStatOptionsEntry ::=
   SEQUENCE
      {
      er1646v2VrfLtdDhcpStatOptionsActions
         VariableLengthTableActions,
      er1646v2VrfLtdDhcpStatOptionsGlobalIx
         GlobalIndex,
      er1646v2VrfLtdDhcpStatOptionsTableIx
         TableIndex,
      er1646v2VrfLtdDhcpStatOptionsCode
         Integer32,
      er1646v2VrfLtdDhcpStatOptionsValueAscii
         DisplayString,
      er1646v2VrfLtdDhcpStatOptionsValueDecimal
         Integer32,
      er1646v2VrfLtdDhcpStatOptionsValueHexData
         OCTET STRING,
      er1646v2VrfLtdDhcpStatOptionsValueIpAddress
         IpAddress
      }

er1646v2VrfLtdDhcpStatOptionsActions OBJECT-TYPE
   SYNTAX      VariableLengthTableActions
   MAX-ACCESS  read-write
   STATUS      current
   DESCRIPTION
      "By way of this field, some manipulations
       on this table may be performed."
   ::= {er1646v2VrfLtdDhcpStatOptionsEntry 2}

er1646v2VrfLtdDhcpStatOptionsGlobalIx OBJECT-TYPE
   SYNTAX      GlobalIndex
   MAX-ACCESS  not-accessible
   STATUS      current
   DESCRIPTION
      "The value of the tlsCntTreeGlobalIndex of the MANAGED OBJECT."
   ::= {er1646v2VrfLtdDhcpStatOptionsEntry 10}

er1646v2VrfLtdDhcpStatOptionsTableIx OBJECT-TYPE
   SYNTAX      TableIndex
   MAX-ACCESS  not-accessible
   STATUS      current
   DESCRIPTION
      ""
   ::= {er1646v2VrfLtdDhcpStatOptionsEntry 11}

er1646v2VrfLtdDhcpStatOptionsCode OBJECT-TYPE
   SYNTAX      Integer32
   MAX-ACCESS  read-write
   STATUS      current
   DESCRIPTION
      "Path: vrfRouterLtd.editConf.dhcpStatic.options.code"
   ::= {er1646v2VrfLtdDhcpStatOptionsEntry 16777216}

er1646v2VrfLtdDhcpStatOptionsValueAscii OBJECT-TYPE
   SYNTAX      DisplayString
   MAX-ACCESS  read-write
   STATUS      current
   DESCRIPTION
      "Path: vrfRouterLtd.editConf.dhcpStatic.options.value.ascii"
   ::= {er1646v2VrfLtdDhcpStatOptionsEntry 33619968}

er1646v2VrfLtdDhcpStatOptionsValueDecimal OBJECT-TYPE
   SYNTAX      Integer32
   MAX-ACCESS  read-write
   STATUS      current
   DESCRIPTION
      "Path: vrfRouterLtd.editConf.dhcpStatic.options.value.decimal"
   ::= {er1646v2VrfLtdDhcpStatOptionsEntry 33685504}

er1646v2VrfLtdDhcpStatOptionsValueHexData OBJECT-TYPE
   SYNTAX      OCTET STRING
   MAX-ACCESS  read-write
   STATUS      current
   DESCRIPTION
      "Path: vrfRouterLtd.editConf.dhcpStatic.options.value.hexData"
   ::= {er1646v2VrfLtdDhcpStatOptionsEntry 33751040}

er1646v2VrfLtdDhcpStatOptionsValueIpAddress OBJECT-TYPE
   SYNTAX      IpAddress
   MAX-ACCESS  read-write
   STATUS      current
   DESCRIPTION
      "Path: vrfRouterLtd.editConf.dhcpStatic.options.value.ipAddress"
   ::= {er1646v2VrfLtdDhcpStatOptionsEntry 33816576}


er1646v2VrfLtdDhcpDyn OBJECT IDENTIFIER ::= {er1646v2VrfLtd 52}

er1646v2VrfLtdDhcpDynSSCTable OBJECT-TYPE
   SYNTAX      SEQUENCE OF Er1646v2VrfLtdDhcpDynEntry
   MAX-ACCESS  not-accessible
   STATUS      current
   DESCRIPTION
      "Initialisation DHCP server"
   ::= {er1646v2VrfLtdDhcpDyn 1}

er1646v2VrfLtdDhcpDynEntry OBJECT-TYPE
   SYNTAX      Er1646v2VrfLtdDhcpDynEntry
   MAX-ACCESS  not-accessible
   STATUS      current
   DESCRIPTION
      ""
   INDEX      { er1646v2VrfLtdDhcpDynGlobalIx,
                er1646v2VrfLtdDhcpDynTableIx }
   ::= {er1646v2VrfLtdDhcpDynSSCTable 1}

Er1646v2VrfLtdDhcpDynEntry ::=
   SEQUENCE
      {
      er1646v2VrfLtdDhcpDynActions
         VariableLengthTableActions,
      er1646v2VrfLtdDhcpDynGlobalIx
         GlobalIndex,
      er1646v2VrfLtdDhcpDynTableIx
         TableIndex,
      er1646v2VrfLtdDhcpDynIpcpSubnet
         DisplayString,
      er1646v2VrfLtdDhcpDynIpStartAddress
         IpAddress,
      er1646v2VrfLtdDhcpDynIpEndAddress
         IpAddress,
      er1646v2VrfLtdDhcpDynMask
         IpAddress,
      er1646v2VrfLtdDhcpDynGateway
         IpAddress,
      er1646v2VrfLtdDhcpDynInterface
         DisplayString,
      er1646v2VrfLtdDhcpDynDnsSetting
         INTEGER,
      er1646v2VrfLtdDhcpDynNameServer
         IpAddress,
      er1646v2VrfLtdDhcpDynNameServer2
         IpAddress,
      er1646v2VrfLtdDhcpDynTftpServer
         IpAddress,
      er1646v2VrfLtdDhcpDynTftpServerOption
         DisplayString,
      er1646v2VrfLtdDhcpDynLeaseTime
         TimeTicks,
      er1646v2VrfLtdDhcpDynHoldTime
         TimeTicks,
      er1646v2VrfLtdDhcpDynBootFile
         DisplayString,
      er1646v2VrfLtdDhcpDynBootFileOption
         DisplayString,
      er1646v2VrfLtdDhcpDynHostName
         DisplayString,
      er1646v2VrfLtdDhcpDynDomainName
         DisplayString,
      er1646v2VrfLtdDhcpDynNetbiosNS
         IpAddress,
      er1646v2VrfLtdDhcpDynNetbiosNS2
         IpAddress,
      er1646v2VrfLtdDhcpDynNetbiosNT
         INTEGER
      }

er1646v2VrfLtdDhcpDynActions OBJECT-TYPE
   SYNTAX      VariableLengthTableActions
   MAX-ACCESS  read-write
   STATUS      current
   DESCRIPTION
      "By way of this field, some manipulations
       on this table may be performed."
   ::= {er1646v2VrfLtdDhcpDynEntry 2}

er1646v2VrfLtdDhcpDynGlobalIx OBJECT-TYPE
   SYNTAX      GlobalIndex
   MAX-ACCESS  not-accessible
   STATUS      current
   DESCRIPTION
      "The value of the tlsCntTreeGlobalIndex of the MANAGED OBJECT."
   ::= {er1646v2VrfLtdDhcpDynEntry 10}

er1646v2VrfLtdDhcpDynTableIx OBJECT-TYPE
   SYNTAX      TableIndex
   MAX-ACCESS  not-accessible
   STATUS      current
   DESCRIPTION
      ""
   ::= {er1646v2VrfLtdDhcpDynEntry 11}

er1646v2VrfLtdDhcpDynIpcpSubnet OBJECT-TYPE
   SYNTAX      DisplayString
   MAX-ACCESS  read-write
   STATUS      current
   DESCRIPTION
      "Path: vrfRouterLtd.editConf.dhcpDynamic.ipcpSubnet"
   ::= {er1646v2VrfLtdDhcpDynEntry 301989888}

er1646v2VrfLtdDhcpDynIpStartAddress OBJECT-TYPE
   SYNTAX      IpAddress
   MAX-ACCESS  read-write
   STATUS      current
   DESCRIPTION
      "Path: vrfRouterLtd.editConf.dhcpDynamic.ipStartAddress"
   ::= {er1646v2VrfLtdDhcpDynEntry 16777216}

er1646v2VrfLtdDhcpDynIpEndAddress OBJECT-TYPE
   SYNTAX      IpAddress
   MAX-ACCESS  read-write
   STATUS      current
   DESCRIPTION
      "Path: vrfRouterLtd.editConf.dhcpDynamic.ipEndAddress"
   ::= {er1646v2VrfLtdDhcpDynEntry 33554432}

er1646v2VrfLtdDhcpDynMask OBJECT-TYPE
   SYNTAX      IpAddress
   MAX-ACCESS  read-write
   STATUS      current
   DESCRIPTION
      "Path: vrfRouterLtd.editConf.dhcpDynamic.mask"
   ::= {er1646v2VrfLtdDhcpDynEntry 50331648}

er1646v2VrfLtdDhcpDynGateway OBJECT-TYPE
   SYNTAX      IpAddress
   MAX-ACCESS  read-write
   STATUS      current
   DESCRIPTION
      "Path: vrfRouterLtd.editConf.dhcpDynamic.gateway"
   ::= {er1646v2VrfLtdDhcpDynEntry 67108864}

er1646v2VrfLtdDhcpDynInterface OBJECT-TYPE
   SYNTAX      DisplayString
   MAX-ACCESS  read-write
   STATUS      current
   DESCRIPTION
      "Path: vrfRouterLtd.editConf.dhcpDynamic.interface"
   ::= {er1646v2VrfLtdDhcpDynEntry 268435456}

er1646v2VrfLtdDhcpDynDnsSetting OBJECT-TYPE
   SYNTAX      INTEGER
               {
               configured (0),
               learned (1),
               relay (2)
               }
   MAX-ACCESS  read-write
   STATUS      current
   DESCRIPTION
      "Path: vrfRouterLtd.editConf.dhcpDynamic.dnsSetting

       Possibilities:
               configured   (0)
               learned   (1)
               relay   (2)"
   ::= {er1646v2VrfLtdDhcpDynEntry 285212672}

er1646v2VrfLtdDhcpDynNameServer OBJECT-TYPE
   SYNTAX      IpAddress
   MAX-ACCESS  read-write
   STATUS      current
   DESCRIPTION
      "Path: vrfRouterLtd.editConf.dhcpDynamic.nameServer"
   ::= {er1646v2VrfLtdDhcpDynEntry 83886080}

er1646v2VrfLtdDhcpDynNameServer2 OBJECT-TYPE
   SYNTAX      IpAddress
   MAX-ACCESS  read-write
   STATUS      current
   DESCRIPTION
      "Path: vrfRouterLtd.editConf.dhcpDynamic.nameServer2"
   ::= {er1646v2VrfLtdDhcpDynEntry 234881024}

er1646v2VrfLtdDhcpDynTftpServer OBJECT-TYPE
   SYNTAX      IpAddress
   MAX-ACCESS  read-write
   STATUS      current
   DESCRIPTION
      "Path: vrfRouterLtd.editConf.dhcpDynamic.tftpServer"
   ::= {er1646v2VrfLtdDhcpDynEntry 100663296}

er1646v2VrfLtdDhcpDynTftpServerOption OBJECT-TYPE
   SYNTAX      DisplayString
   MAX-ACCESS  read-write
   STATUS      current
   DESCRIPTION
      "Path: vrfRouterLtd.editConf.dhcpDynamic.tftpServerOption"
   ::= {er1646v2VrfLtdDhcpDynEntry 335544320}

er1646v2VrfLtdDhcpDynLeaseTime OBJECT-TYPE
   SYNTAX      TimeTicks
   MAX-ACCESS  read-write
   STATUS      current
   DESCRIPTION
      "Path: vrfRouterLtd.editConf.dhcpDynamic.leaseTime

       Time in centi-second."
   ::= {er1646v2VrfLtdDhcpDynEntry 117440512}

er1646v2VrfLtdDhcpDynHoldTime OBJECT-TYPE
   SYNTAX      TimeTicks
   MAX-ACCESS  read-write
   STATUS      current
   DESCRIPTION
      "Path: vrfRouterLtd.editConf.dhcpDynamic.holdTime

       Time in centi-second."
   ::= {er1646v2VrfLtdDhcpDynEntry 134217728}

er1646v2VrfLtdDhcpDynBootFile OBJECT-TYPE
   SYNTAX      DisplayString
   MAX-ACCESS  read-write
   STATUS      current
   DESCRIPTION
      "Path: vrfRouterLtd.editConf.dhcpDynamic.bootFile"
   ::= {er1646v2VrfLtdDhcpDynEntry 150994944}

er1646v2VrfLtdDhcpDynBootFileOption OBJECT-TYPE
   SYNTAX      DisplayString
   MAX-ACCESS  read-write
   STATUS      current
   DESCRIPTION
      "Path: vrfRouterLtd.editConf.dhcpDynamic.bootFileOption"
   ::= {er1646v2VrfLtdDhcpDynEntry 352321536}

er1646v2VrfLtdDhcpDynHostName OBJECT-TYPE
   SYNTAX      DisplayString
   MAX-ACCESS  read-write
   STATUS      current
   DESCRIPTION
      "Path: vrfRouterLtd.editConf.dhcpDynamic.hostName"
   ::= {er1646v2VrfLtdDhcpDynEntry 167772160}

er1646v2VrfLtdDhcpDynDomainName OBJECT-TYPE
   SYNTAX      DisplayString
   MAX-ACCESS  read-write
   STATUS      current
   DESCRIPTION
      "Path: vrfRouterLtd.editConf.dhcpDynamic.domainName"
   ::= {er1646v2VrfLtdDhcpDynEntry 184549376}

er1646v2VrfLtdDhcpDynNetbiosNS OBJECT-TYPE
   SYNTAX      IpAddress
   MAX-ACCESS  read-write
   STATUS      current
   DESCRIPTION
      "Path: vrfRouterLtd.editConf.dhcpDynamic.netbiosNameServer"
   ::= {er1646v2VrfLtdDhcpDynEntry 201326592}

er1646v2VrfLtdDhcpDynNetbiosNS2 OBJECT-TYPE
   SYNTAX      IpAddress
   MAX-ACCESS  read-write
   STATUS      current
   DESCRIPTION
      "Path: vrfRouterLtd.editConf.dhcpDynamic.netbiosNameServer2"
   ::= {er1646v2VrfLtdDhcpDynEntry 251658240}

er1646v2VrfLtdDhcpDynNetbiosNT OBJECT-TYPE
   SYNTAX      INTEGER
               {
               nomnode (0),
               bmnode (1),
               pmnode (2),
               mmnode (4),
               hmnode (8)
               }
   MAX-ACCESS  read-write
   STATUS      current
   DESCRIPTION
      "Path: vrfRouterLtd.editConf.dhcpDynamic.netbiosNodeType

       Possibilities:
               no-node   (0)
               B-node   (1)
               P-node   (2)
               M-node   (4)
               H-node   (8)"
   ::= {er1646v2VrfLtdDhcpDynEntry 218103808}

er1646v2VrfLtdDhcpDynOptions OBJECT-TYPE
   SYNTAX      SEQUENCE OF Er1646v2VrfLtdDhcpDynOptionsEntry
   MAX-ACCESS  not-accessible
   STATUS      current
   DESCRIPTION
      ""
   ::= {er1646v2VrfLtdDhcpDyn 402653184}

er1646v2VrfLtdDhcpDynOptionsEntry OBJECT-TYPE
   SYNTAX      Er1646v2VrfLtdDhcpDynOptionsEntry
   MAX-ACCESS  not-accessible
   STATUS      current
   DESCRIPTION
      ""
   INDEX      { er1646v2VrfLtdDhcpDynOptionsGlobalIx,
                er1646v2VrfLtdDhcpDynTableIx,
                er1646v2VrfLtdDhcpDynOptionsTableIx }
   ::= {er1646v2VrfLtdDhcpDynOptions 1}

Er1646v2VrfLtdDhcpDynOptionsEntry ::=
   SEQUENCE
      {
      er1646v2VrfLtdDhcpDynOptionsActions
         VariableLengthTableActions,
      er1646v2VrfLtdDhcpDynOptionsGlobalIx
         GlobalIndex,
      er1646v2VrfLtdDhcpDynOptionsTableIx
         TableIndex,
      er1646v2VrfLtdDhcpDynOptionsCode
         Integer32,
      er1646v2VrfLtdDhcpDynOptionsValueAscii
         DisplayString,
      er1646v2VrfLtdDhcpDynOptionsValueDecimal
         Integer32,
      er1646v2VrfLtdDhcpDynOptionsValueHexData
         OCTET STRING,
      er1646v2VrfLtdDhcpDynOptionsValueIpAddress
         IpAddress
      }

er1646v2VrfLtdDhcpDynOptionsActions OBJECT-TYPE
   SYNTAX      VariableLengthTableActions
   MAX-ACCESS  read-write
   STATUS      current
   DESCRIPTION
      "By way of this field, some manipulations
       on this table may be performed."
   ::= {er1646v2VrfLtdDhcpDynOptionsEntry 2}

er1646v2VrfLtdDhcpDynOptionsGlobalIx OBJECT-TYPE
   SYNTAX      GlobalIndex
   MAX-ACCESS  not-accessible
   STATUS      current
   DESCRIPTION
      "The value of the tlsCntTreeGlobalIndex of the MANAGED OBJECT."
   ::= {er1646v2VrfLtdDhcpDynOptionsEntry 10}

er1646v2VrfLtdDhcpDynOptionsTableIx OBJECT-TYPE
   SYNTAX      TableIndex
   MAX-ACCESS  not-accessible
   STATUS      current
   DESCRIPTION
      ""
   ::= {er1646v2VrfLtdDhcpDynOptionsEntry 11}

er1646v2VrfLtdDhcpDynOptionsCode OBJECT-TYPE
   SYNTAX      Integer32
   MAX-ACCESS  read-write
   STATUS      current
   DESCRIPTION
      "Path: vrfRouterLtd.editConf.dhcpDynamic.options.code"
   ::= {er1646v2VrfLtdDhcpDynOptionsEntry 16777216}

er1646v2VrfLtdDhcpDynOptionsValueAscii OBJECT-TYPE
   SYNTAX      DisplayString
   MAX-ACCESS  read-write
   STATUS      current
   DESCRIPTION
      "Path: vrfRouterLtd.editConf.dhcpDynamic.options.value.ascii"
   ::= {er1646v2VrfLtdDhcpDynOptionsEntry 33619968}

er1646v2VrfLtdDhcpDynOptionsValueDecimal OBJECT-TYPE
   SYNTAX      Integer32
   MAX-ACCESS  read-write
   STATUS      current
   DESCRIPTION
      "Path: vrfRouterLtd.editConf.dhcpDynamic.options.value.decimal"
   ::= {er1646v2VrfLtdDhcpDynOptionsEntry 33685504}

er1646v2VrfLtdDhcpDynOptionsValueHexData OBJECT-TYPE
   SYNTAX      OCTET STRING
   MAX-ACCESS  read-write
   STATUS      current
   DESCRIPTION
      "Path: vrfRouterLtd.editConf.dhcpDynamic.options.value.hexData"
   ::= {er1646v2VrfLtdDhcpDynOptionsEntry 33751040}

er1646v2VrfLtdDhcpDynOptionsValueIpAddress OBJECT-TYPE
   SYNTAX      IpAddress
   MAX-ACCESS  read-write
   STATUS      current
   DESCRIPTION
      "Path: vrfRouterLtd.editConf.dhcpDynamic.options.value.ipAddress"
   ::= {er1646v2VrfLtdDhcpDynOptionsEntry 33816576}


er1646v2VrfLtdDhcpCheckAddress OBJECT IDENTIFIER ::= {er1646v2VrfLtd 53}

er1646v2VrfLtdDhcpCheckAddressTable OBJECT-TYPE
   SYNTAX      SEQUENCE OF Er1646v2VrfLtdDhcpCheckAddressEntry
   MAX-ACCESS  not-accessible
   STATUS      current
   DESCRIPTION
      "Should the DCHP server check if the given address is free"
   ::= {er1646v2VrfLtdDhcpCheckAddress 1}

er1646v2VrfLtdDhcpCheckAddressEntry OBJECT-TYPE
   SYNTAX      Er1646v2VrfLtdDhcpCheckAddressEntry
   MAX-ACCESS  not-accessible
   STATUS      current
   DESCRIPTION
      ""
   INDEX      { er1646v2VrfLtdDhcpCheckAddressGlobalIx }
   ::= {er1646v2VrfLtdDhcpCheckAddressTable 1}

Er1646v2VrfLtdDhcpCheckAddressEntry ::=
   SEQUENCE
      {
      er1646v2VrfLtdDhcpCheckAddressGlobalIx
         GlobalIndex,
      er1646v2VrfLtdDhcpCheckAddressValue
         INTEGER
      }

er1646v2VrfLtdDhcpCheckAddressGlobalIx OBJECT-TYPE
   SYNTAX      GlobalIndex
   MAX-ACCESS  not-accessible
   STATUS      current
   DESCRIPTION
      "The value of the tlsCntTreeGlobalIndex of the MANAGED OBJECT."
   ::= {er1646v2VrfLtdDhcpCheckAddressEntry 10}

er1646v2VrfLtdDhcpCheckAddressValue OBJECT-TYPE
   SYNTAX      INTEGER
               {
               disabled (0),
               enabled (1),
               arpOnly (2)
               }
   MAX-ACCESS  read-write
   STATUS      current
   DESCRIPTION
      "Path: vrfRouterLtd.editConf.dhcpCheckAddress

       Possibilities:
               disabled   (0)
               enabled   (1)
               arpOnly   (2)"
   ::= {er1646v2VrfLtdDhcpCheckAddressEntry 2147483648}


er1646v2VrfLtdDhcpCustomVendorId OBJECT IDENTIFIER ::= {er1646v2VrfLtd 81}

er1646v2VrfLtdDhcpCustomVendorIdTable OBJECT-TYPE
   SYNTAX      SEQUENCE OF Er1646v2VrfLtdDhcpCustomVendorIdEntry
   MAX-ACCESS  not-accessible
   STATUS      current
   DESCRIPTION
      "custom-defined DCHP Vendor Id"
   ::= {er1646v2VrfLtdDhcpCustomVendorId 1}

er1646v2VrfLtdDhcpCustomVendorIdEntry OBJECT-TYPE
   SYNTAX      Er1646v2VrfLtdDhcpCustomVendorIdEntry
   MAX-ACCESS  not-accessible
   STATUS      current
   DESCRIPTION
      ""
   INDEX      { er1646v2VrfLtdDhcpCustomVendorIdGlobalIx }
   ::= {er1646v2VrfLtdDhcpCustomVendorIdTable 1}

Er1646v2VrfLtdDhcpCustomVendorIdEntry ::=
   SEQUENCE
      {
      er1646v2VrfLtdDhcpCustomVendorIdGlobalIx
         GlobalIndex,
      er1646v2VrfLtdDhcpCustomVendorIdValue
         DisplayString
      }

er1646v2VrfLtdDhcpCustomVendorIdGlobalIx OBJECT-TYPE
   SYNTAX      GlobalIndex
   MAX-ACCESS  not-accessible
   STATUS      current
   DESCRIPTION
      "The value of the tlsCntTreeGlobalIndex of the MANAGED OBJECT."
   ::= {er1646v2VrfLtdDhcpCustomVendorIdEntry 10}

er1646v2VrfLtdDhcpCustomVendorIdValue OBJECT-TYPE
   SYNTAX      DisplayString
   MAX-ACCESS  read-write
   STATUS      current
   DESCRIPTION
      "Path: vrfRouterLtd.editConf.dhcpCustomVendorId"
   ::= {er1646v2VrfLtdDhcpCustomVendorIdEntry 2147483648}


er1646v2VrfLtdDhcpClientIdentifier OBJECT IDENTIFIER ::= {er1646v2VrfLtd 91}

er1646v2VrfLtdDhcpClientIdentifierTable OBJECT-TYPE
   SYNTAX      SEQUENCE OF Er1646v2VrfLtdDhcpClientIdentifierEntry
   MAX-ACCESS  not-accessible
   STATUS      current
   DESCRIPTION
      "custom-defined DCHP Vendor Id"
   ::= {er1646v2VrfLtdDhcpClientIdentifier 1}

er1646v2VrfLtdDhcpClientIdentifierEntry OBJECT-TYPE
   SYNTAX      Er1646v2VrfLtdDhcpClientIdentifierEntry
   MAX-ACCESS  not-accessible
   STATUS      current
   DESCRIPTION
      ""
   INDEX      { er1646v2VrfLtdDhcpClientIdentifierGlobalIx }
   ::= {er1646v2VrfLtdDhcpClientIdentifierTable 1}

Er1646v2VrfLtdDhcpClientIdentifierEntry ::=
   SEQUENCE
      {
      er1646v2VrfLtdDhcpClientIdentifierGlobalIx
         GlobalIndex,
      er1646v2VrfLtdDhcpClientIdentifierValue
         INTEGER
      }

er1646v2VrfLtdDhcpClientIdentifierGlobalIx OBJECT-TYPE
   SYNTAX      GlobalIndex
   MAX-ACCESS  not-accessible
   STATUS      current
   DESCRIPTION
      "The value of the tlsCntTreeGlobalIndex of the MANAGED OBJECT."
   ::= {er1646v2VrfLtdDhcpClientIdentifierEntry 10}

er1646v2VrfLtdDhcpClientIdentifierValue OBJECT-TYPE
   SYNTAX      INTEGER
               {
               default (0),
               lowest (1),
               interfaceMac (2)
               }
   MAX-ACCESS  read-write
   STATUS      current
   DESCRIPTION
      "Path: vrfRouterLtd.editConf.dhcpClientIdentifier

       Possibilities:
               default   (0)
               lowest   (1)
               interfaceMac   (2)"
   ::= {er1646v2VrfLtdDhcpClientIdentifierEntry 2147483648}


er1646v2VrfLtdAddrPools OBJECT IDENTIFIER ::= {er1646v2VrfLtd 108}

er1646v2VrfLtdAddrPoolsSSCTable OBJECT-TYPE
   SYNTAX      SEQUENCE OF Er1646v2VrfLtdAddrPoolsEntry
   MAX-ACCESS  not-accessible
   STATUS      current
   DESCRIPTION
      "ip address pool union"
   ::= {er1646v2VrfLtdAddrPools 1}

er1646v2VrfLtdAddrPoolsEntry OBJECT-TYPE
   SYNTAX      Er1646v2VrfLtdAddrPoolsEntry
   MAX-ACCESS  not-accessible
   STATUS      current
   DESCRIPTION
      ""
   INDEX      { er1646v2VrfLtdAddrPoolsGlobalIx,
                er1646v2VrfLtdAddrPoolsTableIx }
   ::= {er1646v2VrfLtdAddrPoolsSSCTable 1}

Er1646v2VrfLtdAddrPoolsEntry ::=
   SEQUENCE
      {
      er1646v2VrfLtdAddrPoolsActions
         VariableLengthTableActions,
      er1646v2VrfLtdAddrPoolsGlobalIx
         GlobalIndex,
      er1646v2VrfLtdAddrPoolsTableIx
         TableIndex,
      er1646v2VrfLtdAddrPoolsName
         DisplayString,
      er1646v2VrfLtdAddrPoolsPoolIntervalFrom
         IpAddress,
      er1646v2VrfLtdAddrPoolsPoolIntervalTo
         IpAddress
      }

er1646v2VrfLtdAddrPoolsActions OBJECT-TYPE
   SYNTAX      VariableLengthTableActions
   MAX-ACCESS  read-write
   STATUS      current
   DESCRIPTION
      "By way of this field, some manipulations
       on this table may be performed."
   ::= {er1646v2VrfLtdAddrPoolsEntry 2}

er1646v2VrfLtdAddrPoolsGlobalIx OBJECT-TYPE
   SYNTAX      GlobalIndex
   MAX-ACCESS  not-accessible
   STATUS      current
   DESCRIPTION
      "The value of the tlsCntTreeGlobalIndex of the MANAGED OBJECT."
   ::= {er1646v2VrfLtdAddrPoolsEntry 10}

er1646v2VrfLtdAddrPoolsTableIx OBJECT-TYPE
   SYNTAX      TableIndex
   MAX-ACCESS  not-accessible
   STATUS      current
   DESCRIPTION
      ""
   ::= {er1646v2VrfLtdAddrPoolsEntry 11}

er1646v2VrfLtdAddrPoolsName OBJECT-TYPE
   SYNTAX      DisplayString
   MAX-ACCESS  read-write
   STATUS      current
   DESCRIPTION
      "Path: vrfRouterLtd.editConf.addrPools.name"
   ::= {er1646v2VrfLtdAddrPoolsEntry 16777216}

er1646v2VrfLtdAddrPoolsPoolIntervalFrom OBJECT-TYPE
   SYNTAX      IpAddress
   MAX-ACCESS  read-write
   STATUS      current
   DESCRIPTION
      "Path: vrfRouterLtd.editConf.addrPools.pool.interval.from"
   ::= {er1646v2VrfLtdAddrPoolsEntry 33686016}

er1646v2VrfLtdAddrPoolsPoolIntervalTo OBJECT-TYPE
   SYNTAX      IpAddress
   MAX-ACCESS  read-write
   STATUS      current
   DESCRIPTION
      "Path: vrfRouterLtd.editConf.addrPools.pool.interval.to"
   ::= {er1646v2VrfLtdAddrPoolsEntry 33686272}

er1646v2VrfLtdAddrPoolsPoolList OBJECT-TYPE
   SYNTAX      SEQUENCE OF Er1646v2VrfLtdAddrPoolsPoolListEntry
   MAX-ACCESS  not-accessible
   STATUS      current
   DESCRIPTION
      ""
   ::= {er1646v2VrfLtdAddrPools 33619968}

er1646v2VrfLtdAddrPoolsPoolListEntry OBJECT-TYPE
   SYNTAX      Er1646v2VrfLtdAddrPoolsPoolListEntry
   MAX-ACCESS  not-accessible
   STATUS      current
   DESCRIPTION
      ""
   INDEX      { er1646v2VrfLtdAddrPoolsPoolListGlobalIx,
                er1646v2VrfLtdAddrPoolsTableIx,
                er1646v2VrfLtdAddrPoolsPoolListTableIx }
   ::= {er1646v2VrfLtdAddrPoolsPoolList 1}

Er1646v2VrfLtdAddrPoolsPoolListEntry ::=
   SEQUENCE
      {
      er1646v2VrfLtdAddrPoolsPoolListActions
         VariableLengthTableActions,
      er1646v2VrfLtdAddrPoolsPoolListGlobalIx
         GlobalIndex,
      er1646v2VrfLtdAddrPoolsPoolListTableIx
         TableIndex,
      er1646v2VrfLtdAddrPoolsPoolListLocal
         IpAddress,
      er1646v2VrfLtdAddrPoolsPoolListRemote
         IpAddress,
      er1646v2VrfLtdAddrPoolsPoolListNetMask
         IpAddress
      }

er1646v2VrfLtdAddrPoolsPoolListActions OBJECT-TYPE
   SYNTAX      VariableLengthTableActions
   MAX-ACCESS  read-write
   STATUS      current
   DESCRIPTION
      "By way of this field, some manipulations
       on this table may be performed."
   ::= {er1646v2VrfLtdAddrPoolsPoolListEntry 2}

er1646v2VrfLtdAddrPoolsPoolListGlobalIx OBJECT-TYPE
   SYNTAX      GlobalIndex
   MAX-ACCESS  not-accessible
   STATUS      current
   DESCRIPTION
      "The value of the tlsCntTreeGlobalIndex of the MANAGED OBJECT."
   ::= {er1646v2VrfLtdAddrPoolsPoolListEntry 10}

er1646v2VrfLtdAddrPoolsPoolListTableIx OBJECT-TYPE
   SYNTAX      TableIndex
   MAX-ACCESS  not-accessible
   STATUS      current
   DESCRIPTION
      ""
   ::= {er1646v2VrfLtdAddrPoolsPoolListEntry 11}

er1646v2VrfLtdAddrPoolsPoolListLocal OBJECT-TYPE
   SYNTAX      IpAddress
   MAX-ACCESS  read-write
   STATUS      current
   DESCRIPTION
      "Path: vrfRouterLtd.editConf.addrPools.pool.list.local"
   ::= {er1646v2VrfLtdAddrPoolsPoolListEntry 33554432}

er1646v2VrfLtdAddrPoolsPoolListRemote OBJECT-TYPE
   SYNTAX      IpAddress
   MAX-ACCESS  read-write
   STATUS      current
   DESCRIPTION
      "Path: vrfRouterLtd.editConf.addrPools.pool.list.remote"
   ::= {er1646v2VrfLtdAddrPoolsPoolListEntry 50331648}

er1646v2VrfLtdAddrPoolsPoolListNetMask OBJECT-TYPE
   SYNTAX      IpAddress
   MAX-ACCESS  read-write
   STATUS      current
   DESCRIPTION
      "Path: vrfRouterLtd.editConf.addrPools.pool.list.netMask"
   ::= {er1646v2VrfLtdAddrPoolsPoolListEntry 67108864}


er1646v2VrfLtdDns OBJECT IDENTIFIER ::= {er1646v2VrfLtd 64}

er1646v2VrfLtdDnsSSCTable OBJECT-TYPE
   SYNTAX      SEQUENCE OF Er1646v2VrfLtdDnsEntry
   MAX-ACCESS  not-accessible
   STATUS      current
   DESCRIPTION
      "Domain Name System"
   ::= {er1646v2VrfLtdDns 1}

er1646v2VrfLtdDnsEntry OBJECT-TYPE
   SYNTAX      Er1646v2VrfLtdDnsEntry
   MAX-ACCESS  not-accessible
   STATUS      current
   DESCRIPTION
      ""
   INDEX      { er1646v2VrfLtdDnsGlobalIx }
   ::= {er1646v2VrfLtdDnsSSCTable 1}

Er1646v2VrfLtdDnsEntry ::=
   SEQUENCE
      {
      er1646v2VrfLtdDnsGlobalIx
         GlobalIndex,
      er1646v2VrfLtdDnsPrimaryDns
         IpAddress,
      er1646v2VrfLtdDnsSecondaryDns
         IpAddress,
      er1646v2VrfLtdDnsDomainName
         DisplayString,
      er1646v2VrfLtdDnsIpV6Router
         DisplayString,
      er1646v2VrfLtdDnsPreference
         Integer32,
      er1646v2VrfLtdDnsProxy
         INTEGER,
      er1646v2VrfLtdDnsCacheSize
         Integer32
      }

er1646v2VrfLtdDnsGlobalIx OBJECT-TYPE
   SYNTAX      GlobalIndex
   MAX-ACCESS  not-accessible
   STATUS      current
   DESCRIPTION
      "The value of the tlsCntTreeGlobalIndex of the MANAGED OBJECT."
   ::= {er1646v2VrfLtdDnsEntry 10}

er1646v2VrfLtdDnsPrimaryDns OBJECT-TYPE
   SYNTAX      IpAddress
   MAX-ACCESS  read-write
   STATUS      current
   DESCRIPTION
      "Path: vrfRouterLtd.editConf.dns.primaryDns"
   ::= {er1646v2VrfLtdDnsEntry 16777216}

er1646v2VrfLtdDnsSecondaryDns OBJECT-TYPE
   SYNTAX      IpAddress
   MAX-ACCESS  read-write
   STATUS      current
   DESCRIPTION
      "Path: vrfRouterLtd.editConf.dns.secondaryDns"
   ::= {er1646v2VrfLtdDnsEntry 33554432}

er1646v2VrfLtdDnsDomainName OBJECT-TYPE
   SYNTAX      DisplayString
   MAX-ACCESS  read-write
   STATUS      current
   DESCRIPTION
      "Path: vrfRouterLtd.editConf.dns.domainName"
   ::= {er1646v2VrfLtdDnsEntry 50331648}

er1646v2VrfLtdDnsIpV6Router OBJECT-TYPE
   SYNTAX      DisplayString
   MAX-ACCESS  read-write
   STATUS      current
   DESCRIPTION
      "Path: vrfRouterLtd.editConf.dns.ipV6Router"
   ::= {er1646v2VrfLtdDnsEntry 67108864}

er1646v2VrfLtdDnsPreference OBJECT-TYPE
   SYNTAX      Integer32
   MAX-ACCESS  read-write
   STATUS      current
   DESCRIPTION
      "Path: vrfRouterLtd.editConf.dns.preference"
   ::= {er1646v2VrfLtdDnsEntry 83886080}

er1646v2VrfLtdDnsProxy OBJECT-TYPE
   SYNTAX      INTEGER
               {
               disabled (0),
               enabled (1)
               }
   MAX-ACCESS  read-write
   STATUS      current
   DESCRIPTION
      "Path: vrfRouterLtd.editConf.dns.proxy

       Possibilities:
               disabled   (0)
               enabled   (1)"
   ::= {er1646v2VrfLtdDnsEntry 100663296}

er1646v2VrfLtdDnsCacheSize OBJECT-TYPE
   SYNTAX      Integer32
   MAX-ACCESS  read-write
   STATUS      current
   DESCRIPTION
      "Path: vrfRouterLtd.editConf.dns.cacheSize"
   ::= {er1646v2VrfLtdDnsEntry 117440512}


er1646v2VrfLtdLog OBJECT IDENTIFIER ::= {er1646v2VrfLtd 67}

er1646v2VrfLtdLogSSCTable OBJECT-TYPE
   SYNTAX      SEQUENCE OF Er1646v2VrfLtdLogEntry
   MAX-ACCESS  not-accessible
   STATUS      current
   DESCRIPTION
      "router logging"
   ::= {er1646v2VrfLtdLog 1}

er1646v2VrfLtdLogEntry OBJECT-TYPE
   SYNTAX      Er1646v2VrfLtdLogEntry
   MAX-ACCESS  not-accessible
   STATUS      current
   DESCRIPTION
      ""
   INDEX      { er1646v2VrfLtdLogGlobalIx }
   ::= {er1646v2VrfLtdLogSSCTable 1}

Er1646v2VrfLtdLogEntry ::=
   SEQUENCE
      {
      er1646v2VrfLtdLogGlobalIx
         GlobalIndex,
      er1646v2VrfLtdLogMode
         INTEGER,
      er1646v2VrfLtdLogDhcpSyslogMask
         Integer32
      }

er1646v2VrfLtdLogGlobalIx OBJECT-TYPE
   SYNTAX      GlobalIndex
   MAX-ACCESS  not-accessible
   STATUS      current
   DESCRIPTION
      "The value of the tlsCntTreeGlobalIndex of the MANAGED OBJECT."
   ::= {er1646v2VrfLtdLogEntry 10}

er1646v2VrfLtdLogMode OBJECT-TYPE
   SYNTAX      INTEGER
               {
               disabled (0),
               enabled (1)
               }
   MAX-ACCESS  read-write
   STATUS      current
   DESCRIPTION
      "Path: vrfRouterLtd.editConf.log.mode

       Possibilities:
               disabled   (0)
               enabled   (1)"
   ::= {er1646v2VrfLtdLogEntry 16777216}

er1646v2VrfLtdLogDhcpSyslogMask OBJECT-TYPE
   SYNTAX      Integer32
   MAX-ACCESS  read-write
   STATUS      current
   DESCRIPTION
      "Path: vrfRouterLtd.editConf.log.dhcpSyslogMask

       Bit meanings:
               bit 0 = lease,
               bit 1 = renew,
               bit 2 = rebind,
               bit 3 = expired"
   ::= {er1646v2VrfLtdLogEntry 33554432}


er1646v2VrfLtdHelperProtocols OBJECT IDENTIFIER ::= {er1646v2VrfLtd 15}

er1646v2VrfLtdHelperProtocolsSSCTable OBJECT-TYPE
   SYNTAX      SEQUENCE OF Er1646v2VrfLtdHelperProtocolsEntry
   MAX-ACCESS  not-accessible
   STATUS      current
   DESCRIPTION
      "list of protocols to be forwarded by the IP helpers"
   ::= {er1646v2VrfLtdHelperProtocols 1}

er1646v2VrfLtdHelperProtocolsEntry OBJECT-TYPE
   SYNTAX      Er1646v2VrfLtdHelperProtocolsEntry
   MAX-ACCESS  not-accessible
   STATUS      current
   DESCRIPTION
      ""
   INDEX      { er1646v2VrfLtdHelperProtocolsGlobalIx,
                er1646v2VrfLtdHelperProtocolsTableIx }
   ::= {er1646v2VrfLtdHelperProtocolsSSCTable 1}

Er1646v2VrfLtdHelperProtocolsEntry ::=
   SEQUENCE
      {
      er1646v2VrfLtdHelperProtocolsActions
         VariableLengthTableActions,
      er1646v2VrfLtdHelperProtocolsGlobalIx
         GlobalIndex,
      er1646v2VrfLtdHelperProtocolsTableIx
         TableIndex,
      er1646v2VrfLtdHelperProtocolsType
         Integer32
      }

er1646v2VrfLtdHelperProtocolsActions OBJECT-TYPE
   SYNTAX      VariableLengthTableActions
   MAX-ACCESS  read-write
   STATUS      current
   DESCRIPTION
      "By way of this field, some manipulations
       on this table may be performed."
   ::= {er1646v2VrfLtdHelperProtocolsEntry 2}

er1646v2VrfLtdHelperProtocolsGlobalIx OBJECT-TYPE
   SYNTAX      GlobalIndex
   MAX-ACCESS  not-accessible
   STATUS      current
   DESCRIPTION
      "The value of the tlsCntTreeGlobalIndex of the MANAGED OBJECT."
   ::= {er1646v2VrfLtdHelperProtocolsEntry 10}

er1646v2VrfLtdHelperProtocolsTableIx OBJECT-TYPE
   SYNTAX      TableIndex
   MAX-ACCESS  not-accessible
   STATUS      current
   DESCRIPTION
      ""
   ::= {er1646v2VrfLtdHelperProtocolsEntry 11}

er1646v2VrfLtdHelperProtocolsType OBJECT-TYPE
   SYNTAX      Integer32
   MAX-ACCESS  read-write
   STATUS      current
   DESCRIPTION
      "Path: vrfRouterLtd.editConf.helperProtocols.protocol"
   ::= {er1646v2VrfLtdHelperProtocolsEntry 16777216}


er1646v2VrfLtdHosts OBJECT IDENTIFIER ::= {er1646v2VrfLtd 49}

er1646v2VrfLtdHostsSSCTable OBJECT-TYPE
   SYNTAX      SEQUENCE OF Er1646v2VrfLtdHostsEntry
   MAX-ACCESS  not-accessible
   STATUS      current
   DESCRIPTION
      "table of hosts with their ip address"
   ::= {er1646v2VrfLtdHosts 1}

er1646v2VrfLtdHostsEntry OBJECT-TYPE
   SYNTAX      Er1646v2VrfLtdHostsEntry
   MAX-ACCESS  not-accessible
   STATUS      current
   DESCRIPTION
      ""
   INDEX      { er1646v2VrfLtdHostsGlobalIx,
                er1646v2VrfLtdHostsTableIx }
   ::= {er1646v2VrfLtdHostsSSCTable 1}

Er1646v2VrfLtdHostsEntry ::=
   SEQUENCE
      {
      er1646v2VrfLtdHostsActions
         VariableLengthTableActions,
      er1646v2VrfLtdHostsGlobalIx
         GlobalIndex,
      er1646v2VrfLtdHostsTableIx
         TableIndex,
      er1646v2VrfLtdHostsHostname
         DisplayString,
      er1646v2VrfLtdHostsIpAddress
         IpAddress
      }

er1646v2VrfLtdHostsActions OBJECT-TYPE
   SYNTAX      VariableLengthTableActions
   MAX-ACCESS  read-write
   STATUS      current
   DESCRIPTION
      "By way of this field, some manipulations
       on this table may be performed."
   ::= {er1646v2VrfLtdHostsEntry 2}

er1646v2VrfLtdHostsGlobalIx OBJECT-TYPE
   SYNTAX      GlobalIndex
   MAX-ACCESS  not-accessible
   STATUS      current
   DESCRIPTION
      "The value of the tlsCntTreeGlobalIndex of the MANAGED OBJECT."
   ::= {er1646v2VrfLtdHostsEntry 10}

er1646v2VrfLtdHostsTableIx OBJECT-TYPE
   SYNTAX      TableIndex
   MAX-ACCESS  not-accessible
   STATUS      current
   DESCRIPTION
      ""
   ::= {er1646v2VrfLtdHostsEntry 11}

er1646v2VrfLtdHostsHostname OBJECT-TYPE
   SYNTAX      DisplayString
   MAX-ACCESS  read-write
   STATUS      current
   DESCRIPTION
      "Path: vrfRouterLtd.editConf.hosts.hostname"
   ::= {er1646v2VrfLtdHostsEntry 16777216}

er1646v2VrfLtdHostsIpAddress OBJECT-TYPE
   SYNTAX      IpAddress
   MAX-ACCESS  read-write
   STATUS      current
   DESCRIPTION
      "Path: vrfRouterLtd.editConf.hosts.ipAddress"
   ::= {er1646v2VrfLtdHostsEntry 33554432}


er1646v2VrfLtdQm OBJECT IDENTIFIER ::= {er1646v2VrfLtd 77}

er1646v2VrfLtdQmSSCTable OBJECT-TYPE
   SYNTAX      SEQUENCE OF Er1646v2VrfLtdQmEntry
   MAX-ACCESS  not-accessible
   STATUS      current
   DESCRIPTION
      "quality monitor"
   ::= {er1646v2VrfLtdQm 1}

er1646v2VrfLtdQmEntry OBJECT-TYPE
   SYNTAX      Er1646v2VrfLtdQmEntry
   MAX-ACCESS  not-accessible
   STATUS      current
   DESCRIPTION
      ""
   INDEX      { er1646v2VrfLtdQmGlobalIx }
   ::= {er1646v2VrfLtdQmSSCTable 1}

Er1646v2VrfLtdQmEntry ::=
   SEQUENCE
      {
      er1646v2VrfLtdQmGlobalIx
         GlobalIndex,
      er1646v2VrfLtdQmMonitor
         INTEGER,
      er1646v2VrfLtdQmType
         INTEGER,
      er1646v2VrfLtdQmStartDelay
         TimeTicks
      }

er1646v2VrfLtdQmGlobalIx OBJECT-TYPE
   SYNTAX      GlobalIndex
   MAX-ACCESS  not-accessible
   STATUS      current
   DESCRIPTION
      "The value of the tlsCntTreeGlobalIndex of the MANAGED OBJECT."
   ::= {er1646v2VrfLtdQmEntry 10}

er1646v2VrfLtdQmMonitor OBJECT-TYPE
   SYNTAX      INTEGER
               {
               disabled (0),
               enabled (1)
               }
   MAX-ACCESS  read-write
   STATUS      current
   DESCRIPTION
      "Path: vrfRouterLtd.editConf.qualityMonitor.monitor

       Possibilities:
               disabled   (0)
               enabled   (1)"
   ::= {er1646v2VrfLtdQmEntry 33554432}

er1646v2VrfLtdQmType OBJECT-TYPE
   SYNTAX      INTEGER
               {
               sequential (0),
               concurrent (1)
               }
   MAX-ACCESS  read-write
   STATUS      current
   DESCRIPTION
      "Path: vrfRouterLtd.editConf.qualityMonitor.type

       Possibilities:
               sequential   (0)
               concurrent   (1)"
   ::= {er1646v2VrfLtdQmEntry 16777216}

er1646v2VrfLtdQmStartDelay OBJECT-TYPE
   SYNTAX      TimeTicks
   MAX-ACCESS  read-write
   STATUS      current
   DESCRIPTION
      "Path: vrfRouterLtd.editConf.qualityMonitor.startDelay

       Time in centi-second."
   ::= {er1646v2VrfLtdQmEntry 83886080}

er1646v2VrfLtdQmDest OBJECT-TYPE
   SYNTAX      SEQUENCE OF Er1646v2VrfLtdQmDestEntry
   MAX-ACCESS  not-accessible
   STATUS      current
   DESCRIPTION
      ""
   ::= {er1646v2VrfLtdQm 50331648}

er1646v2VrfLtdQmDestEntry OBJECT-TYPE
   SYNTAX      Er1646v2VrfLtdQmDestEntry
   MAX-ACCESS  not-accessible
   STATUS      current
   DESCRIPTION
      ""
   INDEX      { er1646v2VrfLtdQmDestGlobalIx,
                er1646v2VrfLtdQmDestTableIx }
   ::= {er1646v2VrfLtdQmDest 1}

Er1646v2VrfLtdQmDestEntry ::=
   SEQUENCE
      {
      er1646v2VrfLtdQmDestActions
         VariableLengthTableActions,
      er1646v2VrfLtdQmDestGlobalIx
         GlobalIndex,
      er1646v2VrfLtdQmDestTableIx
         TableIndex,
      er1646v2VrfLtdQmDestName
         DisplayString,
      er1646v2VrfLtdQmDestAdminStatus
         INTEGER,
      er1646v2VrfLtdQmDestIpAddress
         IpAddress,
      er1646v2VrfLtdQmDestHostName
         DisplayString,
      er1646v2VrfLtdQmDestSource
         IpAddress,
      er1646v2VrfLtdQmDestTos
         INTEGER,
      er1646v2VrfLtdQmDestPriority
         INTEGER,
      er1646v2VrfLtdQmDestProtocolIcmp
         OCTET STRING,
      er1646v2VrfLtdQmDestProtocolUdpEcho
         OCTET STRING,
      er1646v2VrfLtdQmDestProtocolUdpServerPort
         Integer32,
      er1646v2VrfLtdQmDestProtocolTwampLightPort
         Integer32,
      er1646v2VrfLtdQmDestProtocolBfdInterval
         Integer32,
      er1646v2VrfLtdQmDestProtocolBfdMinRx
         Integer32,
      er1646v2VrfLtdQmDestProtocolBfdMultiplier
         Integer32,
      er1646v2VrfLtdQmDestProtocolBfdEcho
         INTEGER,
      er1646v2VrfLtdQmDestTxInterface
         DisplayString,
      er1646v2VrfLtdQmDestTxGateway
         IpAddress,
      er1646v2VrfLtdQmDestInterval
         Integer32,
      er1646v2VrfLtdQmDestTimeOut
         Integer32,
      er1646v2VrfLtdQmDestLength
         Integer32,
      er1646v2VrfLtdQmDestIdleSamples
         Integer32,
      er1646v2VrfLtdQmDestLossAlarmSamples
         Integer32,
      er1646v2VrfLtdQmDestLossAlarmAlarmOn
         Integer32,
      er1646v2VrfLtdQmDestLossAlarmAlarmOff
         Integer32,
      er1646v2VrfLtdQmDestLossAlarmAlarmUpOn
         Integer32,
      er1646v2VrfLtdQmDestLossAlarmAlarmUpOff
         Integer32,
      er1646v2VrfLtdQmDestLossAlarmAlarmDownOn
         Integer32,
      er1646v2VrfLtdQmDestLossAlarmAlarmDownOff
         Integer32,
      er1646v2VrfLtdQmDestDelayAlarmSamples
         Integer32,
      er1646v2VrfLtdQmDestDelayAlarmDelayAvrgOn
         Integer32,
      er1646v2VrfLtdQmDestDelayAlarmDelayAvrgOff
         Integer32,
      er1646v2VrfLtdQmDestDelayAlarmDelayMaxOn
         Integer32,
      er1646v2VrfLtdQmDestDelayAlarmDelayMaxOff
         Integer32,
      er1646v2VrfLtdQmDestDelayAlarmDelayMinMaxOn
         Integer32,
      er1646v2VrfLtdQmDestDelayAlarmDelayMinMaxOff
         Integer32,
      er1646v2VrfLtdQmDestDelayAlarmDsType
         INTEGER,
      er1646v2VrfLtdQmDestDelayAlarmDsBinsN
         INTEGER,
      er1646v2VrfLtdQmDestDelayAlarmDsBinsNMn
         Integer32,
      er1646v2VrfLtdQmDestDelayAlarmDsBinsNMx
         Integer32,
      er1646v2VrfLtdQmDestDelayAlarmDsBinsTB1
         Integer32,
      er1646v2VrfLtdQmDestDelayAlarmDsBinsTB2
         Integer32,
      er1646v2VrfLtdQmDestDelayAlarmDsBinsTB3
         Integer32,
      er1646v2VrfLtdQmDestDelayAlarmDsBinsTB4
         Integer32,
      er1646v2VrfLtdQmDestDelayAlarmDsBinsTB5
         Integer32,
      er1646v2VrfLtdQmDestDelayAlarmDsBinsTB6
         Integer32,
      er1646v2VrfLtdQmDestDelayAlarmDsBinsTB7
         Integer32,
      er1646v2VrfLtdQmDestDelayAlarmDsBinsTB8
         Integer32,
      er1646v2VrfLtdQmDestDelayAlarmDsBinsTMx
         Integer32,
      er1646v2VrfLtdQmDestDelayAlarmJitterAvrgOn
         Integer32,
      er1646v2VrfLtdQmDestDelayAlarmJitterAvrgOff
         Integer32,
      er1646v2VrfLtdQmDestDelayAlarmJitterMaxOn
         Integer32,
      er1646v2VrfLtdQmDestDelayAlarmJitterMaxOff
         Integer32,
      er1646v2VrfLtdQmDestDelayAlarmJsN
         INTEGER,
      er1646v2VrfLtdQmDestDelayAlarmJsNMn
         Integer32,
      er1646v2VrfLtdQmDestDelayAlarmJsNMx
         Integer32,
      er1646v2VrfLtdQmDestDelayAlarmJsTB1
         Integer32,
      er1646v2VrfLtdQmDestDelayAlarmJsTB2
         Integer32,
      er1646v2VrfLtdQmDestDelayAlarmJsTB3
         Integer32,
      er1646v2VrfLtdQmDestDelayAlarmJsTB4
         Integer32,
      er1646v2VrfLtdQmDestDelayAlarmJsTB5
         Integer32,
      er1646v2VrfLtdQmDestDelayAlarmJsTB6
         Integer32,
      er1646v2VrfLtdQmDestDelayAlarmJsTB7
         Integer32,
      er1646v2VrfLtdQmDestDelayAlarmJsTB8
         Integer32,
      er1646v2VrfLtdQmDestDelayAlarmJsTMx
         Integer32,
      er1646v2VrfLtdQmDestDelayAlarmJitterUpAvrgOn
         Integer32,
      er1646v2VrfLtdQmDestDelayAlarmJitterUpAvrgOff
         Integer32,
      er1646v2VrfLtdQmDestDelayAlarmJitterUpMaxOn
         Integer32,
      er1646v2VrfLtdQmDestDelayAlarmJitterUpMaxOff
         Integer32,
      er1646v2VrfLtdQmDestDelayAlarmJupsN
         INTEGER,
      er1646v2VrfLtdQmDestDelayAlarmJupsNMn
         Integer32,
      er1646v2VrfLtdQmDestDelayAlarmJupsNMx
         Integer32,
      er1646v2VrfLtdQmDestDelayAlarmJupsTB1
         Integer32,
      er1646v2VrfLtdQmDestDelayAlarmJupsTB2
         Integer32,
      er1646v2VrfLtdQmDestDelayAlarmJupsTB3
         Integer32,
      er1646v2VrfLtdQmDestDelayAlarmJupsTB4
         Integer32,
      er1646v2VrfLtdQmDestDelayAlarmJupsTB5
         Integer32,
      er1646v2VrfLtdQmDestDelayAlarmJupsTB6
         Integer32,
      er1646v2VrfLtdQmDestDelayAlarmJupsTB7
         Integer32,
      er1646v2VrfLtdQmDestDelayAlarmJupsTB8
         Integer32,
      er1646v2VrfLtdQmDestDelayAlarmJupsTMx
         Integer32,
      er1646v2VrfLtdQmDestDelayAlarmJitterDownAvrgOn
         Integer32,
      er1646v2VrfLtdQmDestDelayAlarmJitterDownAvrgOff
         Integer32,
      er1646v2VrfLtdQmDestDelayAlarmJitterDownMaxOn
         Integer32,
      er1646v2VrfLtdQmDestDelayAlarmJitterDownMaxOff
         Integer32,
      er1646v2VrfLtdQmDestDelayAlarmJdownsN
         INTEGER,
      er1646v2VrfLtdQmDestDelayAlarmJdownsNMn
         Integer32,
      er1646v2VrfLtdQmDestDelayAlarmJdownsNMx
         Integer32,
      er1646v2VrfLtdQmDestDelayAlarmJdownsTB1
         Integer32,
      er1646v2VrfLtdQmDestDelayAlarmJdownsTB2
         Integer32,
      er1646v2VrfLtdQmDestDelayAlarmJdownsTB3
         Integer32,
      er1646v2VrfLtdQmDestDelayAlarmJdownsTB4
         Integer32,
      er1646v2VrfLtdQmDestDelayAlarmJdownsTB5
         Integer32,
      er1646v2VrfLtdQmDestDelayAlarmJdownsTB6
         Integer32,
      er1646v2VrfLtdQmDestDelayAlarmJdownsTB7
         Integer32,
      er1646v2VrfLtdQmDestDelayAlarmJdownsTB8
         Integer32,
      er1646v2VrfLtdQmDestDelayAlarmJdownsTMx
         Integer32,
      er1646v2VrfLtdQmDestDelayAlarmDelayUpAvrgOn
         Integer32,
      er1646v2VrfLtdQmDestDelayAlarmDelayUpAvrgOff
         Integer32,
      er1646v2VrfLtdQmDestDelayAlarmDelayUpMaxOn
         Integer32,
      er1646v2VrfLtdQmDestDelayAlarmDelayUpMaxOff
         Integer32,
      er1646v2VrfLtdQmDestDelayAlarmDupsType
         INTEGER,
      er1646v2VrfLtdQmDestDelayAlarmDupsBinsN
         INTEGER,
      er1646v2VrfLtdQmDestDelayAlarmDupsBinsNMn
         Integer32,
      er1646v2VrfLtdQmDestDelayAlarmDupsBinsNMx
         Integer32,
      er1646v2VrfLtdQmDestDelayAlarmDupsBinsTB1
         Integer32,
      er1646v2VrfLtdQmDestDelayAlarmDupsBinsTB2
         Integer32,
      er1646v2VrfLtdQmDestDelayAlarmDupsBinsTB3
         Integer32,
      er1646v2VrfLtdQmDestDelayAlarmDupsBinsTB4
         Integer32,
      er1646v2VrfLtdQmDestDelayAlarmDupsBinsTB5
         Integer32,
      er1646v2VrfLtdQmDestDelayAlarmDupsBinsTB6
         Integer32,
      er1646v2VrfLtdQmDestDelayAlarmDupsBinsTB7
         Integer32,
      er1646v2VrfLtdQmDestDelayAlarmDupsBinsTB8
         Integer32,
      er1646v2VrfLtdQmDestDelayAlarmDupsBinsTMx
         Integer32,
      er1646v2VrfLtdQmDestDelayAlarmDelayDownAvrgOn
         Integer32,
      er1646v2VrfLtdQmDestDelayAlarmDelayDownAvrgOff
         Integer32,
      er1646v2VrfLtdQmDestDelayAlarmDelayDownMaxOn
         Integer32,
      er1646v2VrfLtdQmDestDelayAlarmDelayDownMaxOff
         Integer32,
      er1646v2VrfLtdQmDestDelayAlarmDdownsType
         INTEGER,
      er1646v2VrfLtdQmDestDelayAlarmDdownsBinsN
         INTEGER,
      er1646v2VrfLtdQmDestDelayAlarmDdownsBinsNMn
         Integer32,
      er1646v2VrfLtdQmDestDelayAlarmDdownsBinsNMx
         Integer32,
      er1646v2VrfLtdQmDestDelayAlarmDdownsBinsTB1
         Integer32,
      er1646v2VrfLtdQmDestDelayAlarmDdownsBinsTB2
         Integer32,
      er1646v2VrfLtdQmDestDelayAlarmDdownsBinsTB3
         Integer32,
      er1646v2VrfLtdQmDestDelayAlarmDdownsBinsTB4
         Integer32,
      er1646v2VrfLtdQmDestDelayAlarmDdownsBinsTB5
         Integer32,
      er1646v2VrfLtdQmDestDelayAlarmDdownsBinsTB6
         Integer32,
      er1646v2VrfLtdQmDestDelayAlarmDdownsBinsTB7
         Integer32,
      er1646v2VrfLtdQmDestDelayAlarmDdownsBinsTB8
         Integer32,
      er1646v2VrfLtdQmDestDelayAlarmDdownsBinsTMx
         Integer32,
      er1646v2VrfLtdQmDestAlarmMask
         Integer32,
      er1646v2VrfLtdQmDestLogging
         INTEGER,
      er1646v2VrfLtdQmDestLoggingDepth
         INTEGER
      }

er1646v2VrfLtdQmDestActions OBJECT-TYPE
   SYNTAX      VariableLengthTableActions
   MAX-ACCESS  read-write
   STATUS      current
   DESCRIPTION
      "By way of this field, some manipulations
       on this table may be performed."
   ::= {er1646v2VrfLtdQmDestEntry 2}

er1646v2VrfLtdQmDestGlobalIx OBJECT-TYPE
   SYNTAX      GlobalIndex
   MAX-ACCESS  not-accessible
   STATUS      current
   DESCRIPTION
      "The value of the tlsCntTreeGlobalIndex of the MANAGED OBJECT."
   ::= {er1646v2VrfLtdQmDestEntry 10}

er1646v2VrfLtdQmDestTableIx OBJECT-TYPE
   SYNTAX      TableIndex
   MAX-ACCESS  not-accessible
   STATUS      current
   DESCRIPTION
      ""
   ::= {er1646v2VrfLtdQmDestEntry 11}

er1646v2VrfLtdQmDestName OBJECT-TYPE
   SYNTAX      DisplayString
   MAX-ACCESS  read-write
   STATUS      current
   DESCRIPTION
      "Path: vrfRouterLtd.editConf.qualityMonitor.destinations.name"
   ::= {er1646v2VrfLtdQmDestEntry 234881024}

er1646v2VrfLtdQmDestAdminStatus OBJECT-TYPE
   SYNTAX      INTEGER
               {
               enabled (1),
               onDemand (2),
               disabled (3)
               }
   MAX-ACCESS  read-write
   STATUS      current
   DESCRIPTION
      "Path: vrfRouterLtd.editConf.qualityMonitor.destinations.adminStatus

       Possibilities:
               enabled   (1)
               onDemand   (2)
               disabled   (3)"
   ::= {er1646v2VrfLtdQmDestEntry 369098752}

er1646v2VrfLtdQmDestIpAddress OBJECT-TYPE
   SYNTAX      IpAddress
   MAX-ACCESS  read-write
   STATUS      current
   DESCRIPTION
      "Path: vrfRouterLtd.editConf.qualityMonitor.destinations.ipAddress"
   ::= {er1646v2VrfLtdQmDestEntry 16777216}

er1646v2VrfLtdQmDestHostName OBJECT-TYPE
   SYNTAX      DisplayString
   MAX-ACCESS  read-write
   STATUS      current
   DESCRIPTION
      "Path: vrfRouterLtd.editConf.qualityMonitor.destinations.hostName"
   ::= {er1646v2VrfLtdQmDestEntry 33554432}

er1646v2VrfLtdQmDestSource OBJECT-TYPE
   SYNTAX      IpAddress
   MAX-ACCESS  read-write
   STATUS      current
   DESCRIPTION
      "Path: vrfRouterLtd.editConf.qualityMonitor.destinations.source"
   ::= {er1646v2VrfLtdQmDestEntry 184549376}

er1646v2VrfLtdQmDestTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfRouterLtd.editConf.qualityMonitor.destinations.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VrfLtdQmDestEntry 167772160}

er1646v2VrfLtdQmDestPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: vrfRouterLtd.editConf.qualityMonitor.destinations.priority

       Possibilities:
               queue1   (0)
               queue2   (1)
               queue3   (2)
               queue4   (3)
               queue5   (4)
               lowDelayQueue   (5)
               lowDelay2Queue   (6)
               systemQueue   (7)"
   ::= {er1646v2VrfLtdQmDestEntry 218103808}

er1646v2VrfLtdQmDestProtocolIcmp OBJECT-TYPE
   SYNTAX      OCTET STRING
   MAX-ACCESS  read-write
   STATUS      current
   DESCRIPTION
      "Path: vrfRouterLtd.editConf.qualityMonitor.destinations.protocol.icmp"
   ::= {er1646v2VrfLtdQmDestEntry 50397184}

er1646v2VrfLtdQmDestProtocolUdpEcho OBJECT-TYPE
   SYNTAX      OCTET STRING
   MAX-ACCESS  read-write
   STATUS      current
   DESCRIPTION
      "Path: vrfRouterLtd.editConf.qualityMonitor.destinations.protocol.udpEcho"
   ::= {er1646v2VrfLtdQmDestEntry 50462720}

er1646v2VrfLtdQmDestProtocolUdpServerPort OBJECT-TYPE
   SYNTAX      Integer32
   MAX-ACCESS  read-write
   STATUS      current
   DESCRIPTION
      "Path: vrfRouterLtd.editConf.qualityMonitor.destinations.protocol.udpServerPort"
   ::= {er1646v2VrfLtdQmDestEntry 50528256}

er1646v2VrfLtdQmDestProtocolTwampLightPort OBJECT-TYPE
   SYNTAX      Integer32
   MAX-ACCESS  read-write
   STATUS      current
   DESCRIPTION
      "Path: vrfRouterLtd.editConf.qualityMonitor.destinations.protocol.twampLightPort"
   ::= {er1646v2VrfLtdQmDestEntry 50593792}

er1646v2VrfLtdQmDestProtocolBfdInterval OBJECT-TYPE
   SYNTAX      Integer32
   UNITS       "ms"
   MAX-ACCESS  read-write
   STATUS      current
   DESCRIPTION
      "Path: vrfRouterLtd.editConf.qualityMonitor.destinations.protocol.bfd.interval

       unit name = ms"
   ::= {er1646v2VrfLtdQmDestEntry 50659584}

er1646v2VrfLtdQmDestProtocolBfdMinRx OBJECT-TYPE
   SYNTAX      Integer32
   UNITS       "ms"
   MAX-ACCESS  read-write
   STATUS      current
   DESCRIPTION
      "Path: vrfRouterLtd.editConf.qualityMonitor.destinations.protocol.bfd.minRx

       unit name = ms"
   ::= {er1646v2VrfLtdQmDestEntry 50659840}

er1646v2VrfLtdQmDestProtocolBfdMultiplier OBJECT-TYPE
   SYNTAX      Integer32
   MAX-ACCESS  read-write
   STATUS      current
   DESCRIPTION
      "Path: vrfRouterLtd.editConf.qualityMonitor.destinations.protocol.bfd.multiplier"
   ::= {er1646v2VrfLtdQmDestEntry 50660096}

er1646v2VrfLtdQmDestProtocolBfdEcho OBJECT-TYPE
   SYNTAX      INTEGER
               {
               txRx (1),
               tx (2),
               rx (3),
               no (4)
               }
   MAX-ACCESS  read-write
   STATUS      current
   DESCRIPTION
      "Path: vrfRouterLtd.editConf.qualityMonitor.destinations.protocol.bfd.echo

       Possibilities:
               txRx   (1)
               tx   (2)
               rx   (3)
               no   (4)"
   ::= {er1646v2VrfLtdQmDestEntry 50660352}

er1646v2VrfLtdQmDestTxInterface OBJECT-TYPE
   SYNTAX      DisplayString
   MAX-ACCESS  read-write
   STATUS      current
   DESCRIPTION
      "Path: vrfRouterLtd.editConf.qualityMonitor.destinations.txInterface"
   ::= {er1646v2VrfLtdQmDestEntry 402653184}

er1646v2VrfLtdQmDestTxGateway OBJECT-TYPE
   SYNTAX      IpAddress
   MAX-ACCESS  read-write
   STATUS      current
   DESCRIPTION
      "Path: vrfRouterLtd.editConf.qualityMonitor.destinations.txGateway"
   ::= {er1646v2VrfLtdQmDestEntry 419430400}

er1646v2VrfLtdQmDestInterval OBJECT-TYPE
   SYNTAX      Integer32
   UNITS       "100msec"
   MAX-ACCESS  read-write
   STATUS      current
   DESCRIPTION
      "Path: vrfRouterLtd.editConf.qualityMonitor.destinations.interval

       unit name = 100msec"
   ::= {er1646v2VrfLtdQmDestEntry 67108864}

er1646v2VrfLtdQmDestTimeOut OBJECT-TYPE
   SYNTAX      Integer32
   UNITS       "100msec"
   MAX-ACCESS  read-write
   STATUS      current
   DESCRIPTION
      "Path: vrfRouterLtd.editConf.qualityMonitor.destinations.timeOut

       unit name = 100msec"
   ::= {er1646v2VrfLtdQmDestEntry 150994944}

er1646v2VrfLtdQmDestLength OBJECT-TYPE
   SYNTAX      Integer32
   MAX-ACCESS  read-write
   STATUS      current
   DESCRIPTION
      "Path: vrfRouterLtd.editConf.qualityMonitor.destinations.length"
   ::= {er1646v2VrfLtdQmDestEntry 83886080}

er1646v2VrfLtdQmDestIdleSamples OBJECT-TYPE
   SYNTAX      Integer32
   MAX-ACCESS  read-write
   STATUS      current
   DESCRIPTION
      "Path: vrfRouterLtd.editConf.qualityMonitor.destinations.idleSamples"
   ::= {er1646v2VrfLtdQmDestEntry 268435456}

er1646v2VrfLtdQmDestLossAlarmSamples OBJECT-TYPE
   SYNTAX      Integer32
   MAX-ACCESS  read-write
   STATUS      current
   DESCRIPTION
      "Path: vrfRouterLtd.editConf.qualityMonitor.destinations.lossAlarm.samples"
   ::= {er1646v2VrfLtdQmDestEntry 100728832}

er1646v2VrfLtdQmDestLossAlarmAlarmOn OBJECT-TYPE
   SYNTAX      Integer32
   MAX-ACCESS  read-write
   STATUS      current
   DESCRIPTION
      "Path: vrfRouterLtd.editConf.qualityMonitor.destinations.lossAlarm.alarmOn"
   ::= {er1646v2VrfLtdQmDestEntry 100794368}

er1646v2VrfLtdQmDestLossAlarmAlarmOff OBJECT-TYPE
   SYNTAX      Integer32
   MAX-ACCESS  read-write
   STATUS      current
   DESCRIPTION
      "Path: vrfRouterLtd.editConf.qualityMonitor.destinations.lossAlarm.alarmOff"
   ::= {er1646v2VrfLtdQmDestEntry 100859904}

er1646v2VrfLtdQmDestLossAlarmAlarmUpOn OBJECT-TYPE
   SYNTAX      Integer32
   MAX-ACCESS  read-write
   STATUS      current
   DESCRIPTION
      "Path: vrfRouterLtd.editConf.qualityMonitor.destinations.lossAlarm.alarmUpOn"
   ::= {er1646v2VrfLtdQmDestEntry 100925440}

er1646v2VrfLtdQmDestLossAlarmAlarmUpOff OBJECT-TYPE
   SYNTAX      Integer32
   MAX-ACCESS  read-write
   STATUS      current
   DESCRIPTION
      "Path: vrfRouterLtd.editConf.qualityMonitor.destinations.lossAlarm.alarmUpOff"
   ::= {er1646v2VrfLtdQmDestEntry 100990976}

er1646v2VrfLtdQmDestLossAlarmAlarmDownOn OBJECT-TYPE
   SYNTAX      Integer32
   MAX-ACCESS  read-write
   STATUS      current
   DESCRIPTION
      "Path: vrfRouterLtd.editConf.qualityMonitor.destinations.lossAlarm.alarmDownOn"
   ::= {er1646v2VrfLtdQmDestEntry 101056512}

er1646v2VrfLtdQmDestLossAlarmAlarmDownOff OBJECT-TYPE
   SYNTAX      Integer32
   MAX-ACCESS  read-write
   STATUS      current
   DESCRIPTION
      "Path: vrfRouterLtd.editConf.qualityMonitor.destinations.lossAlarm.alarmDownOff"
   ::= {er1646v2VrfLtdQmDestEntry 101122048}

er1646v2VrfLtdQmDestDelayAlarmSamples OBJECT-TYPE
   SYNTAX      Integer32
   MAX-ACCESS  read-write
   STATUS      current
   DESCRIPTION
      "Path: vrfRouterLtd.editConf.qualityMonitor.destinations.delayAlarm.samples"
   ::= {er1646v2VrfLtdQmDestEntry 117506048}

er1646v2VrfLtdQmDestDelayAlarmDelayAvrgOn OBJECT-TYPE
   SYNTAX      Integer32
   UNITS       "msec"
   MAX-ACCESS  read-write
   STATUS      current
   DESCRIPTION
      "Path: vrfRouterLtd.editConf.qualityMonitor.destinations.delayAlarm.delayAvrgOn

       unit name = msec"
   ::= {er1646v2VrfLtdQmDestEntry 117571584}

er1646v2VrfLtdQmDestDelayAlarmDelayAvrgOff OBJECT-TYPE
   SYNTAX      Integer32
   UNITS       "msec"
   MAX-ACCESS  read-write
   STATUS      current
   DESCRIPTION
      "Path: vrfRouterLtd.editConf.qualityMonitor.destinations.delayAlarm.delayAvrgOff

       unit name = msec"
   ::= {er1646v2VrfLtdQmDestEntry 117637120}

er1646v2VrfLtdQmDestDelayAlarmDelayMaxOn OBJECT-TYPE
   SYNTAX      Integer32
   UNITS       "msec"
   MAX-ACCESS  read-write
   STATUS      current
   DESCRIPTION
      "Path: vrfRouterLtd.editConf.qualityMonitor.destinations.delayAlarm.delayMaxOn

       unit name = msec"
   ::= {er1646v2VrfLtdQmDestEntry 117702656}

er1646v2VrfLtdQmDestDelayAlarmDelayMaxOff OBJECT-TYPE
   SYNTAX      Integer32
   UNITS       "msec"
   MAX-ACCESS  read-write
   STATUS      current
   DESCRIPTION
      "Path: vrfRouterLtd.editConf.qualityMonitor.destinations.delayAlarm.delayMaxOff

       unit name = msec"
   ::= {er1646v2VrfLtdQmDestEntry 117768192}

er1646v2VrfLtdQmDestDelayAlarmDelayMinMaxOn OBJECT-TYPE
   SYNTAX      Integer32
   UNITS       "msec"
   MAX-ACCESS  read-write
   STATUS      current
   DESCRIPTION
      "Path: vrfRouterLtd.editConf.qualityMonitor.destinations.delayAlarm.delayMinMaxOn

       unit name = msec"
   ::= {er1646v2VrfLtdQmDestEntry 118095872}

er1646v2VrfLtdQmDestDelayAlarmDelayMinMaxOff OBJECT-TYPE
   SYNTAX      Integer32
   UNITS       "msec"
   MAX-ACCESS  read-write
   STATUS      current
   DESCRIPTION
      "Path: vrfRouterLtd.editConf.qualityMonitor.destinations.delayAlarm.delayMinMaxOff

       unit name = msec"
   ::= {er1646v2VrfLtdQmDestEntry 118161408}

er1646v2VrfLtdQmDestDelayAlarmDsType OBJECT-TYPE
   SYNTAX      INTEGER
               {
               fd (1),
               fdr (2)
               }
   MAX-ACCESS  read-write
   STATUS      current
   DESCRIPTION
      "Path: vrfRouterLtd.editConf.qualityMonitor.destinations.delayAlarm.delayStat.type

       Possibilities:
               fd   (1)
               fdr   (2)"
   ::= {er1646v2VrfLtdQmDestEntry 119283712}

er1646v2VrfLtdQmDestDelayAlarmDsBinsN OBJECT-TYPE
   SYNTAX      INTEGER
               {
               none (0)
               }
   MAX-ACCESS  read-write
   STATUS      current
   DESCRIPTION
      "Path: vrfRouterLtd.editConf.qualityMonitor.destinations.delayAlarm.delayStat.bins.none

       Possibilities:
               none   (0)"
   ::= {er1646v2VrfLtdQmDestEntry 119292928}

er1646v2VrfLtdQmDestDelayAlarmDsBinsNMn OBJECT-TYPE
   SYNTAX      Integer32
   UNITS       "msec"
   MAX-ACCESS  read-write
   STATUS      current
   DESCRIPTION
      "Path: vrfRouterLtd.editConf.qualityMonitor.destinations.delayAlarm.delayStat.bins.range.min

       unit name = msec"
   ::= {er1646v2VrfLtdQmDestEntry 119294080}

er1646v2VrfLtdQmDestDelayAlarmDsBinsNMx OBJECT-TYPE
   SYNTAX      Integer32
   UNITS       "msec"
   MAX-ACCESS  read-write
   STATUS      current
   DESCRIPTION
      "Path: vrfRouterLtd.editConf.qualityMonitor.destinations.delayAlarm.delayStat.bins.range.max

       unit name = msec"
   ::= {er1646v2VrfLtdQmDestEntry 119294208}

er1646v2VrfLtdQmDestDelayAlarmDsBinsTB1 OBJECT-TYPE
   SYNTAX      Integer32
   UNITS       "msec"
   MAX-ACCESS  read-write
   STATUS      current
   DESCRIPTION
      "Path: vrfRouterLtd.editConf.qualityMonitor.destinations.delayAlarm.delayStat.bins.table.bin1

       unit name = msec"
   ::= {er1646v2VrfLtdQmDestEntry 119295040}

er1646v2VrfLtdQmDestDelayAlarmDsBinsTB2 OBJECT-TYPE
   SYNTAX      Integer32
   UNITS       "msec"
   MAX-ACCESS  read-write
   STATUS      current
   DESCRIPTION
      "Path: vrfRouterLtd.editConf.qualityMonitor.destinations.delayAlarm.delayStat.bins.table.bin2

       unit name = msec"
   ::= {er1646v2VrfLtdQmDestEntry 119295104}

er1646v2VrfLtdQmDestDelayAlarmDsBinsTB3 OBJECT-TYPE
   SYNTAX      Integer32
   UNITS       "msec"
   MAX-ACCESS  read-write
   STATUS      current
   DESCRIPTION
      "Path: vrfRouterLtd.editConf.qualityMonitor.destinations.delayAlarm.delayStat.bins.table.bin3

       unit name = msec"
   ::= {er1646v2VrfLtdQmDestEntry 119295168}

er1646v2VrfLtdQmDestDelayAlarmDsBinsTB4 OBJECT-TYPE
   SYNTAX      Integer32
   UNITS       "msec"
   MAX-ACCESS  read-write
   STATUS      current
   DESCRIPTION
      "Path: vrfRouterLtd.editConf.qualityMonitor.destinations.delayAlarm.delayStat.bins.table.bin4

       unit name = msec"
   ::= {er1646v2VrfLtdQmDestEntry 119295232}

er1646v2VrfLtdQmDestDelayAlarmDsBinsTB5 OBJECT-TYPE
   SYNTAX      Integer32
   UNITS       "msec"
   MAX-ACCESS  read-write
   STATUS      current
   DESCRIPTION
      "Path: vrfRouterLtd.editConf.qualityMonitor.destinations.delayAlarm.delayStat.bins.table.bin5

       unit name = msec"
   ::= {er1646v2VrfLtdQmDestEntry 119295296}

er1646v2VrfLtdQmDestDelayAlarmDsBinsTB6 OBJECT-TYPE
   SYNTAX      Integer32
   UNITS       "msec"
   MAX-ACCESS  read-write
   STATUS      current
   DESCRIPTION
      "Path: vrfRouterLtd.editConf.qualityMonitor.destinations.delayAlarm.delayStat.bins.table.bin6

       unit name = msec"
   ::= {er1646v2VrfLtdQmDestEntry 119295360}

er1646v2VrfLtdQmDestDelayAlarmDsBinsTB7 OBJECT-TYPE
   SYNTAX      Integer32
   UNITS       "msec"
   MAX-ACCESS  read-write
   STATUS      current
   DESCRIPTION
      "Path: vrfRouterLtd.editConf.qualityMonitor.destinations.delayAlarm.delayStat.bins.table.bin7

       unit name = msec"
   ::= {er1646v2VrfLtdQmDestEntry 119295424}

er1646v2VrfLtdQmDestDelayAlarmDsBinsTB8 OBJECT-TYPE
   SYNTAX      Integer32
   UNITS       "msec"
   MAX-ACCESS  read-write
   STATUS      current
   DESCRIPTION
      "Path: vrfRouterLtd.editConf.qualityMonitor.destinations.delayAlarm.delayStat.bins.table.bin8

       unit name = msec"
   ::= {er1646v2VrfLtdQmDestEntry 119295488}

er1646v2VrfLtdQmDestDelayAlarmDsBinsTMx OBJECT-TYPE
   SYNTAX      Integer32
   UNITS       "msec"
   MAX-ACCESS  read-write
   STATUS      current
   DESCRIPTION
      "Path: vrfRouterLtd.editConf.qualityMonitor.destinations.delayAlarm.delayStat.bins.table.max

       unit name = msec"
   ::= {er1646v2VrfLtdQmDestEntry 119295552}

er1646v2VrfLtdQmDestDelayAlarmJitterAvrgOn OBJECT-TYPE
   SYNTAX      Integer32
   UNITS       "msec"
   MAX-ACCESS  read-write
   STATUS      current
   DESCRIPTION
      "Path: vrfRouterLtd.editConf.qualityMonitor.destinations.delayAlarm.jitterAvrgOn

       unit name = msec"
   ::= {er1646v2VrfLtdQmDestEntry 117833728}

er1646v2VrfLtdQmDestDelayAlarmJitterAvrgOff OBJECT-TYPE
   SYNTAX      Integer32
   UNITS       "msec"
   MAX-ACCESS  read-write
   STATUS      current
   DESCRIPTION
      "Path: vrfRouterLtd.editConf.qualityMonitor.destinations.delayAlarm.jitterAvrgOff

       unit name = msec"
   ::= {er1646v2VrfLtdQmDestEntry 117899264}

er1646v2VrfLtdQmDestDelayAlarmJitterMaxOn OBJECT-TYPE
   SYNTAX      Integer32
   UNITS       "msec"
   MAX-ACCESS  read-write
   STATUS      current
   DESCRIPTION
      "Path: vrfRouterLtd.editConf.qualityMonitor.destinations.delayAlarm.jitterMaxOn

       unit name = msec"
   ::= {er1646v2VrfLtdQmDestEntry 117964800}

er1646v2VrfLtdQmDestDelayAlarmJitterMaxOff OBJECT-TYPE
   SYNTAX      Integer32
   UNITS       "msec"
   MAX-ACCESS  read-write
   STATUS      current
   DESCRIPTION
      "Path: vrfRouterLtd.editConf.qualityMonitor.destinations.delayAlarm.jitterMaxOff

       unit name = msec"
   ::= {er1646v2VrfLtdQmDestEntry 118030336}

er1646v2VrfLtdQmDestDelayAlarmJsN OBJECT-TYPE
   SYNTAX      INTEGER
               {
               none (0)
               }
   MAX-ACCESS  read-write
   STATUS      current
   DESCRIPTION
      "Path: vrfRouterLtd.editConf.qualityMonitor.destinations.delayAlarm.jitterStat.none

       Possibilities:
               none   (0)"
   ::= {er1646v2VrfLtdQmDestEntry 119676928}

er1646v2VrfLtdQmDestDelayAlarmJsNMn OBJECT-TYPE
   SYNTAX      Integer32
   UNITS       "msec"
   MAX-ACCESS  read-write
   STATUS      current
   DESCRIPTION
      "Path: vrfRouterLtd.editConf.qualityMonitor.destinations.delayAlarm.jitterStat.range.min

       unit name = msec"
   ::= {er1646v2VrfLtdQmDestEntry 119686144}

er1646v2VrfLtdQmDestDelayAlarmJsNMx OBJECT-TYPE
   SYNTAX      Integer32
   UNITS       "msec"
   MAX-ACCESS  read-write
   STATUS      current
   DESCRIPTION
      "Path: vrfRouterLtd.editConf.qualityMonitor.destinations.delayAlarm.jitterStat.range.max

       unit name = msec"
   ::= {er1646v2VrfLtdQmDestEntry 119687168}

er1646v2VrfLtdQmDestDelayAlarmJsTB1 OBJECT-TYPE
   SYNTAX      Integer32
   UNITS       "msec"
   MAX-ACCESS  read-write
   STATUS      current
   DESCRIPTION
      "Path: vrfRouterLtd.editConf.qualityMonitor.destinations.delayAlarm.jitterStat.table.bin1

       unit name = msec"
   ::= {er1646v2VrfLtdQmDestEntry 119693824}

er1646v2VrfLtdQmDestDelayAlarmJsTB2 OBJECT-TYPE
   SYNTAX      Integer32
   UNITS       "msec"
   MAX-ACCESS  read-write
   STATUS      current
   DESCRIPTION
      "Path: vrfRouterLtd.editConf.qualityMonitor.destinations.delayAlarm.jitterStat.table.bin2

       unit name = msec"
   ::= {er1646v2VrfLtdQmDestEntry 119694336}

er1646v2VrfLtdQmDestDelayAlarmJsTB3 OBJECT-TYPE
   SYNTAX      Integer32
   UNITS       "msec"
   MAX-ACCESS  read-write
   STATUS      current
   DESCRIPTION
      "Path: vrfRouterLtd.editConf.qualityMonitor.destinations.delayAlarm.jitterStat.table.bin3

       unit name = msec"
   ::= {er1646v2VrfLtdQmDestEntry 119694848}

er1646v2VrfLtdQmDestDelayAlarmJsTB4 OBJECT-TYPE
   SYNTAX      Integer32
   UNITS       "msec"
   MAX-ACCESS  read-write
   STATUS      current
   DESCRIPTION
      "Path: vrfRouterLtd.editConf.qualityMonitor.destinations.delayAlarm.jitterStat.table.bin4

       unit name = msec"
   ::= {er1646v2VrfLtdQmDestEntry 119695360}

er1646v2VrfLtdQmDestDelayAlarmJsTB5 OBJECT-TYPE
   SYNTAX      Integer32
   UNITS       "msec"
   MAX-ACCESS  read-write
   STATUS      current
   DESCRIPTION
      "Path: vrfRouterLtd.editConf.qualityMonitor.destinations.delayAlarm.jitterStat.table.bin5

       unit name = msec"
   ::= {er1646v2VrfLtdQmDestEntry 119695872}

er1646v2VrfLtdQmDestDelayAlarmJsTB6 OBJECT-TYPE
   SYNTAX      Integer32
   UNITS       "msec"
   MAX-ACCESS  read-write
   STATUS      current
   DESCRIPTION
      "Path: vrfRouterLtd.editConf.qualityMonitor.destinations.delayAlarm.jitterStat.table.bin6

       unit name = msec"
   ::= {er1646v2VrfLtdQmDestEntry 119696384}

er1646v2VrfLtdQmDestDelayAlarmJsTB7 OBJECT-TYPE
   SYNTAX      Integer32
   UNITS       "msec"
   MAX-ACCESS  read-write
   STATUS      current
   DESCRIPTION
      "Path: vrfRouterLtd.editConf.qualityMonitor.destinations.delayAlarm.jitterStat.table.bin7

       unit name = msec"
   ::= {er1646v2VrfLtdQmDestEntry 119696896}

er1646v2VrfLtdQmDestDelayAlarmJsTB8 OBJECT-TYPE
   SYNTAX      Integer32
   UNITS       "msec"
   MAX-ACCESS  read-write
   STATUS      current
   DESCRIPTION
      "Path: vrfRouterLtd.editConf.qualityMonitor.destinations.delayAlarm.jitterStat.table.bin8

       unit name = msec"
   ::= {er1646v2VrfLtdQmDestEntry 119697408}

er1646v2VrfLtdQmDestDelayAlarmJsTMx OBJECT-TYPE
   SYNTAX      Integer32
   UNITS       "msec"
   MAX-ACCESS  read-write
   STATUS      current
   DESCRIPTION
      "Path: vrfRouterLtd.editConf.qualityMonitor.destinations.delayAlarm.jitterStat.table.max

       unit name = msec"
   ::= {er1646v2VrfLtdQmDestEntry 119697920}

er1646v2VrfLtdQmDestDelayAlarmJitterUpAvrgOn OBJECT-TYPE
   SYNTAX      Integer32
   UNITS       "msec"
   MAX-ACCESS  read-write
   STATUS      current
   DESCRIPTION
      "Path: vrfRouterLtd.editConf.qualityMonitor.destinations.delayAlarm.jitterUpAvrgOn

       unit name = msec"
   ::= {er1646v2VrfLtdQmDestEntry 118226944}

er1646v2VrfLtdQmDestDelayAlarmJitterUpAvrgOff OBJECT-TYPE
   SYNTAX      Integer32
   UNITS       "msec"
   MAX-ACCESS  read-write
   STATUS      current
   DESCRIPTION
      "Path: vrfRouterLtd.editConf.qualityMonitor.destinations.delayAlarm.jitterUpAvrgOff

       unit name = msec"
   ::= {er1646v2VrfLtdQmDestEntry 118292480}

er1646v2VrfLtdQmDestDelayAlarmJitterUpMaxOn OBJECT-TYPE
   SYNTAX      Integer32
   UNITS       "msec"
   MAX-ACCESS  read-write
   STATUS      current
   DESCRIPTION
      "Path: vrfRouterLtd.editConf.qualityMonitor.destinations.delayAlarm.jitterUpMaxOn

       unit name = msec"
   ::= {er1646v2VrfLtdQmDestEntry 118358016}

er1646v2VrfLtdQmDestDelayAlarmJitterUpMaxOff OBJECT-TYPE
   SYNTAX      Integer32
   UNITS       "msec"
   MAX-ACCESS  read-write
   STATUS      current
   DESCRIPTION
      "Path: vrfRouterLtd.editConf.qualityMonitor.destinations.delayAlarm.jitterUpMaxOff

       unit name = msec"
   ::= {er1646v2VrfLtdQmDestEntry 118423552}

er1646v2VrfLtdQmDestDelayAlarmJupsN OBJECT-TYPE
   SYNTAX      INTEGER
               {
               none (0)
               }
   MAX-ACCESS  read-write
   STATUS      current
   DESCRIPTION
      "Path: vrfRouterLtd.editConf.qualityMonitor.destinations.delayAlarm.jitterUpStat.none

       Possibilities:
               none   (0)"
   ::= {er1646v2VrfLtdQmDestEntry 119808000}

er1646v2VrfLtdQmDestDelayAlarmJupsNMn OBJECT-TYPE
   SYNTAX      Integer32
   UNITS       "msec"
   MAX-ACCESS  read-write
   STATUS      current
   DESCRIPTION
      "Path: vrfRouterLtd.editConf.qualityMonitor.destinations.delayAlarm.jitterUpStat.range.min

       unit name = msec"
   ::= {er1646v2VrfLtdQmDestEntry 119817216}

er1646v2VrfLtdQmDestDelayAlarmJupsNMx OBJECT-TYPE
   SYNTAX      Integer32
   UNITS       "msec"
   MAX-ACCESS  read-write
   STATUS      current
   DESCRIPTION
      "Path: vrfRouterLtd.editConf.qualityMonitor.destinations.delayAlarm.jitterUpStat.range.max

       unit name = msec"
   ::= {er1646v2VrfLtdQmDestEntry 119818240}

er1646v2VrfLtdQmDestDelayAlarmJupsTB1 OBJECT-TYPE
   SYNTAX      Integer32
   UNITS       "msec"
   MAX-ACCESS  read-write
   STATUS      current
   DESCRIPTION
      "Path: vrfRouterLtd.editConf.qualityMonitor.destinations.delayAlarm.jitterUpStat.table.bin1

       unit name = msec"
   ::= {er1646v2VrfLtdQmDestEntry 119824896}

er1646v2VrfLtdQmDestDelayAlarmJupsTB2 OBJECT-TYPE
   SYNTAX      Integer32
   UNITS       "msec"
   MAX-ACCESS  read-write
   STATUS      current
   DESCRIPTION
      "Path: vrfRouterLtd.editConf.qualityMonitor.destinations.delayAlarm.jitterUpStat.table.bin2

       unit name = msec"
   ::= {er1646v2VrfLtdQmDestEntry 119825408}

er1646v2VrfLtdQmDestDelayAlarmJupsTB3 OBJECT-TYPE
   SYNTAX      Integer32
   UNITS       "msec"
   MAX-ACCESS  read-write
   STATUS      current
   DESCRIPTION
      "Path: vrfRouterLtd.editConf.qualityMonitor.destinations.delayAlarm.jitterUpStat.table.bin3

       unit name = msec"
   ::= {er1646v2VrfLtdQmDestEntry 119825920}

er1646v2VrfLtdQmDestDelayAlarmJupsTB4 OBJECT-TYPE
   SYNTAX      Integer32
   UNITS       "msec"
   MAX-ACCESS  read-write
   STATUS      current
   DESCRIPTION
      "Path: vrfRouterLtd.editConf.qualityMonitor.destinations.delayAlarm.jitterUpStat.table.bin4

       unit name = msec"
   ::= {er1646v2VrfLtdQmDestEntry 119826432}

er1646v2VrfLtdQmDestDelayAlarmJupsTB5 OBJECT-TYPE
   SYNTAX      Integer32
   UNITS       "msec"
   MAX-ACCESS  read-write
   STATUS      current
   DESCRIPTION
      "Path: vrfRouterLtd.editConf.qualityMonitor.destinations.delayAlarm.jitterUpStat.table.bin5

       unit name = msec"
   ::= {er1646v2VrfLtdQmDestEntry 119826944}

er1646v2VrfLtdQmDestDelayAlarmJupsTB6 OBJECT-TYPE
   SYNTAX      Integer32
   UNITS       "msec"
   MAX-ACCESS  read-write
   STATUS      current
   DESCRIPTION
      "Path: vrfRouterLtd.editConf.qualityMonitor.destinations.delayAlarm.jitterUpStat.table.bin6

       unit name = msec"
   ::= {er1646v2VrfLtdQmDestEntry 119827456}

er1646v2VrfLtdQmDestDelayAlarmJupsTB7 OBJECT-TYPE
   SYNTAX      Integer32
   UNITS       "msec"
   MAX-ACCESS  read-write
   STATUS      current
   DESCRIPTION
      "Path: vrfRouterLtd.editConf.qualityMonitor.destinations.delayAlarm.jitterUpStat.table.bin7

       unit name = msec"
   ::= {er1646v2VrfLtdQmDestEntry 119827968}

er1646v2VrfLtdQmDestDelayAlarmJupsTB8 OBJECT-TYPE
   SYNTAX      Integer32
   UNITS       "msec"
   MAX-ACCESS  read-write
   STATUS      current
   DESCRIPTION
      "Path: vrfRouterLtd.editConf.qualityMonitor.destinations.delayAlarm.jitterUpStat.table.bin8

       unit name = msec"
   ::= {er1646v2VrfLtdQmDestEntry 119828480}

er1646v2VrfLtdQmDestDelayAlarmJupsTMx OBJECT-TYPE
   SYNTAX      Integer32
   UNITS       "msec"
   MAX-ACCESS  read-write
   STATUS      current
   DESCRIPTION
      "Path: vrfRouterLtd.editConf.qualityMonitor.destinations.delayAlarm.jitterUpStat.table.max

       unit name = msec"
   ::= {er1646v2VrfLtdQmDestEntry 119828992}

er1646v2VrfLtdQmDestDelayAlarmJitterDownAvrgOn OBJECT-TYPE
   SYNTAX      Integer32
   UNITS       "msec"
   MAX-ACCESS  read-write
   STATUS      current
   DESCRIPTION
      "Path: vrfRouterLtd.editConf.qualityMonitor.destinations.delayAlarm.jitterDownAvrgOn

       unit name = msec"
   ::= {er1646v2VrfLtdQmDestEntry 118489088}

er1646v2VrfLtdQmDestDelayAlarmJitterDownAvrgOff OBJECT-TYPE
   SYNTAX      Integer32
   UNITS       "msec"
   MAX-ACCESS  read-write
   STATUS      current
   DESCRIPTION
      "Path: vrfRouterLtd.editConf.qualityMonitor.destinations.delayAlarm.jitterDownAvrgOff

       unit name = msec"
   ::= {er1646v2VrfLtdQmDestEntry 118554624}

er1646v2VrfLtdQmDestDelayAlarmJitterDownMaxOn OBJECT-TYPE
   SYNTAX      Integer32
   UNITS       "msec"
   MAX-ACCESS  read-write
   STATUS      current
   DESCRIPTION
      "Path: vrfRouterLtd.editConf.qualityMonitor.destinations.delayAlarm.jitterDownMaxOn

       unit name = msec"
   ::= {er1646v2VrfLtdQmDestEntry 118620160}

er1646v2VrfLtdQmDestDelayAlarmJitterDownMaxOff OBJECT-TYPE
   SYNTAX      Integer32
   UNITS       "msec"
   MAX-ACCESS  read-write
   STATUS      current
   DESCRIPTION
      "Path: vrfRouterLtd.editConf.qualityMonitor.destinations.delayAlarm.jitterDownMaxOff

       unit name = msec"
   ::= {er1646v2VrfLtdQmDestEntry 118685696}

er1646v2VrfLtdQmDestDelayAlarmJdownsN OBJECT-TYPE
   SYNTAX      INTEGER
               {
               none (0)
               }
   MAX-ACCESS  read-write
   STATUS      current
   DESCRIPTION
      "Path: vrfRouterLtd.editConf.qualityMonitor.destinations.delayAlarm.jitterDownStat.none

       Possibilities:
               none   (0)"
   ::= {er1646v2VrfLtdQmDestEntry 119939072}

er1646v2VrfLtdQmDestDelayAlarmJdownsNMn OBJECT-TYPE
   SYNTAX      Integer32
   UNITS       "msec"
   MAX-ACCESS  read-write
   STATUS      current
   DESCRIPTION
      "Path: vrfRouterLtd.editConf.qualityMonitor.destinations.delayAlarm.jitterDownStat.range.min

       unit name = msec"
   ::= {er1646v2VrfLtdQmDestEntry 119948288}

er1646v2VrfLtdQmDestDelayAlarmJdownsNMx OBJECT-TYPE
   SYNTAX      Integer32
   UNITS       "msec"
   MAX-ACCESS  read-write
   STATUS      current
   DESCRIPTION
      "Path: vrfRouterLtd.editConf.qualityMonitor.destinations.delayAlarm.jitterDownStat.range.max

       unit name = msec"
   ::= {er1646v2VrfLtdQmDestEntry 119949312}

er1646v2VrfLtdQmDestDelayAlarmJdownsTB1 OBJECT-TYPE
   SYNTAX      Integer32
   UNITS       "msec"
   MAX-ACCESS  read-write
   STATUS      current
   DESCRIPTION
      "Path: vrfRouterLtd.editConf.qualityMonitor.destinations.delayAlarm.jitterDownStat.table.bin1

       unit name = msec"
   ::= {er1646v2VrfLtdQmDestEntry 119955968}

er1646v2VrfLtdQmDestDelayAlarmJdownsTB2 OBJECT-TYPE
   SYNTAX      Integer32
   UNITS       "msec"
   MAX-ACCESS  read-write
   STATUS      current
   DESCRIPTION
      "Path: vrfRouterLtd.editConf.qualityMonitor.destinations.delayAlarm.jitterDownStat.table.bin2

       unit name = msec"
   ::= {er1646v2VrfLtdQmDestEntry 119956480}

er1646v2VrfLtdQmDestDelayAlarmJdownsTB3 OBJECT-TYPE
   SYNTAX      Integer32
   UNITS       "msec"
   MAX-ACCESS  read-write
   STATUS      current
   DESCRIPTION
      "Path: vrfRouterLtd.editConf.qualityMonitor.destinations.delayAlarm.jitterDownStat.table.bin3

       unit name = msec"
   ::= {er1646v2VrfLtdQmDestEntry 119956992}

er1646v2VrfLtdQmDestDelayAlarmJdownsTB4 OBJECT-TYPE
   SYNTAX      Integer32
   UNITS       "msec"
   MAX-ACCESS  read-write
   STATUS      current
   DESCRIPTION
      "Path: vrfRouterLtd.editConf.qualityMonitor.destinations.delayAlarm.jitterDownStat.table.bin4

       unit name = msec"
   ::= {er1646v2VrfLtdQmDestEntry 119957504}

er1646v2VrfLtdQmDestDelayAlarmJdownsTB5 OBJECT-TYPE
   SYNTAX      Integer32
   UNITS       "msec"
   MAX-ACCESS  read-write
   STATUS      current
   DESCRIPTION
      "Path: vrfRouterLtd.editConf.qualityMonitor.destinations.delayAlarm.jitterDownStat.table.bin5

       unit name = msec"
   ::= {er1646v2VrfLtdQmDestEntry 119958016}

er1646v2VrfLtdQmDestDelayAlarmJdownsTB6 OBJECT-TYPE
   SYNTAX      Integer32
   UNITS       "msec"
   MAX-ACCESS  read-write
   STATUS      current
   DESCRIPTION
      "Path: vrfRouterLtd.editConf.qualityMonitor.destinations.delayAlarm.jitterDownStat.table.bin6

       unit name = msec"
   ::= {er1646v2VrfLtdQmDestEntry 119958528}

er1646v2VrfLtdQmDestDelayAlarmJdownsTB7 OBJECT-TYPE
   SYNTAX      Integer32
   UNITS       "msec"
   MAX-ACCESS  read-write
   STATUS      current
   DESCRIPTION
      "Path: vrfRouterLtd.editConf.qualityMonitor.destinations.delayAlarm.jitterDownStat.table.bin7

       unit name = msec"
   ::= {er1646v2VrfLtdQmDestEntry 119959040}

er1646v2VrfLtdQmDestDelayAlarmJdownsTB8 OBJECT-TYPE
   SYNTAX      Integer32
   UNITS       "msec"
   MAX-ACCESS  read-write
   STATUS      current
   DESCRIPTION
      "Path: vrfRouterLtd.editConf.qualityMonitor.destinations.delayAlarm.jitterDownStat.table.bin8

       unit name = msec"
   ::= {er1646v2VrfLtdQmDestEntry 119959552}

er1646v2VrfLtdQmDestDelayAlarmJdownsTMx OBJECT-TYPE
   SYNTAX      Integer32
   UNITS       "msec"
   MAX-ACCESS  read-write
   STATUS      current
   DESCRIPTION
      "Path: vrfRouterLtd.editConf.qualityMonitor.destinations.delayAlarm.jitterDownStat.table.max

       unit name = msec"
   ::= {er1646v2VrfLtdQmDestEntry 119960064}

er1646v2VrfLtdQmDestDelayAlarmDelayUpAvrgOn OBJECT-TYPE
   SYNTAX      Integer32
   UNITS       "msec"
   MAX-ACCESS  read-write
   STATUS      current
   DESCRIPTION
      "Path: vrfRouterLtd.editConf.qualityMonitor.destinations.delayAlarm.delayUpAvrgOn

       unit name = msec"
   ::= {er1646v2VrfLtdQmDestEntry 118751232}

er1646v2VrfLtdQmDestDelayAlarmDelayUpAvrgOff OBJECT-TYPE
   SYNTAX      Integer32
   UNITS       "msec"
   MAX-ACCESS  read-write
   STATUS      current
   DESCRIPTION
      "Path: vrfRouterLtd.editConf.qualityMonitor.destinations.delayAlarm.delayUpAvrgOff

       unit name = msec"
   ::= {er1646v2VrfLtdQmDestEntry 118816768}

er1646v2VrfLtdQmDestDelayAlarmDelayUpMaxOn OBJECT-TYPE
   SYNTAX      Integer32
   UNITS       "msec"
   MAX-ACCESS  read-write
   STATUS      current
   DESCRIPTION
      "Path: vrfRouterLtd.editConf.qualityMonitor.destinations.delayAlarm.delayUpMaxOn

       unit name = msec"
   ::= {er1646v2VrfLtdQmDestEntry 118882304}

er1646v2VrfLtdQmDestDelayAlarmDelayUpMaxOff OBJECT-TYPE
   SYNTAX      Integer32
   UNITS       "msec"
   MAX-ACCESS  read-write
   STATUS      current
   DESCRIPTION
      "Path: vrfRouterLtd.editConf.qualityMonitor.destinations.delayAlarm.delayUpMaxOff

       unit name = msec"
   ::= {er1646v2VrfLtdQmDestEntry 118947840}

er1646v2VrfLtdQmDestDelayAlarmDupsType OBJECT-TYPE
   SYNTAX      INTEGER
               {
               fd (1),
               fdr (2)
               }
   MAX-ACCESS  read-write
   STATUS      current
   DESCRIPTION
      "Path: vrfRouterLtd.editConf.qualityMonitor.destinations.delayAlarm.delayUpStat.type

       Possibilities:
               fd   (1)
               fdr   (2)"
   ::= {er1646v2VrfLtdQmDestEntry 119414784}

er1646v2VrfLtdQmDestDelayAlarmDupsBinsN OBJECT-TYPE
   SYNTAX      INTEGER
               {
               none (0)
               }
   MAX-ACCESS  read-write
   STATUS      current
   DESCRIPTION
      "Path: vrfRouterLtd.editConf.qualityMonitor.destinations.delayAlarm.delayUpStat.bins.none

       Possibilities:
               none   (0)"
   ::= {er1646v2VrfLtdQmDestEntry 119424000}

er1646v2VrfLtdQmDestDelayAlarmDupsBinsNMn OBJECT-TYPE
   SYNTAX      Integer32
   UNITS       "msec"
   MAX-ACCESS  read-write
   STATUS      current
   DESCRIPTION
      "Path: vrfRouterLtd.editConf.qualityMonitor.destinations.delayAlarm.delayUpStat.bins.range.min

       unit name = msec"
   ::= {er1646v2VrfLtdQmDestEntry 119425152}

er1646v2VrfLtdQmDestDelayAlarmDupsBinsNMx OBJECT-TYPE
   SYNTAX      Integer32
   UNITS       "msec"
   MAX-ACCESS  read-write
   STATUS      current
   DESCRIPTION
      "Path: vrfRouterLtd.editConf.qualityMonitor.destinations.delayAlarm.delayUpStat.bins.range.max

       unit name = msec"
   ::= {er1646v2VrfLtdQmDestEntry 119425280}

er1646v2VrfLtdQmDestDelayAlarmDupsBinsTB1 OBJECT-TYPE
   SYNTAX      Integer32
   UNITS       "msec"
   MAX-ACCESS  read-write
   STATUS      current
   DESCRIPTION
      "Path: vrfRouterLtd.editConf.qualityMonitor.destinations.delayAlarm.delayUpStat.bins.table.bin1

       unit name = msec"
   ::= {er1646v2VrfLtdQmDestEntry 119426112}

er1646v2VrfLtdQmDestDelayAlarmDupsBinsTB2 OBJECT-TYPE
   SYNTAX      Integer32
   UNITS       "msec"
   MAX-ACCESS  read-write
   STATUS      current
   DESCRIPTION
      "Path: vrfRouterLtd.editConf.qualityMonitor.destinations.delayAlarm.delayUpStat.bins.table.bin2

       unit name = msec"
   ::= {er1646v2VrfLtdQmDestEntry 119426176}

er1646v2VrfLtdQmDestDelayAlarmDupsBinsTB3 OBJECT-TYPE
   SYNTAX      Integer32
   UNITS       "msec"
   MAX-ACCESS  read-write
   STATUS      current
   DESCRIPTION
      "Path: vrfRouterLtd.editConf.qualityMonitor.destinations.delayAlarm.delayUpStat.bins.table.bin3

       unit name = msec"
   ::= {er1646v2VrfLtdQmDestEntry 119426240}

er1646v2VrfLtdQmDestDelayAlarmDupsBinsTB4 OBJECT-TYPE
   SYNTAX      Integer32
   UNITS       "msec"
   MAX-ACCESS  read-write
   STATUS      current
   DESCRIPTION
      "Path: vrfRouterLtd.editConf.qualityMonitor.destinations.delayAlarm.delayUpStat.bins.table.bin4

       unit name = msec"
   ::= {er1646v2VrfLtdQmDestEntry 119426304}

er1646v2VrfLtdQmDestDelayAlarmDupsBinsTB5 OBJECT-TYPE
   SYNTAX      Integer32
   UNITS       "msec"
   MAX-ACCESS  read-write
   STATUS      current
   DESCRIPTION
      "Path: vrfRouterLtd.editConf.qualityMonitor.destinations.delayAlarm.delayUpStat.bins.table.bin5

       unit name = msec"
   ::= {er1646v2VrfLtdQmDestEntry 119426368}

er1646v2VrfLtdQmDestDelayAlarmDupsBinsTB6 OBJECT-TYPE
   SYNTAX      Integer32
   UNITS       "msec"
   MAX-ACCESS  read-write
   STATUS      current
   DESCRIPTION
      "Path: vrfRouterLtd.editConf.qualityMonitor.destinations.delayAlarm.delayUpStat.bins.table.bin6

       unit name = msec"
   ::= {er1646v2VrfLtdQmDestEntry 119426432}

er1646v2VrfLtdQmDestDelayAlarmDupsBinsTB7 OBJECT-TYPE
   SYNTAX      Integer32
   UNITS       "msec"
   MAX-ACCESS  read-write
   STATUS      current
   DESCRIPTION
      "Path: vrfRouterLtd.editConf.qualityMonitor.destinations.delayAlarm.delayUpStat.bins.table.bin7

       unit name = msec"
   ::= {er1646v2VrfLtdQmDestEntry 119426496}

er1646v2VrfLtdQmDestDelayAlarmDupsBinsTB8 OBJECT-TYPE
   SYNTAX      Integer32
   UNITS       "msec"
   MAX-ACCESS  read-write
   STATUS      current
   DESCRIPTION
      "Path: vrfRouterLtd.editConf.qualityMonitor.destinations.delayAlarm.delayUpStat.bins.table.bin8

       unit name = msec"
   ::= {er1646v2VrfLtdQmDestEntry 119426560}

er1646v2VrfLtdQmDestDelayAlarmDupsBinsTMx OBJECT-TYPE
   SYNTAX      Integer32
   UNITS       "msec"
   MAX-ACCESS  read-write
   STATUS      current
   DESCRIPTION
      "Path: vrfRouterLtd.editConf.qualityMonitor.destinations.delayAlarm.delayUpStat.bins.table.max

       unit name = msec"
   ::= {er1646v2VrfLtdQmDestEntry 119426624}

er1646v2VrfLtdQmDestDelayAlarmDelayDownAvrgOn OBJECT-TYPE
   SYNTAX      Integer32
   UNITS       "msec"
   MAX-ACCESS  read-write
   STATUS      current
   DESCRIPTION
      "Path: vrfRouterLtd.editConf.qualityMonitor.destinations.delayAlarm.delayDownAvrgOn

       unit name = msec"
   ::= {er1646v2VrfLtdQmDestEntry 119013376}

er1646v2VrfLtdQmDestDelayAlarmDelayDownAvrgOff OBJECT-TYPE
   SYNTAX      Integer32
   UNITS       "msec"
   MAX-ACCESS  read-write
   STATUS      current
   DESCRIPTION
      "Path: vrfRouterLtd.editConf.qualityMonitor.destinations.delayAlarm.delayDownAvrgOff

       unit name = msec"
   ::= {er1646v2VrfLtdQmDestEntry 119078912}

er1646v2VrfLtdQmDestDelayAlarmDelayDownMaxOn OBJECT-TYPE
   SYNTAX      Integer32
   UNITS       "msec"
   MAX-ACCESS  read-write
   STATUS      current
   DESCRIPTION
      "Path: vrfRouterLtd.editConf.qualityMonitor.destinations.delayAlarm.delayDownMaxOn

       unit name = msec"
   ::= {er1646v2VrfLtdQmDestEntry 119144448}

er1646v2VrfLtdQmDestDelayAlarmDelayDownMaxOff OBJECT-TYPE
   SYNTAX      Integer32
   UNITS       "msec"
   MAX-ACCESS  read-write
   STATUS      current
   DESCRIPTION
      "Path: vrfRouterLtd.editConf.qualityMonitor.destinations.delayAlarm.delayDownMaxOff

       unit name = msec"
   ::= {er1646v2VrfLtdQmDestEntry 119209984}

er1646v2VrfLtdQmDestDelayAlarmDdownsType OBJECT-TYPE
   SYNTAX      INTEGER
               {
               fd (1),
               fdr (2)
               }
   MAX-ACCESS  read-write
   STATUS      current
   DESCRIPTION
      "Path: vrfRouterLtd.editConf.qualityMonitor.destinations.delayAlarm.delayDownStat.type

       Possibilities:
               fd   (1)
               fdr   (2)"
   ::= {er1646v2VrfLtdQmDestEntry 119545856}

er1646v2VrfLtdQmDestDelayAlarmDdownsBinsN OBJECT-TYPE
   SYNTAX      INTEGER
               {
               none (0)
               }
   MAX-ACCESS  read-write
   STATUS      current
   DESCRIPTION
      "Path: vrfRouterLtd.editConf.qualityMonitor.destinations.delayAlarm.delayDownStat.bins.none

       Possibilities:
               none   (0)"
   ::= {er1646v2VrfLtdQmDestEntry 119555072}

er1646v2VrfLtdQmDestDelayAlarmDdownsBinsNMn OBJECT-TYPE
   SYNTAX      Integer32
   UNITS       "msec"
   MAX-ACCESS  read-write
   STATUS      current
   DESCRIPTION
      "Path: vrfRouterLtd.editConf.qualityMonitor.destinations.delayAlarm.delayDownStat.bins.range.min

       unit name = msec"
   ::= {er1646v2VrfLtdQmDestEntry 119556224}

er1646v2VrfLtdQmDestDelayAlarmDdownsBinsNMx OBJECT-TYPE
   SYNTAX      Integer32
   UNITS       "msec"
   MAX-ACCESS  read-write
   STATUS      current
   DESCRIPTION
      "Path: vrfRouterLtd.editConf.qualityMonitor.destinations.delayAlarm.delayDownStat.bins.range.max

       unit name = msec"
   ::= {er1646v2VrfLtdQmDestEntry 119556352}

er1646v2VrfLtdQmDestDelayAlarmDdownsBinsTB1 OBJECT-TYPE
   SYNTAX      Integer32
   UNITS       "msec"
   MAX-ACCESS  read-write
   STATUS      current
   DESCRIPTION
      "Path: vrfRouterLtd.editConf.qualityMonitor.destinations.delayAlarm.delayDownStat.bins.table.bin1

       unit name = msec"
   ::= {er1646v2VrfLtdQmDestEntry 119557184}

er1646v2VrfLtdQmDestDelayAlarmDdownsBinsTB2 OBJECT-TYPE
   SYNTAX      Integer32
   UNITS       "msec"
   MAX-ACCESS  read-write
   STATUS      current
   DESCRIPTION
      "Path: vrfRouterLtd.editConf.qualityMonitor.destinations.delayAlarm.delayDownStat.bins.table.bin2

       unit name = msec"
   ::= {er1646v2VrfLtdQmDestEntry 119557248}

er1646v2VrfLtdQmDestDelayAlarmDdownsBinsTB3 OBJECT-TYPE
   SYNTAX      Integer32
   UNITS       "msec"
   MAX-ACCESS  read-write
   STATUS      current
   DESCRIPTION
      "Path: vrfRouterLtd.editConf.qualityMonitor.destinations.delayAlarm.delayDownStat.bins.table.bin3

       unit name = msec"
   ::= {er1646v2VrfLtdQmDestEntry 119557312}

er1646v2VrfLtdQmDestDelayAlarmDdownsBinsTB4 OBJECT-TYPE
   SYNTAX      Integer32
   UNITS       "msec"
   MAX-ACCESS  read-write
   STATUS      current
   DESCRIPTION
      "Path: vrfRouterLtd.editConf.qualityMonitor.destinations.delayAlarm.delayDownStat.bins.table.bin4

       unit name = msec"
   ::= {er1646v2VrfLtdQmDestEntry 119557376}

er1646v2VrfLtdQmDestDelayAlarmDdownsBinsTB5 OBJECT-TYPE
   SYNTAX      Integer32
   UNITS       "msec"
   MAX-ACCESS  read-write
   STATUS      current
   DESCRIPTION
      "Path: vrfRouterLtd.editConf.qualityMonitor.destinations.delayAlarm.delayDownStat.bins.table.bin5

       unit name = msec"
   ::= {er1646v2VrfLtdQmDestEntry 119557440}

er1646v2VrfLtdQmDestDelayAlarmDdownsBinsTB6 OBJECT-TYPE
   SYNTAX      Integer32
   UNITS       "msec"
   MAX-ACCESS  read-write
   STATUS      current
   DESCRIPTION
      "Path: vrfRouterLtd.editConf.qualityMonitor.destinations.delayAlarm.delayDownStat.bins.table.bin6

       unit name = msec"
   ::= {er1646v2VrfLtdQmDestEntry 119557504}

er1646v2VrfLtdQmDestDelayAlarmDdownsBinsTB7 OBJECT-TYPE
   SYNTAX      Integer32
   UNITS       "msec"
   MAX-ACCESS  read-write
   STATUS      current
   DESCRIPTION
      "Path: vrfRouterLtd.editConf.qualityMonitor.destinations.delayAlarm.delayDownStat.bins.table.bin7

       unit name = msec"
   ::= {er1646v2VrfLtdQmDestEntry 119557568}

er1646v2VrfLtdQmDestDelayAlarmDdownsBinsTB8 OBJECT-TYPE
   SYNTAX      Integer32
   UNITS       "msec"
   MAX-ACCESS  read-write
   STATUS      current
   DESCRIPTION
      "Path: vrfRouterLtd.editConf.qualityMonitor.destinations.delayAlarm.delayDownStat.bins.table.bin8

       unit name = msec"
   ::= {er1646v2VrfLtdQmDestEntry 119557632}

er1646v2VrfLtdQmDestDelayAlarmDdownsBinsTMx OBJECT-TYPE
   SYNTAX      Integer32
   UNITS       "msec"
   MAX-ACCESS  read-write
   STATUS      current
   DESCRIPTION
      "Path: vrfRouterLtd.editConf.qualityMonitor.destinations.delayAlarm.delayDownStat.bins.table.max

       unit name = msec"
   ::= {er1646v2VrfLtdQmDestEntry 119557696}

er1646v2VrfLtdQmDestAlarmMask OBJECT-TYPE
   SYNTAX      Integer32
   MAX-ACCESS  read-write
   STATUS      current
   DESCRIPTION
      "Path: vrfRouterLtd.editConf.qualityMonitor.destinations.alarmMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1646v2VrfLtdQmDestEntry 251658240}

er1646v2VrfLtdQmDestLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: vrfRouterLtd.editConf.qualityMonitor.destinations.logging

       Possibilities:
               disabled   (0)
               3min   (3)
               5min   (5)
               10min   (10)
               15min   (15)
               30min   (30)
               60min   (60)"
   ::= {er1646v2VrfLtdQmDestEntry 201326592}

er1646v2VrfLtdQmDestLoggingDepth OBJECT-TYPE
   SYNTAX      INTEGER
               {
               s2 (2),
               s4 (4),
               s8 (8),
               s16 (16),
               s32 (32),
               s128 (128),
               s512 (512),
               s1024 (1024)
               }
   MAX-ACCESS  read-write
   STATUS      current
   DESCRIPTION
      "Path: vrfRouterLtd.editConf.qualityMonitor.destinations.loggingDepth

       Possibilities:
               2   (2)
               4   (4)
               8   (8)
               16   (16)
               32   (32)
               128   (128)
               512   (512)
               1024   (1024)"
   ::= {er1646v2VrfLtdQmDestEntry 503316480}

er1646v2VrfLtdQmUdpServerPort OBJECT-TYPE
   SYNTAX      SEQUENCE OF Er1646v2VrfLtdQmUdpServerPortEntry
   MAX-ACCESS  not-accessible
   STATUS      current
   DESCRIPTION
      ""
   ::= {er1646v2VrfLtdQm 67108864}

er1646v2VrfLtdQmUdpServerPortEntry OBJECT-TYPE
   SYNTAX      Er1646v2VrfLtdQmUdpServerPortEntry
   MAX-ACCESS  not-accessible
   STATUS      current
   DESCRIPTION
      ""
   INDEX      { er1646v2VrfLtdQmUdpServerPortGlobalIx,
                er1646v2VrfLtdQmUdpServerPortTableIx }
   ::= {er1646v2VrfLtdQmUdpServerPort 1}

Er1646v2VrfLtdQmUdpServerPortEntry ::=
   SEQUENCE
      {
      er1646v2VrfLtdQmUdpServerPortActions
         VariableLengthTableActions,
      er1646v2VrfLtdQmUdpServerPortGlobalIx
         GlobalIndex,
      er1646v2VrfLtdQmUdpServerPortTableIx
         TableIndex,
      er1646v2VrfLtdQmUdpServerPortDestinationPort
         Integer32,
      er1646v2VrfLtdQmUdpServerPortService
         INTEGER,
      er1646v2VrfLtdQmUdpServerPortPriority
         INTEGER,
      er1646v2VrfLtdQmUdpServerPortTos
         INTEGER
      }

er1646v2VrfLtdQmUdpServerPortActions OBJECT-TYPE
   SYNTAX      VariableLengthTableActions
   MAX-ACCESS  read-write
   STATUS      current
   DESCRIPTION
      "By way of this field, some manipulations
       on this table may be performed."
   ::= {er1646v2VrfLtdQmUdpServerPortEntry 2}

er1646v2VrfLtdQmUdpServerPortGlobalIx OBJECT-TYPE
   SYNTAX      GlobalIndex
   MAX-ACCESS  not-accessible
   STATUS      current
   DESCRIPTION
      "The value of the tlsCntTreeGlobalIndex of the MANAGED OBJECT."
   ::= {er1646v2VrfLtdQmUdpServerPortEntry 10}

er1646v2VrfLtdQmUdpServerPortTableIx OBJECT-TYPE
   SYNTAX      TableIndex
   MAX-ACCESS  not-accessible
   STATUS      current
   DESCRIPTION
      ""
   ::= {er1646v2VrfLtdQmUdpServerPortEntry 11}

er1646v2VrfLtdQmUdpServerPortDestinationPort OBJECT-TYPE
   SYNTAX      Integer32
   MAX-ACCESS  read-write
   STATUS      current
   DESCRIPTION
      "Path: vrfRouterLtd.editConf.qualityMonitor.udpServerPort.destinationPort"
   ::= {er1646v2VrfLtdQmUdpServerPortEntry 16777216}

er1646v2VrfLtdQmUdpServerPortService OBJECT-TYPE
   SYNTAX      INTEGER
               {
               proprietary (1),
               twampLight (2)
               }
   MAX-ACCESS  read-write
   STATUS      current
   DESCRIPTION
      "Path: vrfRouterLtd.editConf.qualityMonitor.udpServerPort.service

       Possibilities:
               proprietary   (1)
               twampLight   (2)"
   ::= {er1646v2VrfLtdQmUdpServerPortEntry 234881024}

er1646v2VrfLtdQmUdpServerPortPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: vrfRouterLtd.editConf.qualityMonitor.udpServerPort.priority

       Possibilities:
               queue1   (0)
               queue2   (1)
               queue3   (2)
               queue4   (3)
               queue5   (4)
               lowDelayQueue   (5)
               lowDelay2Queue   (6)
               systemQueue   (7)"
   ::= {er1646v2VrfLtdQmUdpServerPortEntry 218103808}

er1646v2VrfLtdQmUdpServerPortTos OBJECT-TYPE
   SYNTAX      INTEGER
               {
               keepTos (-1),
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfRouterLtd.editConf.qualityMonitor.udpServerPort.tos

       Possibilities:
               keepTos   (-1)
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VrfLtdQmUdpServerPortEntry 167772160}


er1646v2VrfLtdForceMtu OBJECT IDENTIFIER ::= {er1646v2VrfLtd 171}

er1646v2VrfLtdForceMtuTable OBJECT-TYPE
   SYNTAX      SEQUENCE OF Er1646v2VrfLtdForceMtuEntry
   MAX-ACCESS  not-accessible
   STATUS      current
   DESCRIPTION
      "force the configured mtu"
   ::= {er1646v2VrfLtdForceMtu 1}

er1646v2VrfLtdForceMtuEntry OBJECT-TYPE
   SYNTAX      Er1646v2VrfLtdForceMtuEntry
   MAX-ACCESS  not-accessible
   STATUS      current
   DESCRIPTION
      ""
   INDEX      { er1646v2VrfLtdForceMtuGlobalIx }
   ::= {er1646v2VrfLtdForceMtuTable 1}

Er1646v2VrfLtdForceMtuEntry ::=
   SEQUENCE
      {
      er1646v2VrfLtdForceMtuGlobalIx
         GlobalIndex,
      er1646v2VrfLtdForceMtuValue
         INTEGER
      }

er1646v2VrfLtdForceMtuGlobalIx OBJECT-TYPE
   SYNTAX      GlobalIndex
   MAX-ACCESS  not-accessible
   STATUS      current
   DESCRIPTION
      "The value of the tlsCntTreeGlobalIndex of the MANAGED OBJECT."
   ::= {er1646v2VrfLtdForceMtuEntry 10}

er1646v2VrfLtdForceMtuValue OBJECT-TYPE
   SYNTAX      INTEGER
               {
               disabled (0),
               enabled (1)
               }
   MAX-ACCESS  read-write
   STATUS      current
   DESCRIPTION
      "Path: vrfRouterLtd.editConf.forceMtu

       Possibilities:
               disabled   (0)
               enabled   (1)"
   ::= {er1646v2VrfLtdForceMtuEntry 2147483648}


er1646v2VrfLtdAlarmMask OBJECT IDENTIFIER ::= {er1646v2VrfLtd 135}

er1646v2VrfLtdAlarmMaskTable OBJECT-TYPE
   SYNTAX      SEQUENCE OF Er1646v2VrfLtdAlarmMaskEntry
   MAX-ACCESS  not-accessible
   STATUS      current
   DESCRIPTION
      "routAlarmMask"
   ::= {er1646v2VrfLtdAlarmMask 1}

er1646v2VrfLtdAlarmMaskEntry OBJECT-TYPE
   SYNTAX      Er1646v2VrfLtdAlarmMaskEntry
   MAX-ACCESS  not-accessible
   STATUS      current
   DESCRIPTION
      ""
   INDEX      { er1646v2VrfLtdAlarmMaskGlobalIx }
   ::= {er1646v2VrfLtdAlarmMaskTable 1}

Er1646v2VrfLtdAlarmMaskEntry ::=
   SEQUENCE
      {
      er1646v2VrfLtdAlarmMaskGlobalIx
         GlobalIndex,
      er1646v2VrfLtdAlarmMaskValue
         Integer32
      }

er1646v2VrfLtdAlarmMaskGlobalIx OBJECT-TYPE
   SYNTAX      GlobalIndex
   MAX-ACCESS  not-accessible
   STATUS      current
   DESCRIPTION
      "The value of the tlsCntTreeGlobalIndex of the MANAGED OBJECT."
   ::= {er1646v2VrfLtdAlarmMaskEntry 10}

er1646v2VrfLtdAlarmMaskValue OBJECT-TYPE
   SYNTAX      Integer32
   MAX-ACCESS  read-write
   STATUS      current
   DESCRIPTION
      "Path: vrfRouterLtd.editConf.alarmMask

       Bit meanings:
               bit 0 = pingActive,
               bit 1 = qMonLoss,
               bit 2 = qMonDelay,
               bit 3 = qMonJitter"
   ::= {er1646v2VrfLtdAlarmMaskEntry 2147483648}


er1646v2VrfLtdAlarmLev OBJECT IDENTIFIER ::= {er1646v2VrfLtd 170}

er1646v2VrfLtdAlarmLevSSCTable OBJECT-TYPE
   SYNTAX      SEQUENCE OF Er1646v2VrfLtdAlarmLevEntry
   MAX-ACCESS  not-accessible
   STATUS      current
   DESCRIPTION
      "routAlarmLevels"
   ::= {er1646v2VrfLtdAlarmLev 1}

er1646v2VrfLtdAlarmLevEntry OBJECT-TYPE
   SYNTAX      Er1646v2VrfLtdAlarmLevEntry
   MAX-ACCESS  not-accessible
   STATUS      current
   DESCRIPTION
      ""
   INDEX      { er1646v2VrfLtdAlarmLevGlobalIx }
   ::= {er1646v2VrfLtdAlarmLevSSCTable 1}

Er1646v2VrfLtdAlarmLevEntry ::=
   SEQUENCE
      {
      er1646v2VrfLtdAlarmLevGlobalIx
         GlobalIndex,
      er1646v2VrfLtdAlarmLevPingActive
         Integer32,
      er1646v2VrfLtdAlarmLevQMonLoss
         Integer32,
      er1646v2VrfLtdAlarmLevQMonDelay
         Integer32,
      er1646v2VrfLtdAlarmLevQMonJitter
         Integer32
      }

er1646v2VrfLtdAlarmLevGlobalIx OBJECT-TYPE
   SYNTAX      GlobalIndex
   MAX-ACCESS  not-accessible
   STATUS      current
   DESCRIPTION
      "The value of the tlsCntTreeGlobalIndex of the MANAGED OBJECT."
   ::= {er1646v2VrfLtdAlarmLevEntry 10}

er1646v2VrfLtdAlarmLevPingActive OBJECT-TYPE
   SYNTAX      Integer32
   MAX-ACCESS  read-write
   STATUS      current
   DESCRIPTION
      "Path: vrfRouterLtd.editConf.alarmLevel.pingActive"
   ::= {er1646v2VrfLtdAlarmLevEntry 16777216}

er1646v2VrfLtdAlarmLevQMonLoss OBJECT-TYPE
   SYNTAX      Integer32
   MAX-ACCESS  read-write
   STATUS      current
   DESCRIPTION
      "Path: vrfRouterLtd.editConf.alarmLevel.qMonLoss"
   ::= {er1646v2VrfLtdAlarmLevEntry 33554432}

er1646v2VrfLtdAlarmLevQMonDelay OBJECT-TYPE
   SYNTAX      Integer32
   MAX-ACCESS  read-write
   STATUS      current
   DESCRIPTION
      "Path: vrfRouterLtd.editConf.alarmLevel.qMonDelay"
   ::= {er1646v2VrfLtdAlarmLevEntry 50331648}

er1646v2VrfLtdAlarmLevQMonJitter OBJECT-TYPE
   SYNTAX      Integer32
   MAX-ACCESS  read-write
   STATUS      current
   DESCRIPTION
      "Path: vrfRouterLtd.editConf.alarmLevel.qMonJitter"
   ::= {er1646v2VrfLtdAlarmLevEntry 67108864}


er1646v2VrfLtdAccPol OBJECT IDENTIFIER ::= {er1646v2VrfLtd 73}

er1646v2VrfLtdAccPolTable OBJECT-TYPE
   SYNTAX      SEQUENCE OF Er1646v2VrfLtdAccPolEntry
   MAX-ACCESS  not-accessible
   STATUS      current
   DESCRIPTION
      "trafficPolicy to be applied in the inbound direction for NAT"
   ::= {er1646v2VrfLtdAccPol 1}

er1646v2VrfLtdAccPolEntry OBJECT-TYPE
   SYNTAX      Er1646v2VrfLtdAccPolEntry
   MAX-ACCESS  not-accessible
   STATUS      current
   DESCRIPTION
      ""
   INDEX      { er1646v2VrfLtdAccPolGlobalIx }
   ::= {er1646v2VrfLtdAccPolTable 1}

Er1646v2VrfLtdAccPolEntry ::=
   SEQUENCE
      {
      er1646v2VrfLtdAccPolGlobalIx
         GlobalIndex,
      er1646v2VrfLtdAccPolValue
         DisplayString
      }

er1646v2VrfLtdAccPolGlobalIx OBJECT-TYPE
   SYNTAX      GlobalIndex
   MAX-ACCESS  not-accessible
   STATUS      current
   DESCRIPTION
      "The value of the tlsCntTreeGlobalIndex of the MANAGED OBJECT."
   ::= {er1646v2VrfLtdAccPolEntry 10}

er1646v2VrfLtdAccPolValue OBJECT-TYPE
   SYNTAX      DisplayString
   MAX-ACCESS  read-write
   STATUS      current
   DESCRIPTION
      "Path: vrfRouterLtd.editConf.trafficPolicy"
   ::= {er1646v2VrfLtdAccPolEntry 2147483648}



sr1646v2VrfLtd OBJECT IDENTIFIER ::= {r1646v2VrfLtd 14}


sr1646v2VrfLtdSnmpIndex OBJECT IDENTIFIER ::= {sr1646v2VrfLtd 269}

sr1646v2VrfLtdSnmpIndexTable OBJECT-TYPE
   SYNTAX      SEQUENCE OF Sr1646v2VrfLtdSnmpIndexEntry
   MAX-ACCESS  not-accessible
   STATUS      current
   DESCRIPTION
      "SNMP index assigned to this object"
   ::= {sr1646v2VrfLtdSnmpIndex 1}

sr1646v2VrfLtdSnmpIndexEntry OBJECT-TYPE
   SYNTAX      Sr1646v2VrfLtdSnmpIndexEntry
   MAX-ACCESS  not-accessible
   STATUS      current
   DESCRIPTION
      ""
   INDEX      { sr1646v2VrfLtdSnmpIndexGlobalIx }
   ::= {sr1646v2VrfLtdSnmpIndexTable 1}

Sr1646v2VrfLtdSnmpIndexEntry ::=
   SEQUENCE
      {
      sr1646v2VrfLtdSnmpIndexGlobalIx
         GlobalIndex,
      sr1646v2VrfLtdSnmpIndexValue
         Integer32
      }

sr1646v2VrfLtdSnmpIndexGlobalIx OBJECT-TYPE
   SYNTAX      GlobalIndex
   MAX-ACCESS  not-accessible
   STATUS      current
   DESCRIPTION
      "The value of the tlsCntTreeGlobalIndex of the MANAGED OBJECT."
   ::= {sr1646v2VrfLtdSnmpIndexEntry 10}

sr1646v2VrfLtdSnmpIndexValue OBJECT-TYPE
   SYNTAX      Integer32
   MAX-ACCESS  read-only
   STATUS      current
   DESCRIPTION
      "Path: vrfRouterLtd.status.snmpIndex"
   ::= {sr1646v2VrfLtdSnmpIndexEntry 2147483648}


sr1646v2VrfLtdRoutingTable OBJECT IDENTIFIER ::= {sr1646v2VrfLtd 32}

sr1646v2VrfLtdRoutingTableSSCTable OBJECT-TYPE
   SYNTAX      SEQUENCE OF Sr1646v2VrfLtdRoutingTableEntry
   MAX-ACCESS  not-accessible
   STATUS      current
   DESCRIPTION
      "routingTable"
   ::= {sr1646v2VrfLtdRoutingTable 1}

sr1646v2VrfLtdRoutingTableEntry OBJECT-TYPE
   SYNTAX      Sr1646v2VrfLtdRoutingTableEntry
   MAX-ACCESS  not-accessible
   STATUS      current
   DESCRIPTION
      ""
   INDEX      { sr1646v2VrfLtdRoutingTableGlobalIx,
                sr1646v2VrfLtdRoutingTableTableIx }
   ::= {sr1646v2VrfLtdRoutingTableSSCTable 1}

Sr1646v2VrfLtdRoutingTableEntry ::=
   SEQUENCE
      {
      sr1646v2VrfLtdRoutingTableGlobalIx
         GlobalIndex,
      sr1646v2VrfLtdRoutingTableTableIx
         TableIndex,
      sr1646v2VrfLtdRoutingTableNetwork
         IpAddress,
      sr1646v2VrfLtdRoutingTableMask
         IpAddress,
      sr1646v2VrfLtdRoutingTableGateway
         IpAddress,
      sr1646v2VrfLtdRoutingTableIf
         DisplayString,
      sr1646v2VrfLtdRoutingTableEncap
         INTEGER,
      sr1646v2VrfLtdRoutingTableStatus
         INTEGER,
      sr1646v2VrfLtdRoutingTablePref
         Integer32,
      sr1646v2VrfLtdRoutingTableType
         INTEGER,
      sr1646v2VrfLtdRoutingTableMetric
         Integer32,
      sr1646v2VrfLtdRoutingTableTimeOut
         TimeTicks,
      sr1646v2VrfLtdRoutingTableTag
         DisplayString
      }

sr1646v2VrfLtdRoutingTableGlobalIx OBJECT-TYPE
   SYNTAX      GlobalIndex
   MAX-ACCESS  not-accessible
   STATUS      current
   DESCRIPTION
      "The value of the tlsCntTreeGlobalIndex of the MANAGED OBJECT."
   ::= {sr1646v2VrfLtdRoutingTableEntry 10}

sr1646v2VrfLtdRoutingTableTableIx OBJECT-TYPE
   SYNTAX      TableIndex
   MAX-ACCESS  not-accessible
   STATUS      current
   DESCRIPTION
      ""
   ::= {sr1646v2VrfLtdRoutingTableEntry 11}

sr1646v2VrfLtdRoutingTableNetwork OBJECT-TYPE
   SYNTAX      IpAddress
   MAX-ACCESS  read-only
   STATUS      current
   DESCRIPTION
      "Path: vrfRouterLtd.status.routingTable.network"
   ::= {sr1646v2VrfLtdRoutingTableEntry 16777216}

sr1646v2VrfLtdRoutingTableMask OBJECT-TYPE
   SYNTAX      IpAddress
   MAX-ACCESS  read-only
   STATUS      current
   DESCRIPTION
      "Path: vrfRouterLtd.status.routingTable.mask"
   ::= {sr1646v2VrfLtdRoutingTableEntry 33554432}

sr1646v2VrfLtdRoutingTableGateway OBJECT-TYPE
   SYNTAX      IpAddress
   MAX-ACCESS  read-only
   STATUS      current
   DESCRIPTION
      "Path: vrfRouterLtd.status.routingTable.gateway"
   ::= {sr1646v2VrfLtdRoutingTableEntry 50331648}

sr1646v2VrfLtdRoutingTableIf OBJECT-TYPE
   SYNTAX      DisplayString
   MAX-ACCESS  read-only
   STATUS      current
   DESCRIPTION
      "Path: vrfRouterLtd.status.routingTable.interface"
   ::= {sr1646v2VrfLtdRoutingTableEntry 67108864}

sr1646v2VrfLtdRoutingTableEncap OBJECT-TYPE
   SYNTAX      INTEGER
               {
               none (0),
               framemrelay (1),
               ppp (2),
               ethernet (3),
               x25 (4),
               atm (5),
               policysdependent (6),
               pppoA (7),
               pppoE (8),
               sasdependent (9),
               gre (10)
               }
   MAX-ACCESS  read-only
   STATUS      current
   DESCRIPTION
      "Path: vrfRouterLtd.status.routingTable.encapsulation

       Possibilities:
               none   (0)
               frame-relay   (1)
               ppp   (2)
               ethernet   (3)
               x25   (4)
               atm   (5)
               policy dependent   (6)
               pppoA   (7)
               pppoE   (8)
               sa dependent   (9)
               gre   (10)"
   ::= {sr1646v2VrfLtdRoutingTableEntry 83886080}

sr1646v2VrfLtdRoutingTableStatus OBJECT-TYPE
   SYNTAX      INTEGER
               {
               down (0),
               up (1),
               discard (2),
               spoofing (3),
               holdDown (4),
               closed (5)
               }
   MAX-ACCESS  read-only
   STATUS      current
   DESCRIPTION
      "Path: vrfRouterLtd.status.routingTable.status

       Possibilities:
               down   (0)
               up   (1)
               discard   (2)
               spoofing   (3)
               holdDown   (4)
               closed   (5)"
   ::= {sr1646v2VrfLtdRoutingTableEntry 100663296}

sr1646v2VrfLtdRoutingTablePref OBJECT-TYPE
   SYNTAX      Integer32
   MAX-ACCESS  read-only
   STATUS      current
   DESCRIPTION
      "Path: vrfRouterLtd.status.routingTable.preference"
   ::= {sr1646v2VrfLtdRoutingTableEntry 117440512}

sr1646v2VrfLtdRoutingTableType OBJECT-TYPE
   SYNTAX      INTEGER
               {
               internal (0),
               local (1),
               host (2),
               static (3),
               rip (4),
               ospf (5),
               bgp (6),
               float (7),
               dial (8),
               policy (9),
               nat (10),
               radius (11),
               orchid (12),
               reject (13),
               ipsec (14),
               floatIpsec (15),
               mgmtProxy (16),
               ipV6natpt (17),
               pim (18),
               none (19),
               fixedDial (20),
               fixedOutPolicy (21),
               fixedInterface (22),
               fixedIpsec (23),
               staticTimed (24),
               staticTracked (25),
               everyCat (26)
               }
   MAX-ACCESS  read-only
   STATUS      current
   DESCRIPTION
      "Path: vrfRouterLtd.status.routingTable.type

       Possibilities:
               internal   (0)
               local   (1)
               host   (2)
               static   (3)
               rip   (4)
               ospf   (5)
               bgp   (6)
               float   (7)
               dial   (8)
               policy   (9)
               nat   (10)
               radius   (11)
               orchid   (12)
               reject   (13)
               ipsec   (14)
               floatIpsec   (15)
               mgmtProxy   (16)
               ipV6natpt   (17)
               pim   (18)
               none   (19)
               fixedDial   (20)
               fixedOutPolicy   (21)
               fixedInterface   (22)
               fixedIpsec   (23)
               staticTimed   (24)
               staticTracked   (25)
               everyCat   (26)"
   ::= {sr1646v2VrfLtdRoutingTableEntry 134217728}

sr1646v2VrfLtdRoutingTableMetric OBJECT-TYPE
   SYNTAX      Integer32
   MAX-ACCESS  read-only
   STATUS      current
   DESCRIPTION
      "Path: vrfRouterLtd.status.routingTable.metric"
   ::= {sr1646v2VrfLtdRoutingTableEntry 150994944}

sr1646v2VrfLtdRoutingTableTimeOut OBJECT-TYPE
   SYNTAX      TimeTicks
   MAX-ACCESS  read-only
   STATUS      current
   DESCRIPTION
      "Path: vrfRouterLtd.status.routingTable.timeOut

       Time in centi-second."
   ::= {sr1646v2VrfLtdRoutingTableEntry 167772160}

sr1646v2VrfLtdRoutingTableTag OBJECT-TYPE
   SYNTAX      DisplayString
   MAX-ACCESS  read-only
   STATUS      current
   DESCRIPTION
      "Path: vrfRouterLtd.status.routingTable.tag"
   ::= {sr1646v2VrfLtdRoutingTableEntry 201326592}


sr1646v2VrfLtdDhcpBinding OBJECT IDENTIFIER ::= {sr1646v2VrfLtd 54}

sr1646v2VrfLtdDhcpBindingSSCTable OBJECT-TYPE
   SYNTAX      SEQUENCE OF Sr1646v2VrfLtdDhcpBindingEntry
   MAX-ACCESS  not-accessible
   STATUS      current
   DESCRIPTION
      "table containing DHCP client information"
   ::= {sr1646v2VrfLtdDhcpBinding 1}

sr1646v2VrfLtdDhcpBindingEntry OBJECT-TYPE
   SYNTAX      Sr1646v2VrfLtdDhcpBindingEntry
   MAX-ACCESS  not-accessible
   STATUS      current
   DESCRIPTION
      ""
   INDEX      { sr1646v2VrfLtdDhcpBindingGlobalIx,
                sr1646v2VrfLtdDhcpBindingTableIx }
   ::= {sr1646v2VrfLtdDhcpBindingSSCTable 1}

Sr1646v2VrfLtdDhcpBindingEntry ::=
   SEQUENCE
      {
      sr1646v2VrfLtdDhcpBindingGlobalIx
         GlobalIndex,
      sr1646v2VrfLtdDhcpBindingTableIx
         TableIndex,
      sr1646v2VrfLtdDhcpBindingIpAddress
         IpAddress,
      sr1646v2VrfLtdDhcpBindingMacAddress
         OCTET STRING,
      sr1646v2VrfLtdDhcpBindingLeaseTime
         TimeTicks,
      sr1646v2VrfLtdDhcpBindingHostName
         DisplayString,
      sr1646v2VrfLtdDhcpBindingInterface
         DisplayString,
      sr1646v2VrfLtdDhcpBindingState
         INTEGER,
      sr1646v2VrfLtdDhcpBindingCheckAddress
         INTEGER
      }

sr1646v2VrfLtdDhcpBindingGlobalIx OBJECT-TYPE
   SYNTAX      GlobalIndex
   MAX-ACCESS  not-accessible
   STATUS      current
   DESCRIPTION
      "The value of the tlsCntTreeGlobalIndex of the MANAGED OBJECT."
   ::= {sr1646v2VrfLtdDhcpBindingEntry 10}

sr1646v2VrfLtdDhcpBindingTableIx OBJECT-TYPE
   SYNTAX      TableIndex
   MAX-ACCESS  not-accessible
   STATUS      current
   DESCRIPTION
      ""
   ::= {sr1646v2VrfLtdDhcpBindingEntry 11}

sr1646v2VrfLtdDhcpBindingIpAddress OBJECT-TYPE
   SYNTAX      IpAddress
   MAX-ACCESS  read-only
   STATUS      current
   DESCRIPTION
      "Path: vrfRouterLtd.status.dhcpBinding.ipAddress"
   ::= {sr1646v2VrfLtdDhcpBindingEntry 16777216}

sr1646v2VrfLtdDhcpBindingMacAddress OBJECT-TYPE
   SYNTAX      OCTET STRING
   MAX-ACCESS  read-only
   STATUS      current
   DESCRIPTION
      "Path: vrfRouterLtd.status.dhcpBinding.macAddress

       MAC address."
   ::= {sr1646v2VrfLtdDhcpBindingEntry 33554432}

sr1646v2VrfLtdDhcpBindingLeaseTime OBJECT-TYPE
   SYNTAX      TimeTicks
   MAX-ACCESS  read-only
   STATUS      current
   DESCRIPTION
      "Path: vrfRouterLtd.status.dhcpBinding.leaseTime

       Time in centi-second."
   ::= {sr1646v2VrfLtdDhcpBindingEntry 50331648}

sr1646v2VrfLtdDhcpBindingHostName OBJECT-TYPE
   SYNTAX      DisplayString
   MAX-ACCESS  read-only
   STATUS      current
   DESCRIPTION
      "Path: vrfRouterLtd.status.dhcpBinding.hostName"
   ::= {sr1646v2VrfLtdDhcpBindingEntry 67108864}

sr1646v2VrfLtdDhcpBindingInterface OBJECT-TYPE
   SYNTAX      DisplayString
   MAX-ACCESS  read-only
   STATUS      current
   DESCRIPTION
      "Path: vrfRouterLtd.status.dhcpBinding.interface"
   ::= {sr1646v2VrfLtdDhcpBindingEntry 100663296}

sr1646v2VrfLtdDhcpBindingState OBJECT-TYPE
   SYNTAX      INTEGER
               {
               onHold (0),
               leased (1),
               reserved (2)
               }
   MAX-ACCESS  read-only
   STATUS      current
   DESCRIPTION
      "Path: vrfRouterLtd.status.dhcpBinding.state

       Possibilities:
               onHold   (0)
               leased   (1)
               reserved   (2)"
   ::= {sr1646v2VrfLtdDhcpBindingEntry 83886080}

sr1646v2VrfLtdDhcpBindingCheckAddress OBJECT-TYPE
   SYNTAX      INTEGER
               {
               idle (0),
               pending (1),
               validated (2),
               rejected (3),
               skipped (4)
               }
   MAX-ACCESS  read-only
   STATUS      current
   DESCRIPTION
      "Path: vrfRouterLtd.status.dhcpBinding.checkAddress

       Possibilities:
               idle   (0)
               pending   (1)
               validated   (2)
               rejected   (3)
               skipped   (4)"
   ::= {sr1646v2VrfLtdDhcpBindingEntry 117440512}


sr1646v2VrfLtdDhcpStat OBJECT IDENTIFIER ::= {sr1646v2VrfLtd 55}

sr1646v2VrfLtdDhcpStatSSCTable OBJECT-TYPE
   SYNTAX      SEQUENCE OF Sr1646v2VrfLtdDhcpStatEntry
   MAX-ACCESS  not-accessible
   STATUS      current
   DESCRIPTION
      "DHCP statistics over addresses free, leased and in hold"
   ::= {sr1646v2VrfLtdDhcpStat 1}

sr1646v2VrfLtdDhcpStatEntry OBJECT-TYPE
   SYNTAX      Sr1646v2VrfLtdDhcpStatEntry
   MAX-ACCESS  not-accessible
   STATUS      current
   DESCRIPTION
      ""
   INDEX      { sr1646v2VrfLtdDhcpStatGlobalIx,
                sr1646v2VrfLtdDhcpStatTableIx }
   ::= {sr1646v2VrfLtdDhcpStatSSCTable 1}

Sr1646v2VrfLtdDhcpStatEntry ::=
   SEQUENCE
      {
      sr1646v2VrfLtdDhcpStatGlobalIx
         GlobalIndex,
      sr1646v2VrfLtdDhcpStatTableIx
         TableIndex,
      sr1646v2VrfLtdDhcpStatStartRange
         IpAddress,
      sr1646v2VrfLtdDhcpStatEndRange
         IpAddress,
      sr1646v2VrfLtdDhcpStatInterface
         DisplayString,
      sr1646v2VrfLtdDhcpStatFree
         Integer32,
      sr1646v2VrfLtdDhcpStatLeased
         Integer32,
      sr1646v2VrfLtdDhcpStatHold
         Integer32
      }

sr1646v2VrfLtdDhcpStatGlobalIx OBJECT-TYPE
   SYNTAX      GlobalIndex
   MAX-ACCESS  not-accessible
   STATUS      current
   DESCRIPTION
      "The value of the tlsCntTreeGlobalIndex of the MANAGED OBJECT."
   ::= {sr1646v2VrfLtdDhcpStatEntry 10}

sr1646v2VrfLtdDhcpStatTableIx OBJECT-TYPE
   SYNTAX      TableIndex
   MAX-ACCESS  not-accessible
   STATUS      current
   DESCRIPTION
      ""
   ::= {sr1646v2VrfLtdDhcpStatEntry 11}

sr1646v2VrfLtdDhcpStatStartRange OBJECT-TYPE
   SYNTAX      IpAddress
   MAX-ACCESS  read-only
   STATUS      current
   DESCRIPTION
      "Path: vrfRouterLtd.status.dhcpStatistics.startRange"
   ::= {sr1646v2VrfLtdDhcpStatEntry 16777216}

sr1646v2VrfLtdDhcpStatEndRange OBJECT-TYPE
   SYNTAX      IpAddress
   MAX-ACCESS  read-only
   STATUS      current
   DESCRIPTION
      "Path: vrfRouterLtd.status.dhcpStatistics.endRange"
   ::= {sr1646v2VrfLtdDhcpStatEntry 33554432}

sr1646v2VrfLtdDhcpStatInterface OBJECT-TYPE
   SYNTAX      DisplayString
   MAX-ACCESS  read-only
   STATUS      current
   DESCRIPTION
      "Path: vrfRouterLtd.status.dhcpStatistics.interface"
   ::= {sr1646v2VrfLtdDhcpStatEntry 100663296}

sr1646v2VrfLtdDhcpStatFree OBJECT-TYPE
   SYNTAX      Integer32
   MAX-ACCESS  read-only
   STATUS      current
   DESCRIPTION
      "Path: vrfRouterLtd.status.dhcpStatistics.free"
   ::= {sr1646v2VrfLtdDhcpStatEntry 50331648}

sr1646v2VrfLtdDhcpStatLeased OBJECT-TYPE
   SYNTAX      Integer32
   MAX-ACCESS  read-only
   STATUS      current
   DESCRIPTION
      "Path: vrfRouterLtd.status.dhcpStatistics.leased"
   ::= {sr1646v2VrfLtdDhcpStatEntry 67108864}

sr1646v2VrfLtdDhcpStatHold OBJECT-TYPE
   SYNTAX      Integer32
   MAX-ACCESS  read-only
   STATUS      current
   DESCRIPTION
      "Path: vrfRouterLtd.status.dhcpStatistics.hold"
   ::= {sr1646v2VrfLtdDhcpStatEntry 83886080}


sr1646v2VrfLtdDhcpRelay OBJECT IDENTIFIER ::= {sr1646v2VrfLtd 71}

sr1646v2VrfLtdDhcpRelaySSCTable OBJECT-TYPE
   SYNTAX      SEQUENCE OF Sr1646v2VrfLtdDhcpRelayEntry
   MAX-ACCESS  not-accessible
   STATUS      current
   DESCRIPTION
      "dhcpRelayInfo"
   ::= {sr1646v2VrfLtdDhcpRelay 1}

sr1646v2VrfLtdDhcpRelayEntry OBJECT-TYPE
   SYNTAX      Sr1646v2VrfLtdDhcpRelayEntry
   MAX-ACCESS  not-accessible
   STATUS      current
   DESCRIPTION
      ""
   INDEX      { sr1646v2VrfLtdDhcpRelayGlobalIx,
                sr1646v2VrfLtdDhcpRelayTableIx }
   ::= {sr1646v2VrfLtdDhcpRelaySSCTable 1}

Sr1646v2VrfLtdDhcpRelayEntry ::=
   SEQUENCE
      {
      sr1646v2VrfLtdDhcpRelayGlobalIx
         GlobalIndex,
      sr1646v2VrfLtdDhcpRelayTableIx
         TableIndex,
      sr1646v2VrfLtdDhcpRelaySourceIntf
         DisplayString,
      sr1646v2VrfLtdDhcpRelayMac
         OCTET STRING,
      sr1646v2VrfLtdDhcpRelayAssignedIp
         IpAddress,
      sr1646v2VrfLtdDhcpRelayServerIp
         IpAddress,
      sr1646v2VrfLtdDhcpRelayDhcpStatus
         INTEGER,
      sr1646v2VrfLtdDhcpRelayLeaseTime
         TimeTicks
      }

sr1646v2VrfLtdDhcpRelayGlobalIx OBJECT-TYPE
   SYNTAX      GlobalIndex
   MAX-ACCESS  not-accessible
   STATUS      current
   DESCRIPTION
      "The value of the tlsCntTreeGlobalIndex of the MANAGED OBJECT."
   ::= {sr1646v2VrfLtdDhcpRelayEntry 10}

sr1646v2VrfLtdDhcpRelayTableIx OBJECT-TYPE
   SYNTAX      TableIndex
   MAX-ACCESS  not-accessible
   STATUS      current
   DESCRIPTION
      ""
   ::= {sr1646v2VrfLtdDhcpRelayEntry 11}

sr1646v2VrfLtdDhcpRelaySourceIntf OBJECT-TYPE
   SYNTAX      DisplayString
   MAX-ACCESS  read-only
   STATUS      current
   DESCRIPTION
      "Path: vrfRouterLtd.status.dhcpRelayInfo.sourceIntf"
   ::= {sr1646v2VrfLtdDhcpRelayEntry 16777216}

sr1646v2VrfLtdDhcpRelayMac OBJECT-TYPE
   SYNTAX      OCTET STRING
   MAX-ACCESS  read-only
   STATUS      current
   DESCRIPTION
      "Path: vrfRouterLtd.status.dhcpRelayInfo.mac

       MAC address."
   ::= {sr1646v2VrfLtdDhcpRelayEntry 33554432}

sr1646v2VrfLtdDhcpRelayAssignedIp OBJECT-TYPE
   SYNTAX      IpAddress
   MAX-ACCESS  read-only
   STATUS      current
   DESCRIPTION
      "Path: vrfRouterLtd.status.dhcpRelayInfo.assignedIp"
   ::= {sr1646v2VrfLtdDhcpRelayEntry 50331648}

sr1646v2VrfLtdDhcpRelayServerIp OBJECT-TYPE
   SYNTAX      IpAddress
   MAX-ACCESS  read-only
   STATUS      current
   DESCRIPTION
      "Path: vrfRouterLtd.status.dhcpRelayInfo.serverIp"
   ::= {sr1646v2VrfLtdDhcpRelayEntry 67108864}

sr1646v2VrfLtdDhcpRelayDhcpStatus OBJECT-TYPE
   SYNTAX      INTEGER
               {
               discover (1),
               offer (2),
               request (3),
               decline (4),
               ack (5),
               nak (6),
               release (7),
               inform (8),
               idle (9)
               }
   MAX-ACCESS  read-only
   STATUS      current
   DESCRIPTION
      "Path: vrfRouterLtd.status.dhcpRelayInfo.dhcpStatus

       Possibilities:
               discover   (1)
               offer   (2)
               request   (3)
               decline   (4)
               ack   (5)
               nak   (6)
               release   (7)
               inform   (8)
               idle   (9)"
   ::= {sr1646v2VrfLtdDhcpRelayEntry 83886080}

sr1646v2VrfLtdDhcpRelayLeaseTime OBJECT-TYPE
   SYNTAX      TimeTicks
   MAX-ACCESS  read-only
   STATUS      current
   DESCRIPTION
      "Path: vrfRouterLtd.status.dhcpRelayInfo.leaseTime

       Time in centi-second."
   ::= {sr1646v2VrfLtdDhcpRelayEntry 117440512}


sr1646v2VrfLtdDhcpBlacklist OBJECT IDENTIFIER ::= {sr1646v2VrfLtd 75}

sr1646v2VrfLtdDhcpBlacklistSSCTable OBJECT-TYPE
   SYNTAX      SEQUENCE OF Sr1646v2VrfLtdDhcpBlacklistEntry
   MAX-ACCESS  not-accessible
   STATUS      current
   DESCRIPTION
      "table containing DHCP Blacklist information"
   ::= {sr1646v2VrfLtdDhcpBlacklist 1}

sr1646v2VrfLtdDhcpBlacklistEntry OBJECT-TYPE
   SYNTAX      Sr1646v2VrfLtdDhcpBlacklistEntry
   MAX-ACCESS  not-accessible
   STATUS      current
   DESCRIPTION
      ""
   INDEX      { sr1646v2VrfLtdDhcpBlacklistGlobalIx,
                sr1646v2VrfLtdDhcpBlacklistTableIx }
   ::= {sr1646v2VrfLtdDhcpBlacklistSSCTable 1}

Sr1646v2VrfLtdDhcpBlacklistEntry ::=
   SEQUENCE
      {
      sr1646v2VrfLtdDhcpBlacklistGlobalIx
         GlobalIndex,
      sr1646v2VrfLtdDhcpBlacklistTableIx
         TableIndex,
      sr1646v2VrfLtdDhcpBlacklistIpAddress
         IpAddress,
      sr1646v2VrfLtdDhcpBlacklistMacAddress
         OCTET STRING,
      sr1646v2VrfLtdDhcpBlacklistReason
         INTEGER
      }

sr1646v2VrfLtdDhcpBlacklistGlobalIx OBJECT-TYPE
   SYNTAX      GlobalIndex
   MAX-ACCESS  not-accessible
   STATUS      current
   DESCRIPTION
      "The value of the tlsCntTreeGlobalIndex of the MANAGED OBJECT."
   ::= {sr1646v2VrfLtdDhcpBlacklistEntry 10}

sr1646v2VrfLtdDhcpBlacklistTableIx OBJECT-TYPE
   SYNTAX      TableIndex
   MAX-ACCESS  not-accessible
   STATUS      current
   DESCRIPTION
      ""
   ::= {sr1646v2VrfLtdDhcpBlacklistEntry 11}

sr1646v2VrfLtdDhcpBlacklistIpAddress OBJECT-TYPE
   SYNTAX      IpAddress
   MAX-ACCESS  read-only
   STATUS      current
   DESCRIPTION
      "Path: vrfRouterLtd.status.dhcpBlacklist.ipAddress"
   ::= {sr1646v2VrfLtdDhcpBlacklistEntry 16777216}

sr1646v2VrfLtdDhcpBlacklistMacAddress OBJECT-TYPE
   SYNTAX      OCTET STRING
   MAX-ACCESS  read-only
   STATUS      current
   DESCRIPTION
      "Path: vrfRouterLtd.status.dhcpBlacklist.macAddress

       MAC address."
   ::= {sr1646v2VrfLtdDhcpBlacklistEntry 33554432}

sr1646v2VrfLtdDhcpBlacklistReason OBJECT-TYPE
   SYNTAX      INTEGER
               {
               none (0),
               arp (1),
               alienAck (2),
               declined (3),
               ping (4),
               networkOrBroadcast (5)
               }
   MAX-ACCESS  read-only
   STATUS      current
   DESCRIPTION
      "Path: vrfRouterLtd.status.dhcpBlacklist.reason

       Possibilities:
               none   (0)
               arp   (1)
               alienAck   (2)
               declined   (3)
               ping   (4)
               networkOrBroadcast   (5)"
   ::= {sr1646v2VrfLtdDhcpBlacklistEntry 50331648}


sr1646v2VrfLtdAddrPools OBJECT IDENTIFIER ::= {sr1646v2VrfLtd 109}

sr1646v2VrfLtdAddrPoolsSSCTable OBJECT-TYPE
   SYNTAX      SEQUENCE OF Sr1646v2VrfLtdAddrPoolsEntry
   MAX-ACCESS  not-accessible
   STATUS      current
   DESCRIPTION
      "ip pool status"
   ::= {sr1646v2VrfLtdAddrPools 1}

sr1646v2VrfLtdAddrPoolsEntry OBJECT-TYPE
   SYNTAX      Sr1646v2VrfLtdAddrPoolsEntry
   MAX-ACCESS  not-accessible
   STATUS      current
   DESCRIPTION
      ""
   INDEX      { sr1646v2VrfLtdAddrPoolsGlobalIx,
                sr1646v2VrfLtdAddrPoolsTableIx }
   ::= {sr1646v2VrfLtdAddrPoolsSSCTable 1}

Sr1646v2VrfLtdAddrPoolsEntry ::=
   SEQUENCE
      {
      sr1646v2VrfLtdAddrPoolsGlobalIx
         GlobalIndex,
      sr1646v2VrfLtdAddrPoolsTableIx
         TableIndex,
      sr1646v2VrfLtdAddrPoolsName
         DisplayString,
      sr1646v2VrfLtdAddrPoolsType
         INTEGER,
      sr1646v2VrfLtdAddrPoolsNrOfAddresses
         Counter32,
      sr1646v2VrfLtdAddrPoolsAvailAddresses
         Counter32
      }

sr1646v2VrfLtdAddrPoolsGlobalIx OBJECT-TYPE
   SYNTAX      GlobalIndex
   MAX-ACCESS  not-accessible
   STATUS      current
   DESCRIPTION
      "The value of the tlsCntTreeGlobalIndex of the MANAGED OBJECT."
   ::= {sr1646v2VrfLtdAddrPoolsEntry 10}

sr1646v2VrfLtdAddrPoolsTableIx OBJECT-TYPE
   SYNTAX      TableIndex
   MAX-ACCESS  not-accessible
   STATUS      current
   DESCRIPTION
      ""
   ::= {sr1646v2VrfLtdAddrPoolsEntry 11}

sr1646v2VrfLtdAddrPoolsName OBJECT-TYPE
   SYNTAX      DisplayString
   MAX-ACCESS  read-only
   STATUS      current
   DESCRIPTION
      "Path: vrfRouterLtd.status.addrPools.name"
   ::= {sr1646v2VrfLtdAddrPoolsEntry 16777216}

sr1646v2VrfLtdAddrPoolsType OBJECT-TYPE
   SYNTAX      INTEGER
               {
               list (1),
               interval (2)
               }
   MAX-ACCESS  read-only
   STATUS      current
   DESCRIPTION
      "Path: vrfRouterLtd.status.addrPools.type

       Possibilities:
               list   (1)
               interval   (2)"
   ::= {sr1646v2VrfLtdAddrPoolsEntry 33554432}

sr1646v2VrfLtdAddrPoolsNrOfAddresses OBJECT-TYPE
   SYNTAX      Counter32
   MAX-ACCESS  read-only
   STATUS      current
   DESCRIPTION
      "Path: vrfRouterLtd.status.addrPools.nrOfAddresses

       32 bit unsigned wrappable counter."
   ::= {sr1646v2VrfLtdAddrPoolsEntry 50331648}

sr1646v2VrfLtdAddrPoolsAvailAddresses OBJECT-TYPE
   SYNTAX      Counter32
   MAX-ACCESS  read-only
   STATUS      current
   DESCRIPTION
      "Path: vrfRouterLtd.status.addrPools.availAddresses

       32 bit unsigned wrappable counter."
   ::= {sr1646v2VrfLtdAddrPoolsEntry 67108864}


sr1646v2VrfLtdPoolReservations OBJECT IDENTIFIER ::= {sr1646v2VrfLtd 103}

sr1646v2VrfLtdPoolReservationsSSCTable OBJECT-TYPE
   SYNTAX      SEQUENCE OF Sr1646v2VrfLtdPoolReservationsEntry
   MAX-ACCESS  not-accessible
   STATUS      current
   DESCRIPTION
      "ip pool occupied addresses"
   ::= {sr1646v2VrfLtdPoolReservations 1}

sr1646v2VrfLtdPoolReservationsEntry OBJECT-TYPE
   SYNTAX      Sr1646v2VrfLtdPoolReservationsEntry
   MAX-ACCESS  not-accessible
   STATUS      current
   DESCRIPTION
      ""
   INDEX      { sr1646v2VrfLtdPoolReservationsGlobalIx,
                sr1646v2VrfLtdPoolReservationsTableIx }
   ::= {sr1646v2VrfLtdPoolReservationsSSCTable 1}

Sr1646v2VrfLtdPoolReservationsEntry ::=
   SEQUENCE
      {
      sr1646v2VrfLtdPoolReservationsGlobalIx
         GlobalIndex,
      sr1646v2VrfLtdPoolReservationsTableIx
         TableIndex,
      sr1646v2VrfLtdPoolReservationsName
         DisplayString,
      sr1646v2VrfLtdPoolReservationsType
         INTEGER,
      sr1646v2VrfLtdPoolReservationsLocal
         IpAddress,
      sr1646v2VrfLtdPoolReservationsRemote
         IpAddress,
      sr1646v2VrfLtdPoolReservationsNetMask
         IpAddress,
      sr1646v2VrfLtdPoolReservationsInterface
         DisplayString
      }

sr1646v2VrfLtdPoolReservationsGlobalIx OBJECT-TYPE
   SYNTAX      GlobalIndex
   MAX-ACCESS  not-accessible
   STATUS      current
   DESCRIPTION
      "The value of the tlsCntTreeGlobalIndex of the MANAGED OBJECT."
   ::= {sr1646v2VrfLtdPoolReservationsEntry 10}

sr1646v2VrfLtdPoolReservationsTableIx OBJECT-TYPE
   SYNTAX      TableIndex
   MAX-ACCESS  not-accessible
   STATUS      current
   DESCRIPTION
      ""
   ::= {sr1646v2VrfLtdPoolReservationsEntry 11}

sr1646v2VrfLtdPoolReservationsName OBJECT-TYPE
   SYNTAX      DisplayString
   MAX-ACCESS  read-only
   STATUS      current
   DESCRIPTION
      "Path: vrfRouterLtd.status.poolReservations.name"
   ::= {sr1646v2VrfLtdPoolReservationsEntry 16777216}

sr1646v2VrfLtdPoolReservationsType OBJECT-TYPE
   SYNTAX      INTEGER
               {
               list (1),
               interval (2)
               }
   MAX-ACCESS  read-only
   STATUS      current
   DESCRIPTION
      "Path: vrfRouterLtd.status.poolReservations.type

       Possibilities:
               list   (1)
               interval   (2)"
   ::= {sr1646v2VrfLtdPoolReservationsEntry 33554432}

sr1646v2VrfLtdPoolReservationsLocal OBJECT-TYPE
   SYNTAX      IpAddress
   MAX-ACCESS  read-only
   STATUS      current
   DESCRIPTION
      "Path: vrfRouterLtd.status.poolReservations.local"
   ::= {sr1646v2VrfLtdPoolReservationsEntry 50331648}

sr1646v2VrfLtdPoolReservationsRemote OBJECT-TYPE
   SYNTAX      IpAddress
   MAX-ACCESS  read-only
   STATUS      current
   DESCRIPTION
      "Path: vrfRouterLtd.status.poolReservations.remote"
   ::= {sr1646v2VrfLtdPoolReservationsEntry 67108864}

sr1646v2VrfLtdPoolReservationsNetMask OBJECT-TYPE
   SYNTAX      IpAddress
   MAX-ACCESS  read-only
   STATUS      current
   DESCRIPTION
      "Path: vrfRouterLtd.status.poolReservations.netMask"
   ::= {sr1646v2VrfLtdPoolReservationsEntry 83886080}

sr1646v2VrfLtdPoolReservationsInterface OBJECT-TYPE
   SYNTAX      DisplayString
   MAX-ACCESS  read-only
   STATUS      current
   DESCRIPTION
      "Path: vrfRouterLtd.status.poolReservations.interface"
   ::= {sr1646v2VrfLtdPoolReservationsEntry 100663296}


sr1646v2VrfLtdDnsCache OBJECT IDENTIFIER ::= {sr1646v2VrfLtd 65}

sr1646v2VrfLtdDnsCacheSSCTable OBJECT-TYPE
   SYNTAX      SEQUENCE OF Sr1646v2VrfLtdDnsCacheEntry
   MAX-ACCESS  not-accessible
   STATUS      current
   DESCRIPTION
      "DNS cache table"
   ::= {sr1646v2VrfLtdDnsCache 1}

sr1646v2VrfLtdDnsCacheEntry OBJECT-TYPE
   SYNTAX      Sr1646v2VrfLtdDnsCacheEntry
   MAX-ACCESS  not-accessible
   STATUS      current
   DESCRIPTION
      ""
   INDEX      { sr1646v2VrfLtdDnsCacheGlobalIx,
                sr1646v2VrfLtdDnsCacheTableIx }
   ::= {sr1646v2VrfLtdDnsCacheSSCTable 1}

Sr1646v2VrfLtdDnsCacheEntry ::=
   SEQUENCE
      {
      sr1646v2VrfLtdDnsCacheGlobalIx
         GlobalIndex,
      sr1646v2VrfLtdDnsCacheTableIx
         TableIndex,
      sr1646v2VrfLtdDnsCacheIpAddress
         IpAddress,
      sr1646v2VrfLtdDnsCacheIpV6Address
         Ipv6Address,
      sr1646v2VrfLtdDnsCacheHostname
         DisplayString,
      sr1646v2VrfLtdDnsCacheTtl
         TimeTicks,
      sr1646v2VrfLtdDnsCacheInfiniteTimeOut
         INTEGER,
      sr1646v2VrfLtdDnsCacheMatches
         Counter32
      }

sr1646v2VrfLtdDnsCacheGlobalIx OBJECT-TYPE
   SYNTAX      GlobalIndex
   MAX-ACCESS  not-accessible
   STATUS      current
   DESCRIPTION
      "The value of the tlsCntTreeGlobalIndex of the MANAGED OBJECT."
   ::= {sr1646v2VrfLtdDnsCacheEntry 10}

sr1646v2VrfLtdDnsCacheTableIx OBJECT-TYPE
   SYNTAX      TableIndex
   MAX-ACCESS  not-accessible
   STATUS      current
   DESCRIPTION
      ""
   ::= {sr1646v2VrfLtdDnsCacheEntry 11}

sr1646v2VrfLtdDnsCacheIpAddress OBJECT-TYPE
   SYNTAX      IpAddress
   MAX-ACCESS  read-only
   STATUS      current
   DESCRIPTION
      "Path: vrfRouterLtd.status.dnsCache.ipAddress"
   ::= {sr1646v2VrfLtdDnsCacheEntry 16777216}

sr1646v2VrfLtdDnsCacheIpV6Address OBJECT-TYPE
   SYNTAX      Ipv6Address
   MAX-ACCESS  read-only
   STATUS      current
   DESCRIPTION
      "Path: vrfRouterLtd.status.dnsCache.ipV6Address

       ipv6 address"
   ::= {sr1646v2VrfLtdDnsCacheEntry 83886080}

sr1646v2VrfLtdDnsCacheHostname OBJECT-TYPE
   SYNTAX      DisplayString
   MAX-ACCESS  read-only
   STATUS      current
   DESCRIPTION
      "Path: vrfRouterLtd.status.dnsCache.hostname"
   ::= {sr1646v2VrfLtdDnsCacheEntry 33554432}

sr1646v2VrfLtdDnsCacheTtl OBJECT-TYPE
   SYNTAX      TimeTicks
   MAX-ACCESS  read-only
   STATUS      current
   DESCRIPTION
      "Path: vrfRouterLtd.status.dnsCache.ttl

       Time in centi-second."
   ::= {sr1646v2VrfLtdDnsCacheEntry 50331648}

sr1646v2VrfLtdDnsCacheInfiniteTimeOut OBJECT-TYPE
   SYNTAX      INTEGER
               {
               disabled (0),
               enabled (1),
               static (2)
               }
   MAX-ACCESS  read-only
   STATUS      current
   DESCRIPTION
      "Path: vrfRouterLtd.status.dnsCache.infiniteTimeOut

       Possibilities:
               disabled   (0)
               enabled   (1)
               static   (2)"
   ::= {sr1646v2VrfLtdDnsCacheEntry 67108864}

sr1646v2VrfLtdDnsCacheMatches OBJECT-TYPE
   SYNTAX      Counter32
   MAX-ACCESS  read-only
   STATUS      current
   DESCRIPTION
      "Path: vrfRouterLtd.status.dnsCache.matches

       32 bit unsigned wrappable counter."
   ::= {sr1646v2VrfLtdDnsCacheEntry 100663296}


sr1646v2VrfLtdDnsServers OBJECT IDENTIFIER ::= {sr1646v2VrfLtd 66}

sr1646v2VrfLtdDnsServersSSCTable OBJECT-TYPE
   SYNTAX      SEQUENCE OF Sr1646v2VrfLtdDnsServersEntry
   MAX-ACCESS  not-accessible
   STATUS      current
   DESCRIPTION
      "DNS server list"
   ::= {sr1646v2VrfLtdDnsServers 1}

sr1646v2VrfLtdDnsServersEntry OBJECT-TYPE
   SYNTAX      Sr1646v2VrfLtdDnsServersEntry
   MAX-ACCESS  not-accessible
   STATUS      current
   DESCRIPTION
      ""
   INDEX      { sr1646v2VrfLtdDnsServersGlobalIx,
                sr1646v2VrfLtdDnsServersTableIx }
   ::= {sr1646v2VrfLtdDnsServersSSCTable 1}

Sr1646v2VrfLtdDnsServersEntry ::=
   SEQUENCE
      {
      sr1646v2VrfLtdDnsServersGlobalIx
         GlobalIndex,
      sr1646v2VrfLtdDnsServersTableIx
         TableIndex,
      sr1646v2VrfLtdDnsServersPrimaryDns
         IpAddress,
      sr1646v2VrfLtdDnsServersSecondaryDns
         IpAddress,
      sr1646v2VrfLtdDnsServersType
         INTEGER,
      sr1646v2VrfLtdDnsServersRcvdInterface
         DisplayString,
      sr1646v2VrfLtdDnsServersPreference
         Integer32,
      sr1646v2VrfLtdDnsServersStatus
         INTEGER
      }

sr1646v2VrfLtdDnsServersGlobalIx OBJECT-TYPE
   SYNTAX      GlobalIndex
   MAX-ACCESS  not-accessible
   STATUS      current
   DESCRIPTION
      "The value of the tlsCntTreeGlobalIndex of the MANAGED OBJECT."
   ::= {sr1646v2VrfLtdDnsServersEntry 10}

sr1646v2VrfLtdDnsServersTableIx OBJECT-TYPE
   SYNTAX      TableIndex
   MAX-ACCESS  not-accessible
   STATUS      current
   DESCRIPTION
      ""
   ::= {sr1646v2VrfLtdDnsServersEntry 11}

sr1646v2VrfLtdDnsServersPrimaryDns OBJECT-TYPE
   SYNTAX      IpAddress
   MAX-ACCESS  read-only
   STATUS      current
   DESCRIPTION
      "Path: vrfRouterLtd.status.dnsServers.primaryDns"
   ::= {sr1646v2VrfLtdDnsServersEntry 16777216}

sr1646v2VrfLtdDnsServersSecondaryDns OBJECT-TYPE
   SYNTAX      IpAddress
   MAX-ACCESS  read-only
   STATUS      current
   DESCRIPTION
      "Path: vrfRouterLtd.status.dnsServers.secondaryDns"
   ::= {sr1646v2VrfLtdDnsServersEntry 33554432}

sr1646v2VrfLtdDnsServersType OBJECT-TYPE
   SYNTAX      INTEGER
               {
               static (0),
               dhcp (1),
               ppp (2)
               }
   MAX-ACCESS  read-only
   STATUS      current
   DESCRIPTION
      "Path: vrfRouterLtd.status.dnsServers.type

       Possibilities:
               static   (0)
               dhcp   (1)
               ppp   (2)"
   ::= {sr1646v2VrfLtdDnsServersEntry 50331648}

sr1646v2VrfLtdDnsServersRcvdInterface OBJECT-TYPE
   SYNTAX      DisplayString
   MAX-ACCESS  read-only
   STATUS      current
   DESCRIPTION
      "Path: vrfRouterLtd.status.dnsServers.rcvdInterface"
   ::= {sr1646v2VrfLtdDnsServersEntry 67108864}

sr1646v2VrfLtdDnsServersPreference OBJECT-TYPE
   SYNTAX      Integer32
   MAX-ACCESS  read-only
   STATUS      current
   DESCRIPTION
      "Path: vrfRouterLtd.status.dnsServers.preference"
   ::= {sr1646v2VrfLtdDnsServersEntry 83886080}

sr1646v2VrfLtdDnsServersStatus OBJECT-TYPE
   SYNTAX      INTEGER
               {
               primActive (2),
               secActive (3),
               inactive (5),
               failed (6)
               }
   MAX-ACCESS  read-only
   STATUS      current
   DESCRIPTION
      "Path: vrfRouterLtd.status.dnsServers.status

       Possibilities:
               primActive   (2)
               secActive   (3)
               inactive   (5)
               failed   (6)"
   ::= {sr1646v2VrfLtdDnsServersEntry 100663296}


sr1646v2VrfLtdDnsDomains OBJECT IDENTIFIER ::= {sr1646v2VrfLtd 72}

sr1646v2VrfLtdDnsDomainsSSCTable OBJECT-TYPE
   SYNTAX      SEQUENCE OF Sr1646v2VrfLtdDnsDomainsEntry
   MAX-ACCESS  not-accessible
   STATUS      current
   DESCRIPTION
      "DNS domain table"
   ::= {sr1646v2VrfLtdDnsDomains 1}

sr1646v2VrfLtdDnsDomainsEntry OBJECT-TYPE
   SYNTAX      Sr1646v2VrfLtdDnsDomainsEntry
   MAX-ACCESS  not-accessible
   STATUS      current
   DESCRIPTION
      ""
   INDEX      { sr1646v2VrfLtdDnsDomainsGlobalIx,
                sr1646v2VrfLtdDnsDomainsTableIx }
   ::= {sr1646v2VrfLtdDnsDomainsSSCTable 1}

Sr1646v2VrfLtdDnsDomainsEntry ::=
   SEQUENCE
      {
      sr1646v2VrfLtdDnsDomainsGlobalIx
         GlobalIndex,
      sr1646v2VrfLtdDnsDomainsTableIx
         TableIndex,
      sr1646v2VrfLtdDnsDomainsName
         DisplayString,
      sr1646v2VrfLtdDnsDomainsType
         INTEGER,
      sr1646v2VrfLtdDnsDomainsRcvdInterface
         DisplayString
      }

sr1646v2VrfLtdDnsDomainsGlobalIx OBJECT-TYPE
   SYNTAX      GlobalIndex
   MAX-ACCESS  not-accessible
   STATUS      current
   DESCRIPTION
      "The value of the tlsCntTreeGlobalIndex of the MANAGED OBJECT."
   ::= {sr1646v2VrfLtdDnsDomainsEntry 10}

sr1646v2VrfLtdDnsDomainsTableIx OBJECT-TYPE
   SYNTAX      TableIndex
   MAX-ACCESS  not-accessible
   STATUS      current
   DESCRIPTION
      ""
   ::= {sr1646v2VrfLtdDnsDomainsEntry 11}

sr1646v2VrfLtdDnsDomainsName OBJECT-TYPE
   SYNTAX      DisplayString
   MAX-ACCESS  read-only
   STATUS      current
   DESCRIPTION
      "Path: vrfRouterLtd.status.dnsDomains.name"
   ::= {sr1646v2VrfLtdDnsDomainsEntry 16777216}

sr1646v2VrfLtdDnsDomainsType OBJECT-TYPE
   SYNTAX      INTEGER
               {
               static (0),
               dhcp (1),
               ppp (2)
               }
   MAX-ACCESS  read-only
   STATUS      current
   DESCRIPTION
      "Path: vrfRouterLtd.status.dnsDomains.type

       Possibilities:
               static   (0)
               dhcp   (1)
               ppp   (2)"
   ::= {sr1646v2VrfLtdDnsDomainsEntry 33554432}

sr1646v2VrfLtdDnsDomainsRcvdInterface OBJECT-TYPE
   SYNTAX      DisplayString
   MAX-ACCESS  read-only
   STATUS      current
   DESCRIPTION
      "Path: vrfRouterLtd.status.dnsDomains.rcvdInterface"
   ::= {sr1646v2VrfLtdDnsDomainsEntry 50331648}


sr1646v2VrfLtdIgmpTable OBJECT IDENTIFIER ::= {sr1646v2VrfLtd 58}

sr1646v2VrfLtdIgmpTableSSCTable OBJECT-TYPE
   SYNTAX      SEQUENCE OF Sr1646v2VrfLtdIgmpTableEntry
   MAX-ACCESS  not-accessible
   STATUS      current
   DESCRIPTION
      "igmpTable"
   ::= {sr1646v2VrfLtdIgmpTable 1}

sr1646v2VrfLtdIgmpTableEntry OBJECT-TYPE
   SYNTAX      Sr1646v2VrfLtdIgmpTableEntry
   MAX-ACCESS  not-accessible
   STATUS      current
   DESCRIPTION
      ""
   INDEX      { sr1646v2VrfLtdIgmpTableGlobalIx,
                sr1646v2VrfLtdIgmpTableTableIx }
   ::= {sr1646v2VrfLtdIgmpTableSSCTable 1}

Sr1646v2VrfLtdIgmpTableEntry ::=
   SEQUENCE
      {
      sr1646v2VrfLtdIgmpTableGlobalIx
         GlobalIndex,
      sr1646v2VrfLtdIgmpTableTableIx
         TableIndex,
      sr1646v2VrfLtdIgmpTableMulticast
         IpAddress,
      sr1646v2VrfLtdIgmpTableMembers
         Integer32,
      sr1646v2VrfLtdIgmpTableIf
         DisplayString,
      sr1646v2VrfLtdIgmpTableSourceRecordType
         INTEGER
      }

sr1646v2VrfLtdIgmpTableGlobalIx OBJECT-TYPE
   SYNTAX      GlobalIndex
   MAX-ACCESS  not-accessible
   STATUS      current
   DESCRIPTION
      "The value of the tlsCntTreeGlobalIndex of the MANAGED OBJECT."
   ::= {sr1646v2VrfLtdIgmpTableEntry 10}

sr1646v2VrfLtdIgmpTableTableIx OBJECT-TYPE
   SYNTAX      TableIndex
   MAX-ACCESS  not-accessible
   STATUS      current
   DESCRIPTION
      ""
   ::= {sr1646v2VrfLtdIgmpTableEntry 11}

sr1646v2VrfLtdIgmpTableMulticast OBJECT-TYPE
   SYNTAX      IpAddress
   MAX-ACCESS  read-only
   STATUS      current
   DESCRIPTION
      "Path: vrfRouterLtd.status.igmpTable.multicast"
   ::= {sr1646v2VrfLtdIgmpTableEntry 16777216}

sr1646v2VrfLtdIgmpTableMembers OBJECT-TYPE
   SYNTAX      Integer32
   MAX-ACCESS  read-only
   STATUS      current
   DESCRIPTION
      "Path: vrfRouterLtd.status.igmpTable.members"
   ::= {sr1646v2VrfLtdIgmpTableEntry 50331648}

sr1646v2VrfLtdIgmpTableIf OBJECT-TYPE
   SYNTAX      DisplayString
   MAX-ACCESS  read-only
   STATUS      current
   DESCRIPTION
      "Path: vrfRouterLtd.status.igmpTable.interface"
   ::= {sr1646v2VrfLtdIgmpTableEntry 33554432}

sr1646v2VrfLtdIgmpTableSourceRecordType OBJECT-TYPE
   SYNTAX      INTEGER
               {
               exclude (1),
               include (0)
               }
   MAX-ACCESS  read-only
   STATUS      current
   DESCRIPTION
      "Path: vrfRouterLtd.status.igmpTable.sourceRecordType

       Possibilities:
               exclude   (1)
               include   (0)"
   ::= {sr1646v2VrfLtdIgmpTableEntry 83886080}

sr1646v2VrfLtdIgmpTableSourceRecord OBJECT-TYPE
   SYNTAX      SEQUENCE OF Sr1646v2VrfLtdIgmpTableSourceRecordEntry
   MAX-ACCESS  not-accessible
   STATUS      current
   DESCRIPTION
      ""
   ::= {sr1646v2VrfLtdIgmpTable 67108864}

sr1646v2VrfLtdIgmpTableSourceRecordEntry OBJECT-TYPE
   SYNTAX      Sr1646v2VrfLtdIgmpTableSourceRecordEntry
   MAX-ACCESS  not-accessible
   STATUS      current
   DESCRIPTION
      ""
   INDEX      { sr1646v2VrfLtdIgmpTableSourceRecordGlobalIx,
                sr1646v2VrfLtdIgmpTableTableIx,
                sr1646v2VrfLtdIgmpTableSourceRecordTableIx }
   ::= {sr1646v2VrfLtdIgmpTableSourceRecord 1}

Sr1646v2VrfLtdIgmpTableSourceRecordEntry ::=
   SEQUENCE
      {
      sr1646v2VrfLtdIgmpTableSourceRecordGlobalIx
         GlobalIndex,
      sr1646v2VrfLtdIgmpTableSourceRecordTableIx
         TableIndex,
      sr1646v2VrfLtdIgmpTableSourceRecordIpAddress
         IpAddress
      }

sr1646v2VrfLtdIgmpTableSourceRecordGlobalIx OBJECT-TYPE
   SYNTAX      GlobalIndex
   MAX-ACCESS  not-accessible
   STATUS      current
   DESCRIPTION
      "The value of the tlsCntTreeGlobalIndex of the MANAGED OBJECT."
   ::= {sr1646v2VrfLtdIgmpTableSourceRecordEntry 10}

sr1646v2VrfLtdIgmpTableSourceRecordTableIx OBJECT-TYPE
   SYNTAX      TableIndex
   MAX-ACCESS  not-accessible
   STATUS      current
   DESCRIPTION
      ""
   ::= {sr1646v2VrfLtdIgmpTableSourceRecordEntry 11}

sr1646v2VrfLtdIgmpTableSourceRecordIpAddress OBJECT-TYPE
   SYNTAX      IpAddress
   MAX-ACCESS  read-only
   STATUS      current
   DESCRIPTION
      "Path: vrfRouterLtd.status.igmpTable.sourceRecord.ipAddress"
   ::= {sr1646v2VrfLtdIgmpTableSourceRecordEntry 16777216}


sr1646v2VrfLtdInterfaces OBJECT IDENTIFIER ::= {sr1646v2VrfLtd 199}

sr1646v2VrfLtdInterfacesSSCTable OBJECT-TYPE
   SYNTAX      SEQUENCE OF Sr1646v2VrfLtdInterfacesEntry
   MAX-ACCESS  not-accessible
   STATUS      current
   DESCRIPTION
      "info on routing interfaces"
   ::= {sr1646v2VrfLtdInterfaces 1}

sr1646v2VrfLtdInterfacesEntry OBJECT-TYPE
   SYNTAX      Sr1646v2VrfLtdInterfacesEntry
   MAX-ACCESS  not-accessible
   STATUS      current
   DESCRIPTION
      ""
   INDEX      { sr1646v2VrfLtdInterfacesGlobalIx,
                sr1646v2VrfLtdInterfacesTableIx }
   ::= {sr1646v2VrfLtdInterfacesSSCTable 1}

Sr1646v2VrfLtdInterfacesEntry ::=
   SEQUENCE
      {
      sr1646v2VrfLtdInterfacesGlobalIx
         GlobalIndex,
      sr1646v2VrfLtdInterfacesTableIx
         TableIndex,
      sr1646v2VrfLtdInterfacesIfDescr
         DisplayString,
      sr1646v2VrfLtdInterfacesIfType
         INTEGER,
      sr1646v2VrfLtdInterfacesIfOperStatus
         INTEGER,
      sr1646v2VrfLtdInterfacesIfLastChange
         TimeTicks,
      sr1646v2VrfLtdInterfacesIfLastChangeDate
         DisplayString,
      sr1646v2VrfLtdInterfacesAddress
         IpAddress,
      sr1646v2VrfLtdInterfacesMask
         IpAddress
      }

sr1646v2VrfLtdInterfacesGlobalIx OBJECT-TYPE
   SYNTAX      GlobalIndex
   MAX-ACCESS  not-accessible
   STATUS      current
   DESCRIPTION
      "The value of the tlsCntTreeGlobalIndex of the MANAGED OBJECT."
   ::= {sr1646v2VrfLtdInterfacesEntry 10}

sr1646v2VrfLtdInterfacesTableIx OBJECT-TYPE
   SYNTAX      TableIndex
   MAX-ACCESS  not-accessible
   STATUS      current
   DESCRIPTION
      ""
   ::= {sr1646v2VrfLtdInterfacesEntry 11}

sr1646v2VrfLtdInterfacesIfDescr OBJECT-TYPE
   SYNTAX      DisplayString
   MAX-ACCESS  read-only
   STATUS      current
   DESCRIPTION
      "Path: vrfRouterLtd.status.interfaces.ifDescr"
   ::= {sr1646v2VrfLtdInterfacesEntry 1694498816}

sr1646v2VrfLtdInterfacesIfType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: vrfRouterLtd.status.interfaces.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2VrfLtdInterfacesEntry 1711276032}

sr1646v2VrfLtdInterfacesIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: vrfRouterLtd.status.interfaces.ifOperStatus

       Possibilities:
               up   (1)
               down   (2)
               testing   (3)
               unknown   (4)
               dormant   (5)
               notPresent   (6)
               lowerLayerDown   (7)"
   ::= {sr1646v2VrfLtdInterfacesEntry 1795162112}

sr1646v2VrfLtdInterfacesIfLastChange OBJECT-TYPE
   SYNTAX      TimeTicks
   MAX-ACCESS  read-only
   STATUS      current
   DESCRIPTION
      "Path: vrfRouterLtd.status.interfaces.ifLastChange

       Time in centi-second."
   ::= {sr1646v2VrfLtdInterfacesEntry 1811939328}

sr1646v2VrfLtdInterfacesIfLastChangeDate OBJECT-TYPE
   SYNTAX      DisplayString
   MAX-ACCESS  read-only
   STATUS      current
   DESCRIPTION
      "Path: vrfRouterLtd.status.interfaces.ifLastChangeDate"
   ::= {sr1646v2VrfLtdInterfacesEntry 3070230528}

sr1646v2VrfLtdInterfacesAddress OBJECT-TYPE
   SYNTAX      IpAddress
   MAX-ACCESS  read-only
   STATUS      current
   DESCRIPTION
      "Path: vrfRouterLtd.status.interfaces.address"
   ::= {sr1646v2VrfLtdInterfacesEntry 2030043136}

sr1646v2VrfLtdInterfacesMask OBJECT-TYPE
   SYNTAX      IpAddress
   MAX-ACCESS  read-only
   STATUS      current
   DESCRIPTION
      "Path: vrfRouterLtd.status.interfaces.mask"
   ::= {sr1646v2VrfLtdInterfacesEntry 2063597568}

sr1646v2VrfLtdInterfacesSecondaryIp OBJECT-TYPE
   SYNTAX      SEQUENCE OF Sr1646v2VrfLtdInterfacesSecondaryIpEntry
   MAX-ACCESS  not-accessible
   STATUS      current
   DESCRIPTION
      ""
   ::= {sr1646v2VrfLtdInterfaces 385875968}

sr1646v2VrfLtdInterfacesSecondaryIpEntry OBJECT-TYPE
   SYNTAX      Sr1646v2VrfLtdInterfacesSecondaryIpEntry
   MAX-ACCESS  not-accessible
   STATUS      current
   DESCRIPTION
      ""
   INDEX      { sr1646v2VrfLtdInterfacesSecondaryIpGlobalIx,
                sr1646v2VrfLtdInterfacesTableIx,
                sr1646v2VrfLtdInterfacesSecondaryIpTableIx }
   ::= {sr1646v2VrfLtdInterfacesSecondaryIp 1}

Sr1646v2VrfLtdInterfacesSecondaryIpEntry ::=
   SEQUENCE
      {
      sr1646v2VrfLtdInterfacesSecondaryIpGlobalIx
         GlobalIndex,
      sr1646v2VrfLtdInterfacesSecondaryIpTableIx
         TableIndex,
      sr1646v2VrfLtdInterfacesSecondaryIpAddress
         IpAddress,
      sr1646v2VrfLtdInterfacesSecondaryIpNetMask
         IpAddress
      }

sr1646v2VrfLtdInterfacesSecondaryIpGlobalIx OBJECT-TYPE
   SYNTAX      GlobalIndex
   MAX-ACCESS  not-accessible
   STATUS      current
   DESCRIPTION
      "The value of the tlsCntTreeGlobalIndex of the MANAGED OBJECT."
   ::= {sr1646v2VrfLtdInterfacesSecondaryIpEntry 10}

sr1646v2VrfLtdInterfacesSecondaryIpTableIx OBJECT-TYPE
   SYNTAX      TableIndex
   MAX-ACCESS  not-accessible
   STATUS      current
   DESCRIPTION
      ""
   ::= {sr1646v2VrfLtdInterfacesSecondaryIpEntry 11}

sr1646v2VrfLtdInterfacesSecondaryIpAddress OBJECT-TYPE
   SYNTAX      IpAddress
   MAX-ACCESS  read-only
   STATUS      current
   DESCRIPTION
      "Path: vrfRouterLtd.status.interfaces.secondaryIp.address"
   ::= {sr1646v2VrfLtdInterfacesSecondaryIpEntry 2030043136}

sr1646v2VrfLtdInterfacesSecondaryIpNetMask OBJECT-TYPE
   SYNTAX      IpAddress
   MAX-ACCESS  read-only
   STATUS      current
   DESCRIPTION
      "Path: vrfRouterLtd.status.interfaces.secondaryIp.netMask"
   ::= {sr1646v2VrfLtdInterfacesSecondaryIpEntry 2063597568}



pr1646v2VrfLtd OBJECT IDENTIFIER ::= {r1646v2VrfLtd 12}


pr1646v2VrfLtdRoutingTable OBJECT IDENTIFIER ::= {pr1646v2VrfLtd 33}

pr1646v2VrfLtdRoutingTableSSCTable OBJECT-TYPE
   SYNTAX      SEQUENCE OF Pr1646v2VrfLtdRoutingTableEntry
   MAX-ACCESS  not-accessible
   STATUS      current
   DESCRIPTION
      "routingTable"
   ::= {pr1646v2VrfLtdRoutingTable 1}

pr1646v2VrfLtdRoutingTableEntry OBJECT-TYPE
   SYNTAX      Pr1646v2VrfLtdRoutingTableEntry
   MAX-ACCESS  not-accessible
   STATUS      current
   DESCRIPTION
      ""
   INDEX      { pr1646v2VrfLtdRoutingTableGlobalIx,
                pr1646v2VrfLtdRoutingTableTableIx }
   ::= {pr1646v2VrfLtdRoutingTableSSCTable 1}

Pr1646v2VrfLtdRoutingTableEntry ::=
   SEQUENCE
      {
      pr1646v2VrfLtdRoutingTableGlobalIx
         GlobalIndex,
      pr1646v2VrfLtdRoutingTableTableIx
         TableIndex,
      pr1646v2VrfLtdRoutingTableNetwork
         IpAddress,
      pr1646v2VrfLtdRoutingTableMask
         IpAddress,
      pr1646v2VrfLtdRoutingTableGateway
         IpAddress,
      pr1646v2VrfLtdRoutingTableIf
         DisplayString,
      pr1646v2VrfLtdRoutingTableUses
         Gauge32,
      pr1646v2VrfLtdRoutingTableOctets
         Gauge32
      }

pr1646v2VrfLtdRoutingTableGlobalIx OBJECT-TYPE
   SYNTAX      GlobalIndex
   MAX-ACCESS  not-accessible
   STATUS      current
   DESCRIPTION
      "The value of the tlsCntTreeGlobalIndex of the MANAGED OBJECT."
   ::= {pr1646v2VrfLtdRoutingTableEntry 10}

pr1646v2VrfLtdRoutingTableTableIx OBJECT-TYPE
   SYNTAX      TableIndex
   MAX-ACCESS  not-accessible
   STATUS      current
   DESCRIPTION
      ""
   ::= {pr1646v2VrfLtdRoutingTableEntry 11}

pr1646v2VrfLtdRoutingTableNetwork OBJECT-TYPE
   SYNTAX      IpAddress
   MAX-ACCESS  read-only
   STATUS      current
   DESCRIPTION
      "Path: vrfRouterLtd.performance.routingTable.network"
   ::= {pr1646v2VrfLtdRoutingTableEntry 16777216}

pr1646v2VrfLtdRoutingTableMask OBJECT-TYPE
   SYNTAX      IpAddress
   MAX-ACCESS  read-only
   STATUS      current
   DESCRIPTION
      "Path: vrfRouterLtd.performance.routingTable.mask"
   ::= {pr1646v2VrfLtdRoutingTableEntry 33554432}

pr1646v2VrfLtdRoutingTableGateway OBJECT-TYPE
   SYNTAX      IpAddress
   MAX-ACCESS  read-only
   STATUS      current
   DESCRIPTION
      "Path: vrfRouterLtd.performance.routingTable.gateway"
   ::= {pr1646v2VrfLtdRoutingTableEntry 50331648}

pr1646v2VrfLtdRoutingTableIf OBJECT-TYPE
   SYNTAX      DisplayString
   MAX-ACCESS  read-only
   STATUS      current
   DESCRIPTION
      "Path: vrfRouterLtd.performance.routingTable.interface"
   ::= {pr1646v2VrfLtdRoutingTableEntry 67108864}

pr1646v2VrfLtdRoutingTableUses OBJECT-TYPE
   SYNTAX      Gauge32
   MAX-ACCESS  read-only
   STATUS      current
   DESCRIPTION
      "Path: vrfRouterLtd.performance.routingTable.uses

       32 bit unsigned gauge value."
   ::= {pr1646v2VrfLtdRoutingTableEntry 83886080}

pr1646v2VrfLtdRoutingTableOctets OBJECT-TYPE
   SYNTAX      Gauge32
   MAX-ACCESS  read-only
   STATUS      current
   DESCRIPTION
      "Path: vrfRouterLtd.performance.routingTable.octets

       32 bit unsigned gauge value."
   ::= {pr1646v2VrfLtdRoutingTableEntry 100663296}


pr1646v2VrfLtdPingResults OBJECT IDENTIFIER ::= {pr1646v2VrfLtd 46}

pr1646v2VrfLtdPingResultsSSCTable OBJECT-TYPE
   SYNTAX      SEQUENCE OF Pr1646v2VrfLtdPingResultsEntry
   MAX-ACCESS  not-accessible
   STATUS      current
   DESCRIPTION
      "ping statistics"
   ::= {pr1646v2VrfLtdPingResults 1}

pr1646v2VrfLtdPingResultsEntry OBJECT-TYPE
   SYNTAX      Pr1646v2VrfLtdPingResultsEntry
   MAX-ACCESS  not-accessible
   STATUS      current
   DESCRIPTION
      ""
   INDEX      { pr1646v2VrfLtdPingResultsGlobalIx }
   ::= {pr1646v2VrfLtdPingResultsSSCTable 1}

Pr1646v2VrfLtdPingResultsEntry ::=
   SEQUENCE
      {
      pr1646v2VrfLtdPingResultsGlobalIx
         GlobalIndex,
      pr1646v2VrfLtdPingResultsIpAddr
         IpAddress,
      pr1646v2VrfLtdPingResultsNbrTxPckt
         Counter32,
      pr1646v2VrfLtdPingResultsNbrRxPckt
         Counter32,
      pr1646v2VrfLtdPingResultsRepTimMin
         TimeTicks,
      pr1646v2VrfLtdPingResultsRepTimMax
         TimeTicks,
      pr1646v2VrfLtdPingResultsRepTimAvrg
         TimeTicks,
      pr1646v2VrfLtdPingResultsLastError
         DisplayString
      }

pr1646v2VrfLtdPingResultsGlobalIx OBJECT-TYPE
   SYNTAX      GlobalIndex
   MAX-ACCESS  not-accessible
   STATUS      current
   DESCRIPTION
      "The value of the tlsCntTreeGlobalIndex of the MANAGED OBJECT."
   ::= {pr1646v2VrfLtdPingResultsEntry 10}

pr1646v2VrfLtdPingResultsIpAddr OBJECT-TYPE
   SYNTAX      IpAddress
   MAX-ACCESS  read-only
   STATUS      current
   DESCRIPTION
      "Path: vrfRouterLtd.performance.pingResults.ipAddress"
   ::= {pr1646v2VrfLtdPingResultsEntry 16777216}

pr1646v2VrfLtdPingResultsNbrTxPckt OBJECT-TYPE
   SYNTAX      Counter32
   MAX-ACCESS  read-only
   STATUS      current
   DESCRIPTION
      "Path: vrfRouterLtd.performance.pingResults.numOfTxPackets

       32 bit unsigned wrappable counter."
   ::= {pr1646v2VrfLtdPingResultsEntry 33554432}

pr1646v2VrfLtdPingResultsNbrRxPckt OBJECT-TYPE
   SYNTAX      Counter32
   MAX-ACCESS  read-only
   STATUS      current
   DESCRIPTION
      "Path: vrfRouterLtd.performance.pingResults.numOfRxPackets

       32 bit unsigned wrappable counter."
   ::= {pr1646v2VrfLtdPingResultsEntry 50331648}

pr1646v2VrfLtdPingResultsRepTimMin OBJECT-TYPE
   SYNTAX      TimeTicks
   MAX-ACCESS  read-only
   STATUS      current
   DESCRIPTION
      "Path: vrfRouterLtd.performance.pingResults.replyTimeMin

       Time in centi-second."
   ::= {pr1646v2VrfLtdPingResultsEntry 67108864}

pr1646v2VrfLtdPingResultsRepTimMax OBJECT-TYPE
   SYNTAX      TimeTicks
   MAX-ACCESS  read-only
   STATUS      current
   DESCRIPTION
      "Path: vrfRouterLtd.performance.pingResults.replyTimeMax

       Time in centi-second."
   ::= {pr1646v2VrfLtdPingResultsEntry 83886080}

pr1646v2VrfLtdPingResultsRepTimAvrg OBJECT-TYPE
   SYNTAX      TimeTicks
   MAX-ACCESS  read-only
   STATUS      current
   DESCRIPTION
      "Path: vrfRouterLtd.performance.pingResults.replyTimeAvrg

       Time in centi-second."
   ::= {pr1646v2VrfLtdPingResultsEntry 100663296}

pr1646v2VrfLtdPingResultsLastError OBJECT-TYPE
   SYNTAX      DisplayString
   MAX-ACCESS  read-only
   STATUS      current
   DESCRIPTION
      "Path: vrfRouterLtd.performance.pingResults.lastError"
   ::= {pr1646v2VrfLtdPingResultsEntry 117440512}


pr1646v2VrfLtdQm OBJECT IDENTIFIER ::= {pr1646v2VrfLtd 79}

pr1646v2VrfLtdQmSSCTable OBJECT-TYPE
   SYNTAX      SEQUENCE OF Pr1646v2VrfLtdQmEntry
   MAX-ACCESS  not-accessible
   STATUS      current
   DESCRIPTION
      "quality monitor"
   ::= {pr1646v2VrfLtdQm 1}

pr1646v2VrfLtdQmEntry OBJECT-TYPE
   SYNTAX      Pr1646v2VrfLtdQmEntry
   MAX-ACCESS  not-accessible
   STATUS      current
   DESCRIPTION
      ""
   INDEX      { pr1646v2VrfLtdQmGlobalIx,
                pr1646v2VrfLtdQmTableIx }
   ::= {pr1646v2VrfLtdQmSSCTable 1}

Pr1646v2VrfLtdQmEntry ::=
   SEQUENCE
      {
      pr1646v2VrfLtdQmGlobalIx
         GlobalIndex,
      pr1646v2VrfLtdQmTableIx
         TableIndex,
      pr1646v2VrfLtdQmName
         DisplayString,
      pr1646v2VrfLtdQmStatus
         INTEGER,
      pr1646v2VrfLtdQmIpAddress
         IpAddress,
      pr1646v2VrfLtdQmHostName
         DisplayString,
      pr1646v2VrfLtdQmSourceIp
         IpAddress,
      pr1646v2VrfLtdQmSourceId
         Gauge32,
      pr1646v2VrfLtdQmNbrTxPckt
         Counter32,
      pr1646v2VrfLtdQmNbrRxPckt
         Counter32,
      pr1646v2VrfLtdQmError
         Counter32,
      pr1646v2VrfLtdQmDelay
         Integer32,
      pr1646v2VrfLtdQmJitter
         Integer32,
      pr1646v2VrfLtdQmLoss
         Counter32,
      pr1646v2VrfLtdQmLossDelay
         Counter32,
      pr1646v2VrfLtdQmDelayMin
         Integer32,
      pr1646v2VrfLtdQmDelayAvrg
         Integer32,
      pr1646v2VrfLtdQmDelayMax
         Integer32,
      pr1646v2VrfLtdQmDelayBinsType
         INTEGER,
      pr1646v2VrfLtdQmDelayBinsMinMin
         Counter32,
      pr1646v2VrfLtdQmDelayBinsMin
         Integer32,
      pr1646v2VrfLtdQmDelayBinsMinBin1
         Counter32,
      pr1646v2VrfLtdQmDelayBinsBin2
         Counter32,
      pr1646v2VrfLtdQmDelayBinsBin3
         Counter32,
      pr1646v2VrfLtdQmDelayBinsBin4
         Counter32,
      pr1646v2VrfLtdQmDelayBinsBin5
         Counter32,
      pr1646v2VrfLtdQmDelayBinsBin6
         Counter32,
      pr1646v2VrfLtdQmDelayBinsBin7
         Counter32,
      pr1646v2VrfLtdQmDelayBinsMaxBin8
         Counter32,
      pr1646v2VrfLtdQmDelayBinsMax
         Integer32,
      pr1646v2VrfLtdQmDelayBinsPlusMax
         Counter32,
      pr1646v2VrfLtdQmJitterNegMax
         Integer32,
      pr1646v2VrfLtdQmJitterAvrg
         Integer32,
      pr1646v2VrfLtdQmJitterPosMax
         Integer32,
      pr1646v2VrfLtdQmJitterBinsType
         INTEGER,
      pr1646v2VrfLtdQmJitterBinsMinMin
         Counter32,
      pr1646v2VrfLtdQmJitterBinsMin
         Integer32,
      pr1646v2VrfLtdQmJitterBinsMinBin1
         Counter32,
      pr1646v2VrfLtdQmJitterBinsBin2
         Counter32,
      pr1646v2VrfLtdQmJitterBinsBin3
         Counter32,
      pr1646v2VrfLtdQmJitterBinsBin4
         Counter32,
      pr1646v2VrfLtdQmJitterBinsBin5
         Counter32,
      pr1646v2VrfLtdQmJitterBinsBin6
         Counter32,
      pr1646v2VrfLtdQmJitterBinsBin7
         Counter32,
      pr1646v2VrfLtdQmJitterBinsMaxBin8
         Counter32,
      pr1646v2VrfLtdQmJitterBinsMax
         Integer32,
      pr1646v2VrfLtdQmJitterBinsPlusMax
         Counter32,
      pr1646v2VrfLtdQmBfdCtrlOutPkts
         Integer32,
      pr1646v2VrfLtdQmBfdCtrlInPkts
         Integer32,
      pr1646v2VrfLtdQmBfdCtrlLocalState
         INTEGER,
      pr1646v2VrfLtdQmBfdCtrlLocalDiscriminator
         Integer32,
      pr1646v2VrfLtdQmBfdCtrlLocalTxInterval
         Integer32,
      pr1646v2VrfLtdQmBfdCtrlLocalMinTxInterval
         Integer32,
      pr1646v2VrfLtdQmBfdCtrlLocalDetectMultiplier
         Integer32,
      pr1646v2VrfLtdQmBfdCtrlRemoteState
         INTEGER,
      pr1646v2VrfLtdQmBfdCtrlRemoteDiscriminator
         Integer32,
      pr1646v2VrfLtdQmBfdCtrlRemoteMinTxInterval
         Integer32,
      pr1646v2VrfLtdQmBfdCtrlRemoteDetectMultiplier
         Integer32,
      pr1646v2VrfLtdQmBfdCtrlRemoteMinRxInterval
         Integer32,
      pr1646v2VrfLtdQmBfdCtrlRemoteMinRxEchoInterval
         Integer32,
      pr1646v2VrfLtdQmUpDownStatus
         INTEGER,
      pr1646v2VrfLtdQmUpDownLossUp
         Counter32,
      pr1646v2VrfLtdQmUpDownLossDelayUp
         Counter32,
      pr1646v2VrfLtdQmUpDownDelayUpMin
         Integer32,
      pr1646v2VrfLtdQmUpDownDelayUpAvrg
         Integer32,
      pr1646v2VrfLtdQmUpDownDelayUpMax
         Integer32,
      pr1646v2VrfLtdQmUpDownDelayUpBinsType
         INTEGER,
      pr1646v2VrfLtdQmUpDownDelayUpBinsMinMin
         Counter32,
      pr1646v2VrfLtdQmUpDownDelayUpBinsMin
         Integer32,
      pr1646v2VrfLtdQmUpDownDelayUpBinsMinBin1
         Counter32,
      pr1646v2VrfLtdQmUpDownDelayUpBinsBin2
         Counter32,
      pr1646v2VrfLtdQmUpDownDelayUpBinsBin3
         Counter32,
      pr1646v2VrfLtdQmUpDownDelayUpBinsBin4
         Counter32,
      pr1646v2VrfLtdQmUpDownDelayUpBinsBin5
         Counter32,
      pr1646v2VrfLtdQmUpDownDelayUpBinsBin6
         Counter32,
      pr1646v2VrfLtdQmUpDownDelayUpBinsBin7
         Counter32,
      pr1646v2VrfLtdQmUpDownDelayUpBinsMaxBin8
         Counter32,
      pr1646v2VrfLtdQmUpDownDelayUpBinsMax
         Integer32,
      pr1646v2VrfLtdQmUpDownDelayUpBinsPlusMax
         Counter32,
      pr1646v2VrfLtdQmUpDownJitterUp
         Integer32,
      pr1646v2VrfLtdQmUpDownJitterUpNegMax
         Integer32,
      pr1646v2VrfLtdQmUpDownJitterUpAvrg
         Integer32,
      pr1646v2VrfLtdQmUpDownJitterUpPosMax
         Integer32,
      pr1646v2VrfLtdQmUpDownJitterUpBinsType
         INTEGER,
      pr1646v2VrfLtdQmUpDownJitterUpBinsMinMin
         Counter32,
      pr1646v2VrfLtdQmUpDownJitterUpBinsMin
         Integer32,
      pr1646v2VrfLtdQmUpDownJitterUpBinsMinBin1
         Counter32,
      pr1646v2VrfLtdQmUpDownJitterUpBinsBin2
         Counter32,
      pr1646v2VrfLtdQmUpDownJitterUpBinsBin3
         Counter32,
      pr1646v2VrfLtdQmUpDownJitterUpBinsBin4
         Counter32,
      pr1646v2VrfLtdQmUpDownJitterUpBinsBin5
         Counter32,
      pr1646v2VrfLtdQmUpDownJitterUpBinsBin6
         Counter32,
      pr1646v2VrfLtdQmUpDownJitterUpBinsBin7
         Counter32,
      pr1646v2VrfLtdQmUpDownJitterUpBinsMaxBin8
         Counter32,
      pr1646v2VrfLtdQmUpDownJitterUpBinsMax
         Integer32,
      pr1646v2VrfLtdQmUpDownJitterUpBinsPlusMax
         Counter32,
      pr1646v2VrfLtdQmUpDownLossDown
         Counter32,
      pr1646v2VrfLtdQmUpDownLossDelayDown
         Counter32,
      pr1646v2VrfLtdQmUpDownDelayDownMin
         Integer32,
      pr1646v2VrfLtdQmUpDownDelayDownAvrg
         Integer32,
      pr1646v2VrfLtdQmUpDownDelayDownMax
         Integer32,
      pr1646v2VrfLtdQmUpDownDelayDownBinsType
         INTEGER,
      pr1646v2VrfLtdQmUpDownDelayDownBinsMinMin
         Counter32,
      pr1646v2VrfLtdQmUpDownDelayDownBinsMin
         Integer32,
      pr1646v2VrfLtdQmUpDownDelayDownBinsMinBin1
         Counter32,
      pr1646v2VrfLtdQmUpDownDelayDownBinsBin2
         Counter32,
      pr1646v2VrfLtdQmUpDownDelayDownBinsBin3
         Counter32,
      pr1646v2VrfLtdQmUpDownDelayDownBinsBin4
         Counter32,
      pr1646v2VrfLtdQmUpDownDelayDownBinsBin5
         Counter32,
      pr1646v2VrfLtdQmUpDownDelayDownBinsBin6
         Counter32,
      pr1646v2VrfLtdQmUpDownDelayDownBinsBin7
         Counter32,
      pr1646v2VrfLtdQmUpDownDelayDownBinsMaxBin8
         Counter32,
      pr1646v2VrfLtdQmUpDownDelayDownBinsMax
         Integer32,
      pr1646v2VrfLtdQmUpDownDelayDownBinsPlusMax
         Counter32,
      pr1646v2VrfLtdQmUpDownJitterDown
         Integer32,
      pr1646v2VrfLtdQmUpDownJitterDownNegMax
         Integer32,
      pr1646v2VrfLtdQmUpDownJitterDownAvrg
         Integer32,
      pr1646v2VrfLtdQmUpDownJitterDownPosMax
         Integer32,
      pr1646v2VrfLtdQmUpDownJitterDownBinsType
         INTEGER,
      pr1646v2VrfLtdQmUpDownJitterDownBinsMinMin
         Counter32,
      pr1646v2VrfLtdQmUpDownJitterDownBinsMin
         Integer32,
      pr1646v2VrfLtdQmUpDownJitterDownBinsMinBin1
         Counter32,
      pr1646v2VrfLtdQmUpDownJitterDownBinsBin2
         Counter32,
      pr1646v2VrfLtdQmUpDownJitterDownBinsBin3
         Counter32,
      pr1646v2VrfLtdQmUpDownJitterDownBinsBin4
         Counter32,
      pr1646v2VrfLtdQmUpDownJitterDownBinsBin5
         Counter32,
      pr1646v2VrfLtdQmUpDownJitterDownBinsBin6
         Counter32,
      pr1646v2VrfLtdQmUpDownJitterDownBinsBin7
         Counter32,
      pr1646v2VrfLtdQmUpDownJitterDownBinsMaxBin8
         Counter32,
      pr1646v2VrfLtdQmUpDownJitterDownBinsMax
         Integer32,
      pr1646v2VrfLtdQmUpDownJitterDownBinsPlusMax
         Counter32,
      pr1646v2VrfLtdQmLastLogSysUpTime
         TimeTicks,
      pr1646v2VrfLtdQmLastLogNbrTxPckt
         Counter32,
      pr1646v2VrfLtdQmLastLogNbrRxPckt
         Counter32,
      pr1646v2VrfLtdQmLastLogError
         Counter32,
      pr1646v2VrfLtdQmLastLogLoss
         Counter32,
      pr1646v2VrfLtdQmLastLogLossDelay
         Counter32,
      pr1646v2VrfLtdQmLastLogDelayMin
         Integer32,
      pr1646v2VrfLtdQmLastLogDelayAvrg
         Integer32,
      pr1646v2VrfLtdQmLastLogDelayMax
         Integer32,
      pr1646v2VrfLtdQmLastLogJitterNegMax
         Integer32,
      pr1646v2VrfLtdQmLastLogJitterAvrg
         Integer32,
      pr1646v2VrfLtdQmLastLogJitterPosMax
         Integer32,
      pr1646v2VrfLtdQmLastLogUpDownStatus
         INTEGER,
      pr1646v2VrfLtdQmLastLogUpDownLossUp
         Counter32,
      pr1646v2VrfLtdQmLastLogUpDownLossDelayUp
         Counter32,
      pr1646v2VrfLtdQmLastLogUpDownDelayUpMin
         Integer32,
      pr1646v2VrfLtdQmLastLogUpDownDelayUpAvrg
         Integer32,
      pr1646v2VrfLtdQmLastLogUpDownDelayUpMax
         Integer32,
      pr1646v2VrfLtdQmLastLogUpDownJitterUpNegMax
         Integer32,
      pr1646v2VrfLtdQmLastLogUpDownJitterUpAvrg
         Integer32,
      pr1646v2VrfLtdQmLastLogUpDownJitterUpPosMax
         Integer32,
      pr1646v2VrfLtdQmLastLogUpDownLossDown
         Counter32,
      pr1646v2VrfLtdQmLastLogUpDownLossDelayDown
         Counter32,
      pr1646v2VrfLtdQmLastLogUpDownDelayDownMin
         Integer32,
      pr1646v2VrfLtdQmLastLogUpDownDelayDownAvrg
         Integer32,
      pr1646v2VrfLtdQmLastLogUpDownDelayDownMax
         Integer32,
      pr1646v2VrfLtdQmLastLogUpDownJitterDownNegMax
         Integer32,
      pr1646v2VrfLtdQmLastLogUpDownJitterDownAvrg
         Integer32,
      pr1646v2VrfLtdQmLastLogUpDownJitterDownPosMax
         Integer32,
      pr1646v2VrfLtdQmLastLogDate
         DisplayString,
      pr1646v2VrfLtdQmAlarm
         Integer32,
      pr1646v2VrfLtdQmLastError
         DisplayString
      }

pr1646v2VrfLtdQmGlobalIx OBJECT-TYPE
   SYNTAX      GlobalIndex
   MAX-ACCESS  not-accessible
   STATUS      current
   DESCRIPTION
      "The value of the tlsCntTreeGlobalIndex of the MANAGED OBJECT."
   ::= {pr1646v2VrfLtdQmEntry 10}

pr1646v2VrfLtdQmTableIx OBJECT-TYPE
   SYNTAX      TableIndex
   MAX-ACCESS  not-accessible
   STATUS      current
   DESCRIPTION
      ""
   ::= {pr1646v2VrfLtdQmEntry 11}

pr1646v2VrfLtdQmName OBJECT-TYPE
   SYNTAX      DisplayString
   MAX-ACCESS  read-only
   STATUS      current
   DESCRIPTION
      "Path: vrfRouterLtd.performance.qualityMonitor.name"
   ::= {pr1646v2VrfLtdQmEntry 301989888}

pr1646v2VrfLtdQmStatus OBJECT-TYPE
   SYNTAX      INTEGER
               {
               run (1),
               runOnDemand (3),
               halted (2),
               cleared (6),
               disabled (8),
               runIdle (9)
               }
   MAX-ACCESS  read-only
   STATUS      current
   DESCRIPTION
      "Path: vrfRouterLtd.performance.qualityMonitor.status

       Possibilities:
               run   (1)
               runOnDemand   (3)
               halted   (2)
               cleared   (6)
               disabled   (8)
               runIdle   (9)"
   ::= {pr1646v2VrfLtdQmEntry 369098752}

pr1646v2VrfLtdQmIpAddress OBJECT-TYPE
   SYNTAX      IpAddress
   MAX-ACCESS  read-only
   STATUS      current
   DESCRIPTION
      "Path: vrfRouterLtd.performance.qualityMonitor.ipAddress"
   ::= {pr1646v2VrfLtdQmEntry 16777216}

pr1646v2VrfLtdQmHostName OBJECT-TYPE
   SYNTAX      DisplayString
   MAX-ACCESS  read-only
   STATUS      current
   DESCRIPTION
      "Path: vrfRouterLtd.performance.qualityMonitor.hostName"
   ::= {pr1646v2VrfLtdQmEntry 33554432}

pr1646v2VrfLtdQmSourceIp OBJECT-TYPE
   SYNTAX      IpAddress
   MAX-ACCESS  read-only
   STATUS      current
   DESCRIPTION
      "Path: vrfRouterLtd.performance.qualityMonitor.sourceIp"
   ::= {pr1646v2VrfLtdQmEntry 83886080}

pr1646v2VrfLtdQmSourceId OBJECT-TYPE
   SYNTAX      Gauge32
   MAX-ACCESS  read-only
   STATUS      current
   DESCRIPTION
      "Path: vrfRouterLtd.performance.qualityMonitor.sourceId

       32 bit unsigned gauge value."
   ::= {pr1646v2VrfLtdQmEntry 352321536}

pr1646v2VrfLtdQmNbrTxPckt OBJECT-TYPE
   SYNTAX      Counter32
   MAX-ACCESS  read-only
   STATUS      current
   DESCRIPTION
      "Path: vrfRouterLtd.performance.qualityMonitor.nbrOfTxPackets

       32 bit unsigned wrappable counter."
   ::= {pr1646v2VrfLtdQmEntry 50331648}

pr1646v2VrfLtdQmNbrRxPckt OBJECT-TYPE
   SYNTAX      Counter32
   MAX-ACCESS  read-only
   STATUS      current
   DESCRIPTION
      "Path: vrfRouterLtd.performance.qualityMonitor.nbrOfRxPackets

       32 bit unsigned wrappable counter."
   ::= {pr1646v2VrfLtdQmEntry 67108864}

pr1646v2VrfLtdQmError OBJECT-TYPE
   SYNTAX      Counter32
   MAX-ACCESS  read-only
   STATUS      current
   DESCRIPTION
      "Path: vrfRouterLtd.performance.qualityMonitor.error

       32 bit unsigned wrappable counter."
   ::= {pr1646v2VrfLtdQmEntry 285212672}

pr1646v2VrfLtdQmDelay OBJECT-TYPE
   SYNTAX      Integer32
   MAX-ACCESS  read-only
   STATUS      current
   DESCRIPTION
      "Path: vrfRouterLtd.performance.qualityMonitor.delay

       unit name = sec
       formula = 1000 / ; 1000 *"
   ::= {pr1646v2VrfLtdQmEntry 201326592}

pr1646v2VrfLtdQmJitter OBJECT-TYPE
   SYNTAX      Integer32
   MAX-ACCESS  read-only
   STATUS      current
   DESCRIPTION
      "Path: vrfRouterLtd.performance.qualityMonitor.jitter

       unit name = sec
       formula = 1000 / ; 1000 *"
   ::= {pr1646v2VrfLtdQmEntry 218103808}

pr1646v2VrfLtdQmLoss OBJECT-TYPE
   SYNTAX      Counter32
   MAX-ACCESS  read-only
   STATUS      current
   DESCRIPTION
      "Path: vrfRouterLtd.performance.qualityMonitor.loss

       32 bit unsigned wrappable counter."
   ::= {pr1646v2VrfLtdQmEntry 100663296}

pr1646v2VrfLtdQmLossDelay OBJECT-TYPE
   SYNTAX      Counter32
   MAX-ACCESS  read-only
   STATUS      current
   DESCRIPTION
      "Path: vrfRouterLtd.performance.qualityMonitor.lossDelay

       32 bit unsigned wrappable counter."
   ::= {pr1646v2VrfLtdQmEntry 268435456}

pr1646v2VrfLtdQmDelayMin OBJECT-TYPE
   SYNTAX      Integer32
   MAX-ACCESS  read-only
   STATUS      current
   DESCRIPTION
      "Path: vrfRouterLtd.performance.qualityMonitor.delayMin

       unit name = sec
       formula = 1000 / ; 1000 *"
   ::= {pr1646v2VrfLtdQmEntry 184549376}

pr1646v2VrfLtdQmDelayAvrg OBJECT-TYPE
   SYNTAX      Integer32
   MAX-ACCESS  read-only
   STATUS      current
   DESCRIPTION
      "Path: vrfRouterLtd.performance.qualityMonitor.delayAvrg

       unit name = sec
       formula = 1000 / ; 1000 *"
   ::= {pr1646v2VrfLtdQmEntry 117440512}

pr1646v2VrfLtdQmDelayMax OBJECT-TYPE
   SYNTAX      Integer32
   MAX-ACCESS  read-only
   STATUS      current
   DESCRIPTION
      "Path: vrfRouterLtd.performance.qualityMonitor.delayMax

       unit name = sec
       formula = 1000 / ; 1000 *"
   ::= {pr1646v2VrfLtdQmEntry 134217728}

pr1646v2VrfLtdQmDelayBinsType OBJECT-TYPE
   SYNTAX      INTEGER
               {
               fd (1),
               fdr (2),
               notInUse (3),
               ifdv (4)
               }
   MAX-ACCESS  read-only
   STATUS      current
   DESCRIPTION
      "Path: vrfRouterLtd.performance.qualityMonitor.delayBins.type

       Possibilities:
               fd   (1)
               fdr   (2)
               notInUse   (3)
               ifdv   (4)"
   ::= {pr1646v2VrfLtdQmEntry 420937728}

pr1646v2VrfLtdQmDelayBinsMinMin OBJECT-TYPE
   SYNTAX      Counter32
   MAX-ACCESS  read-only
   STATUS      current
   DESCRIPTION
      "Path: vrfRouterLtd.performance.qualityMonitor.delayBins.minMin

       32 bit unsigned wrappable counter."
   ::= {pr1646v2VrfLtdQmEntry 419495936}

pr1646v2VrfLtdQmDelayBinsMin OBJECT-TYPE
   SYNTAX      Integer32
   MAX-ACCESS  read-only
   STATUS      current
   DESCRIPTION
      "Path: vrfRouterLtd.performance.qualityMonitor.delayBins.min

       unit name = sec
       formula = 1000 / ; 1000 *"
   ::= {pr1646v2VrfLtdQmEntry 420806656}

pr1646v2VrfLtdQmDelayBinsMinBin1 OBJECT-TYPE
   SYNTAX      Counter32
   MAX-ACCESS  read-only
   STATUS      current
   DESCRIPTION
      "Path: vrfRouterLtd.performance.qualityMonitor.delayBins.minBin1

       32 bit unsigned wrappable counter."
   ::= {pr1646v2VrfLtdQmEntry 419561472}

pr1646v2VrfLtdQmDelayBinsBin2 OBJECT-TYPE
   SYNTAX      Counter32
   MAX-ACCESS  read-only
   STATUS      current
   DESCRIPTION
      "Path: vrfRouterLtd.performance.qualityMonitor.delayBins.bin2

       32 bit unsigned wrappable counter."
   ::= {pr1646v2VrfLtdQmEntry 419627008}

pr1646v2VrfLtdQmDelayBinsBin3 OBJECT-TYPE
   SYNTAX      Counter32
   MAX-ACCESS  read-only
   STATUS      current
   DESCRIPTION
      "Path: vrfRouterLtd.performance.qualityMonitor.delayBins.bin3

       32 bit unsigned wrappable counter."
   ::= {pr1646v2VrfLtdQmEntry 419692544}

pr1646v2VrfLtdQmDelayBinsBin4 OBJECT-TYPE
   SYNTAX      Counter32
   MAX-ACCESS  read-only
   STATUS      current
   DESCRIPTION
      "Path: vrfRouterLtd.performance.qualityMonitor.delayBins.bin4

       32 bit unsigned wrappable counter."
   ::= {pr1646v2VrfLtdQmEntry 419758080}

pr1646v2VrfLtdQmDelayBinsBin5 OBJECT-TYPE
   SYNTAX      Counter32
   MAX-ACCESS  read-only
   STATUS      current
   DESCRIPTION
      "Path: vrfRouterLtd.performance.qualityMonitor.delayBins.bin5

       32 bit unsigned wrappable counter."
   ::= {pr1646v2VrfLtdQmEntry 419823616}

pr1646v2VrfLtdQmDelayBinsBin6 OBJECT-TYPE
   SYNTAX      Counter32
   MAX-ACCESS  read-only
   STATUS      current
   DESCRIPTION
      "Path: vrfRouterLtd.performance.qualityMonitor.delayBins.bin6

       32 bit unsigned wrappable counter."
   ::= {pr1646v2VrfLtdQmEntry 419889152}

pr1646v2VrfLtdQmDelayBinsBin7 OBJECT-TYPE
   SYNTAX      Counter32
   MAX-ACCESS  read-only
   STATUS      current
   DESCRIPTION
      "Path: vrfRouterLtd.performance.qualityMonitor.delayBins.bin7

       32 bit unsigned wrappable counter."
   ::= {pr1646v2VrfLtdQmEntry 419954688}

pr1646v2VrfLtdQmDelayBinsMaxBin8 OBJECT-TYPE
   SYNTAX      Counter32
   MAX-ACCESS  read-only
   STATUS      current
   DESCRIPTION
      "Path: vrfRouterLtd.performance.qualityMonitor.delayBins.maxBin8

       32 bit unsigned wrappable counter."
   ::= {pr1646v2VrfLtdQmEntry 420020224}

pr1646v2VrfLtdQmDelayBinsMax OBJECT-TYPE
   SYNTAX      Integer32
   MAX-ACCESS  read-only
   STATUS      current
   DESCRIPTION
      "Path: vrfRouterLtd.performance.qualityMonitor.delayBins.max

       unit name = sec
       formula = 1000 / ; 1000 *"
   ::= {pr1646v2VrfLtdQmEntry 420872192}

pr1646v2VrfLtdQmDelayBinsPlusMax OBJECT-TYPE
   SYNTAX      Counter32
   MAX-ACCESS  read-only
   STATUS      current
   DESCRIPTION
      "Path: vrfRouterLtd.performance.qualityMonitor.delayBins.plusMax

       32 bit unsigned wrappable counter."
   ::= {pr1646v2VrfLtdQmEntry 420085760}

pr1646v2VrfLtdQmJitterNegMax OBJECT-TYPE
   SYNTAX      Integer32
   MAX-ACCESS  read-only
   STATUS      current
   DESCRIPTION
      "Path: vrfRouterLtd.performance.qualityMonitor.jitterNegMax

       unit name = sec
       formula = 1000 / ; 1000 *"
   ::= {pr1646v2VrfLtdQmEntry 234881024}

pr1646v2VrfLtdQmJitterAvrg OBJECT-TYPE
   SYNTAX      Integer32
   MAX-ACCESS  read-only
   STATUS      current
   DESCRIPTION
      "Path: vrfRouterLtd.performance.qualityMonitor.jitterAvrg

       unit name = sec
       formula = 1000 / ; 1000 *"
   ::= {pr1646v2VrfLtdQmEntry 150994944}

pr1646v2VrfLtdQmJitterPosMax OBJECT-TYPE
   SYNTAX      Integer32
   MAX-ACCESS  read-only
   STATUS      current
   DESCRIPTION
      "Path: vrfRouterLtd.performance.qualityMonitor.jitterPosMax

       unit name = sec
       formula = 1000 / ; 1000 *"
   ::= {pr1646v2VrfLtdQmEntry 167772160}

pr1646v2VrfLtdQmJitterBinsType OBJECT-TYPE
   SYNTAX      INTEGER
               {
               fd (1),
               fdr (2),
               notInUse (3),
               ifdv (4)
               }
   MAX-ACCESS  read-only
   STATUS      current
   DESCRIPTION
      "Path: vrfRouterLtd.performance.qualityMonitor.jitterBins.type

       Possibilities:
               fd   (1)
               fdr   (2)
               notInUse   (3)
               ifdv   (4)"
   ::= {pr1646v2VrfLtdQmEntry 437714944}

pr1646v2VrfLtdQmJitterBinsMinMin OBJECT-TYPE
   SYNTAX      Counter32
   MAX-ACCESS  read-only
   STATUS      current
   DESCRIPTION
      "Path: vrfRouterLtd.performance.qualityMonitor.jitterBins.minMin

       32 bit unsigned wrappable counter."
   ::= {pr1646v2VrfLtdQmEntry 436273152}

pr1646v2VrfLtdQmJitterBinsMin OBJECT-TYPE
   SYNTAX      Integer32
   MAX-ACCESS  read-only
   STATUS      current
   DESCRIPTION
      "Path: vrfRouterLtd.performance.qualityMonitor.jitterBins.min

       unit name = sec
       formula = 1000 / ; 1000 *"
   ::= {pr1646v2VrfLtdQmEntry 437583872}

pr1646v2VrfLtdQmJitterBinsMinBin1 OBJECT-TYPE
   SYNTAX      Counter32
   MAX-ACCESS  read-only
   STATUS      current
   DESCRIPTION
      "Path: vrfRouterLtd.performance.qualityMonitor.jitterBins.minBin1

       32 bit unsigned wrappable counter."
   ::= {pr1646v2VrfLtdQmEntry 436338688}

pr1646v2VrfLtdQmJitterBinsBin2 OBJECT-TYPE
   SYNTAX      Counter32
   MAX-ACCESS  read-only
   STATUS      current
   DESCRIPTION
      "Path: vrfRouterLtd.performance.qualityMonitor.jitterBins.bin2

       32 bit unsigned wrappable counter."
   ::= {pr1646v2VrfLtdQmEntry 436404224}

pr1646v2VrfLtdQmJitterBinsBin3 OBJECT-TYPE
   SYNTAX      Counter32
   MAX-ACCESS  read-only
   STATUS      current
   DESCRIPTION
      "Path: vrfRouterLtd.performance.qualityMonitor.jitterBins.bin3

       32 bit unsigned wrappable counter."
   ::= {pr1646v2VrfLtdQmEntry 436469760}

pr1646v2VrfLtdQmJitterBinsBin4 OBJECT-TYPE
   SYNTAX      Counter32
   MAX-ACCESS  read-only
   STATUS      current
   DESCRIPTION
      "Path: vrfRouterLtd.performance.qualityMonitor.jitterBins.bin4

       32 bit unsigned wrappable counter."
   ::= {pr1646v2VrfLtdQmEntry 436535296}

pr1646v2VrfLtdQmJitterBinsBin5 OBJECT-TYPE
   SYNTAX      Counter32
   MAX-ACCESS  read-only
   STATUS      current
   DESCRIPTION
      "Path: vrfRouterLtd.performance.qualityMonitor.jitterBins.bin5

       32 bit unsigned wrappable counter."
   ::= {pr1646v2VrfLtdQmEntry 436600832}

pr1646v2VrfLtdQmJitterBinsBin6 OBJECT-TYPE
   SYNTAX      Counter32
   MAX-ACCESS  read-only
   STATUS      current
   DESCRIPTION
      "Path: vrfRouterLtd.performance.qualityMonitor.jitterBins.bin6

       32 bit unsigned wrappable counter."
   ::= {pr1646v2VrfLtdQmEntry 436666368}

pr1646v2VrfLtdQmJitterBinsBin7 OBJECT-TYPE
   SYNTAX      Counter32
   MAX-ACCESS  read-only
   STATUS      current
   DESCRIPTION
      "Path: vrfRouterLtd.performance.qualityMonitor.jitterBins.bin7

       32 bit unsigned wrappable counter."
   ::= {pr1646v2VrfLtdQmEntry 436731904}

pr1646v2VrfLtdQmJitterBinsMaxBin8 OBJECT-TYPE
   SYNTAX      Counter32
   MAX-ACCESS  read-only
   STATUS      current
   DESCRIPTION
      "Path: vrfRouterLtd.performance.qualityMonitor.jitterBins.maxBin8

       32 bit unsigned wrappable counter."
   ::= {pr1646v2VrfLtdQmEntry 436797440}

pr1646v2VrfLtdQmJitterBinsMax OBJECT-TYPE
   SYNTAX      Integer32
   MAX-ACCESS  read-only
   STATUS      current
   DESCRIPTION
      "Path: vrfRouterLtd.performance.qualityMonitor.jitterBins.max

       unit name = sec
       formula = 1000 / ; 1000 *"
   ::= {pr1646v2VrfLtdQmEntry 437649408}

pr1646v2VrfLtdQmJitterBinsPlusMax OBJECT-TYPE
   SYNTAX      Counter32
   MAX-ACCESS  read-only
   STATUS      current
   DESCRIPTION
      "Path: vrfRouterLtd.performance.qualityMonitor.jitterBins.plusMax

       32 bit unsigned wrappable counter."
   ::= {pr1646v2VrfLtdQmEntry 436862976}

pr1646v2VrfLtdQmBfdCtrlOutPkts OBJECT-TYPE
   SYNTAX      Integer32
   MAX-ACCESS  read-only
   STATUS      current
   DESCRIPTION
      "Path: vrfRouterLtd.performance.qualityMonitor.bfdCtrl.outPkts"
   ::= {pr1646v2VrfLtdQmEntry 838926336}

pr1646v2VrfLtdQmBfdCtrlInPkts OBJECT-TYPE
   SYNTAX      Integer32
   MAX-ACCESS  read-only
   STATUS      current
   DESCRIPTION
      "Path: vrfRouterLtd.performance.qualityMonitor.bfdCtrl.inPkts"
   ::= {pr1646v2VrfLtdQmEntry 838991872}

pr1646v2VrfLtdQmBfdCtrlLocalState OBJECT-TYPE
   SYNTAX      INTEGER
               {
               down (1),
               init (2),
               up (3)
               }
   MAX-ACCESS  read-only
   STATUS      current
   DESCRIPTION
      "Path: vrfRouterLtd.performance.qualityMonitor.bfdCtrl.localState

       Possibilities:
               down   (1)
               init   (2)
               up   (3)"
   ::= {pr1646v2VrfLtdQmEntry 839057408}

pr1646v2VrfLtdQmBfdCtrlLocalDiscriminator OBJECT-TYPE
   SYNTAX      Integer32
   MAX-ACCESS  read-only
   STATUS      current
   DESCRIPTION
      "Path: vrfRouterLtd.performance.qualityMonitor.bfdCtrl.localDiscriminator"
   ::= {pr1646v2VrfLtdQmEntry 839122944}

pr1646v2VrfLtdQmBfdCtrlLocalTxInterval OBJECT-TYPE
   SYNTAX      Integer32
   UNITS       "ms"
   MAX-ACCESS  read-only
   STATUS      current
   DESCRIPTION
      "Path: vrfRouterLtd.performance.qualityMonitor.bfdCtrl.localTxInterval

       unit name = ms"
   ::= {pr1646v2VrfLtdQmEntry 839712768}

pr1646v2VrfLtdQmBfdCtrlLocalMinTxInterval OBJECT-TYPE
   SYNTAX      Integer32
   UNITS       "ms"
   MAX-ACCESS  read-only
   STATUS      current
   DESCRIPTION
      "Path: vrfRouterLtd.performance.qualityMonitor.bfdCtrl.localMinTxInterval

       unit name = ms"
   ::= {pr1646v2VrfLtdQmEntry 839188480}

pr1646v2VrfLtdQmBfdCtrlLocalDetectMultiplier OBJECT-TYPE
   SYNTAX      Integer32
   MAX-ACCESS  read-only
   STATUS      current
   DESCRIPTION
      "Path: vrfRouterLtd.performance.qualityMonitor.bfdCtrl.localDetectMultiplier"
   ::= {pr1646v2VrfLtdQmEntry 839254016}

pr1646v2VrfLtdQmBfdCtrlRemoteState OBJECT-TYPE
   SYNTAX      INTEGER
               {
               down (1),
               init (2),
               up (3)
               }
   MAX-ACCESS  read-only
   STATUS      current
   DESCRIPTION
      "Path: vrfRouterLtd.performance.qualityMonitor.bfdCtrl.remoteState

       Possibilities:
               down   (1)
               init   (2)
               up   (3)"
   ::= {pr1646v2VrfLtdQmEntry 839319552}

pr1646v2VrfLtdQmBfdCtrlRemoteDiscriminator OBJECT-TYPE
   SYNTAX      Integer32
   MAX-ACCESS  read-only
   STATUS      current
   DESCRIPTION
      "Path: vrfRouterLtd.performance.qualityMonitor.bfdCtrl.remoteDiscriminator"
   ::= {pr1646v2VrfLtdQmEntry 839450624}

pr1646v2VrfLtdQmBfdCtrlRemoteMinTxInterval OBJECT-TYPE
   SYNTAX      Integer32
   UNITS       "ms"
   MAX-ACCESS  read-only
   STATUS      current
   DESCRIPTION
      "Path: vrfRouterLtd.performance.qualityMonitor.bfdCtrl.remoteMinTxInterval

       unit name = ms"
   ::= {pr1646v2VrfLtdQmEntry 839385088}

pr1646v2VrfLtdQmBfdCtrlRemoteDetectMultiplier OBJECT-TYPE
   SYNTAX      Integer32
   MAX-ACCESS  read-only
   STATUS      current
   DESCRIPTION
      "Path: vrfRouterLtd.performance.qualityMonitor.bfdCtrl.remoteDetectMultiplier"
   ::= {pr1646v2VrfLtdQmEntry 839516160}

pr1646v2VrfLtdQmBfdCtrlRemoteMinRxInterval OBJECT-TYPE
   SYNTAX      Integer32
   UNITS       "ms"
   MAX-ACCESS  read-only
   STATUS      current
   DESCRIPTION
      "Path: vrfRouterLtd.performance.qualityMonitor.bfdCtrl.remoteMinRxInterval

       unit name = ms"
   ::= {pr1646v2VrfLtdQmEntry 839581696}

pr1646v2VrfLtdQmBfdCtrlRemoteMinRxEchoInterval OBJECT-TYPE
   SYNTAX      Integer32
   UNITS       "ms"
   MAX-ACCESS  read-only
   STATUS      current
   DESCRIPTION
      "Path: vrfRouterLtd.performance.qualityMonitor.bfdCtrl.remoteMinRxEchoInterval

       unit name = ms"
   ::= {pr1646v2VrfLtdQmEntry 839647232}

pr1646v2VrfLtdQmUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfRouterLtd.performance.qualityMonitor.upDown.status

       Possibilities:
               notInUse   (3)
               onlyJitter   (1)
               jitterAndLoss   (2)
               all   (4)
               onlyLoss   (8)"
   ::= {pr1646v2VrfLtdQmEntry 504627200}

pr1646v2VrfLtdQmUpDownLossUp OBJECT-TYPE
   SYNTAX      Counter32
   MAX-ACCESS  read-only
   STATUS      current
   DESCRIPTION
      "Path: vrfRouterLtd.performance.qualityMonitor.upDown.lossUp

       32 bit unsigned wrappable counter."
   ::= {pr1646v2VrfLtdQmEntry 503971840}

pr1646v2VrfLtdQmUpDownLossDelayUp OBJECT-TYPE
   SYNTAX      Counter32
   MAX-ACCESS  read-only
   STATUS      current
   DESCRIPTION
      "Path: vrfRouterLtd.performance.qualityMonitor.upDown.lossDelayUp

       32 bit unsigned wrappable counter."
   ::= {pr1646v2VrfLtdQmEntry 504037376}

pr1646v2VrfLtdQmUpDownDelayUpMin OBJECT-TYPE
   SYNTAX      Integer32
   MAX-ACCESS  read-only
   STATUS      current
   DESCRIPTION
      "Path: vrfRouterLtd.performance.qualityMonitor.upDown.delayUpMin

       unit name = sec
       formula = 1000 / ; 1000 *"
   ::= {pr1646v2VrfLtdQmEntry 505282560}

pr1646v2VrfLtdQmUpDownDelayUpAvrg OBJECT-TYPE
   SYNTAX      Integer32
   MAX-ACCESS  read-only
   STATUS      current
   DESCRIPTION
      "Path: vrfRouterLtd.performance.qualityMonitor.upDown.delayUpAvrg

       unit name = sec
       formula = 1000 / ; 1000 *"
   ::= {pr1646v2VrfLtdQmEntry 505348096}

pr1646v2VrfLtdQmUpDownDelayUpMax OBJECT-TYPE
   SYNTAX      Integer32
   MAX-ACCESS  read-only
   STATUS      current
   DESCRIPTION
      "Path: vrfRouterLtd.performance.qualityMonitor.upDown.delayUpMax

       unit name = sec
       formula = 1000 / ; 1000 *"
   ::= {pr1646v2VrfLtdQmEntry 505413632}

pr1646v2VrfLtdQmUpDownDelayUpBinsType OBJECT-TYPE
   SYNTAX      INTEGER
               {
               fd (1),
               fdr (2),
               notInUse (3),
               ifdv (4)
               }
   MAX-ACCESS  read-only
   STATUS      current
   DESCRIPTION
      "Path: vrfRouterLtd.performance.qualityMonitor.upDown.delayUpBins.type

       Possibilities:
               fd   (1)
               fdr   (2)
               notInUse   (3)
               ifdv   (4)"
   ::= {pr1646v2VrfLtdQmEntry 505943808}

pr1646v2VrfLtdQmUpDownDelayUpBinsMinMin OBJECT-TYPE
   SYNTAX      Counter32
   MAX-ACCESS  read-only
   STATUS      current
   DESCRIPTION
      "Path: vrfRouterLtd.performance.qualityMonitor.upDown.delayUpBins.minMin

       32 bit unsigned wrappable counter."
   ::= {pr1646v2VrfLtdQmEntry 505938176}

pr1646v2VrfLtdQmUpDownDelayUpBinsMin OBJECT-TYPE
   SYNTAX      Integer32
   MAX-ACCESS  read-only
   STATUS      current
   DESCRIPTION
      "Path: vrfRouterLtd.performance.qualityMonitor.upDown.delayUpBins.min

       unit name = sec
       formula = 1000 / ; 1000 *"
   ::= {pr1646v2VrfLtdQmEntry 505943296}

pr1646v2VrfLtdQmUpDownDelayUpBinsMinBin1 OBJECT-TYPE
   SYNTAX      Counter32
   MAX-ACCESS  read-only
   STATUS      current
   DESCRIPTION
      "Path: vrfRouterLtd.performance.qualityMonitor.upDown.delayUpBins.minBin1

       32 bit unsigned wrappable counter."
   ::= {pr1646v2VrfLtdQmEntry 505938432}

pr1646v2VrfLtdQmUpDownDelayUpBinsBin2 OBJECT-TYPE
   SYNTAX      Counter32
   MAX-ACCESS  read-only
   STATUS      current
   DESCRIPTION
      "Path: vrfRouterLtd.performance.qualityMonitor.upDown.delayUpBins.bin2

       32 bit unsigned wrappable counter."
   ::= {pr1646v2VrfLtdQmEntry 505938688}

pr1646v2VrfLtdQmUpDownDelayUpBinsBin3 OBJECT-TYPE
   SYNTAX      Counter32
   MAX-ACCESS  read-only
   STATUS      current
   DESCRIPTION
      "Path: vrfRouterLtd.performance.qualityMonitor.upDown.delayUpBins.bin3

       32 bit unsigned wrappable counter."
   ::= {pr1646v2VrfLtdQmEntry 505938944}

pr1646v2VrfLtdQmUpDownDelayUpBinsBin4 OBJECT-TYPE
   SYNTAX      Counter32
   MAX-ACCESS  read-only
   STATUS      current
   DESCRIPTION
      "Path: vrfRouterLtd.performance.qualityMonitor.upDown.delayUpBins.bin4

       32 bit unsigned wrappable counter."
   ::= {pr1646v2VrfLtdQmEntry 505939200}

pr1646v2VrfLtdQmUpDownDelayUpBinsBin5 OBJECT-TYPE
   SYNTAX      Counter32
   MAX-ACCESS  read-only
   STATUS      current
   DESCRIPTION
      "Path: vrfRouterLtd.performance.qualityMonitor.upDown.delayUpBins.bin5

       32 bit unsigned wrappable counter."
   ::= {pr1646v2VrfLtdQmEntry 505939456}

pr1646v2VrfLtdQmUpDownDelayUpBinsBin6 OBJECT-TYPE
   SYNTAX      Counter32
   MAX-ACCESS  read-only
   STATUS      current
   DESCRIPTION
      "Path: vrfRouterLtd.performance.qualityMonitor.upDown.delayUpBins.bin6

       32 bit unsigned wrappable counter."
   ::= {pr1646v2VrfLtdQmEntry 505939712}

pr1646v2VrfLtdQmUpDownDelayUpBinsBin7 OBJECT-TYPE
   SYNTAX      Counter32
   MAX-ACCESS  read-only
   STATUS      current
   DESCRIPTION
      "Path: vrfRouterLtd.performance.qualityMonitor.upDown.delayUpBins.bin7

       32 bit unsigned wrappable counter."
   ::= {pr1646v2VrfLtdQmEntry 505939968}

pr1646v2VrfLtdQmUpDownDelayUpBinsMaxBin8 OBJECT-TYPE
   SYNTAX      Counter32
   MAX-ACCESS  read-only
   STATUS      current
   DESCRIPTION
      "Path: vrfRouterLtd.performance.qualityMonitor.upDown.delayUpBins.maxBin8

       32 bit unsigned wrappable counter."
   ::= {pr1646v2VrfLtdQmEntry 505940224}

pr1646v2VrfLtdQmUpDownDelayUpBinsMax OBJECT-TYPE
   SYNTAX      Integer32
   MAX-ACCESS  read-only
   STATUS      current
   DESCRIPTION
      "Path: vrfRouterLtd.performance.qualityMonitor.upDown.delayUpBins.max

       unit name = sec
       formula = 1000 / ; 1000 *"
   ::= {pr1646v2VrfLtdQmEntry 505943552}

pr1646v2VrfLtdQmUpDownDelayUpBinsPlusMax OBJECT-TYPE
   SYNTAX      Counter32
   MAX-ACCESS  read-only
   STATUS      current
   DESCRIPTION
      "Path: vrfRouterLtd.performance.qualityMonitor.upDown.delayUpBins.plusMax

       32 bit unsigned wrappable counter."
   ::= {pr1646v2VrfLtdQmEntry 505940480}

pr1646v2VrfLtdQmUpDownJitterUp OBJECT-TYPE
   SYNTAX      Integer32
   MAX-ACCESS  read-only
   STATUS      current
   DESCRIPTION
      "Path: vrfRouterLtd.performance.qualityMonitor.upDown.jitterUp

       unit name = sec
       formula = 1000 / ; 1000 *"
   ::= {pr1646v2VrfLtdQmEntry 503775232}

pr1646v2VrfLtdQmUpDownJitterUpNegMax OBJECT-TYPE
   SYNTAX      Integer32
   MAX-ACCESS  read-only
   STATUS      current
   DESCRIPTION
      "Path: vrfRouterLtd.performance.qualityMonitor.upDown.jitterUpNegMax

       unit name = sec
       formula = 1000 / ; 1000 *"
   ::= {pr1646v2VrfLtdQmEntry 503382016}

pr1646v2VrfLtdQmUpDownJitterUpAvrg OBJECT-TYPE
   SYNTAX      Integer32
   MAX-ACCESS  read-only
   STATUS      current
   DESCRIPTION
      "Path: vrfRouterLtd.performance.qualityMonitor.upDown.jitterUpAvrg

       unit name = sec
       formula = 1000 / ; 1000 *"
   ::= {pr1646v2VrfLtdQmEntry 503447552}

pr1646v2VrfLtdQmUpDownJitterUpPosMax OBJECT-TYPE
   SYNTAX      Integer32
   MAX-ACCESS  read-only
   STATUS      current
   DESCRIPTION
      "Path: vrfRouterLtd.performance.qualityMonitor.upDown.jitterUpPosMax

       unit name = sec
       formula = 1000 / ; 1000 *"
   ::= {pr1646v2VrfLtdQmEntry 503513088}

pr1646v2VrfLtdQmUpDownJitterUpBinsType OBJECT-TYPE
   SYNTAX      INTEGER
               {
               fd (1),
               fdr (2),
               notInUse (3),
               ifdv (4)
               }
   MAX-ACCESS  read-only
   STATUS      current
   DESCRIPTION
      "Path: vrfRouterLtd.performance.qualityMonitor.upDown.jitterUpBins.type

       Possibilities:
               fd   (1)
               fdr   (2)
               notInUse   (3)
               ifdv   (4)"
   ::= {pr1646v2VrfLtdQmEntry 506074880}

pr1646v2VrfLtdQmUpDownJitterUpBinsMinMin OBJECT-TYPE
   SYNTAX      Counter32
   MAX-ACCESS  read-only
   STATUS      current
   DESCRIPTION
      "Path: vrfRouterLtd.performance.qualityMonitor.upDown.jitterUpBins.minMin

       32 bit unsigned wrappable counter."
   ::= {pr1646v2VrfLtdQmEntry 506069248}

pr1646v2VrfLtdQmUpDownJitterUpBinsMin OBJECT-TYPE
   SYNTAX      Integer32
   MAX-ACCESS  read-only
   STATUS      current
   DESCRIPTION
      "Path: vrfRouterLtd.performance.qualityMonitor.upDown.jitterUpBins.min

       unit name = sec
       formula = 1000 / ; 1000 *"
   ::= {pr1646v2VrfLtdQmEntry 506074368}

pr1646v2VrfLtdQmUpDownJitterUpBinsMinBin1 OBJECT-TYPE
   SYNTAX      Counter32
   MAX-ACCESS  read-only
   STATUS      current
   DESCRIPTION
      "Path: vrfRouterLtd.performance.qualityMonitor.upDown.jitterUpBins.minBin1

       32 bit unsigned wrappable counter."
   ::= {pr1646v2VrfLtdQmEntry 506069504}

pr1646v2VrfLtdQmUpDownJitterUpBinsBin2 OBJECT-TYPE
   SYNTAX      Counter32
   MAX-ACCESS  read-only
   STATUS      current
   DESCRIPTION
      "Path: vrfRouterLtd.performance.qualityMonitor.upDown.jitterUpBins.bin2

       32 bit unsigned wrappable counter."
   ::= {pr1646v2VrfLtdQmEntry 506069760}

pr1646v2VrfLtdQmUpDownJitterUpBinsBin3 OBJECT-TYPE
   SYNTAX      Counter32
   MAX-ACCESS  read-only
   STATUS      current
   DESCRIPTION
      "Path: vrfRouterLtd.performance.qualityMonitor.upDown.jitterUpBins.bin3

       32 bit unsigned wrappable counter."
   ::= {pr1646v2VrfLtdQmEntry 506070016}

pr1646v2VrfLtdQmUpDownJitterUpBinsBin4 OBJECT-TYPE
   SYNTAX      Counter32
   MAX-ACCESS  read-only
   STATUS      current
   DESCRIPTION
      "Path: vrfRouterLtd.performance.qualityMonitor.upDown.jitterUpBins.bin4

       32 bit unsigned wrappable counter."
   ::= {pr1646v2VrfLtdQmEntry 506070272}

pr1646v2VrfLtdQmUpDownJitterUpBinsBin5 OBJECT-TYPE
   SYNTAX      Counter32
   MAX-ACCESS  read-only
   STATUS      current
   DESCRIPTION
      "Path: vrfRouterLtd.performance.qualityMonitor.upDown.jitterUpBins.bin5

       32 bit unsigned wrappable counter."
   ::= {pr1646v2VrfLtdQmEntry 506070528}

pr1646v2VrfLtdQmUpDownJitterUpBinsBin6 OBJECT-TYPE
   SYNTAX      Counter32
   MAX-ACCESS  read-only
   STATUS      current
   DESCRIPTION
      "Path: vrfRouterLtd.performance.qualityMonitor.upDown.jitterUpBins.bin6

       32 bit unsigned wrappable counter."
   ::= {pr1646v2VrfLtdQmEntry 506070784}

pr1646v2VrfLtdQmUpDownJitterUpBinsBin7 OBJECT-TYPE
   SYNTAX      Counter32
   MAX-ACCESS  read-only
   STATUS      current
   DESCRIPTION
      "Path: vrfRouterLtd.performance.qualityMonitor.upDown.jitterUpBins.bin7

       32 bit unsigned wrappable counter."
   ::= {pr1646v2VrfLtdQmEntry 506071040}

pr1646v2VrfLtdQmUpDownJitterUpBinsMaxBin8 OBJECT-TYPE
   SYNTAX      Counter32
   MAX-ACCESS  read-only
   STATUS      current
   DESCRIPTION
      "Path: vrfRouterLtd.performance.qualityMonitor.upDown.jitterUpBins.maxBin8

       32 bit unsigned wrappable counter."
   ::= {pr1646v2VrfLtdQmEntry 506071296}

pr1646v2VrfLtdQmUpDownJitterUpBinsMax OBJECT-TYPE
   SYNTAX      Integer32
   MAX-ACCESS  read-only
   STATUS      current
   DESCRIPTION
      "Path: vrfRouterLtd.performance.qualityMonitor.upDown.jitterUpBins.max

       unit name = sec
       formula = 1000 / ; 1000 *"
   ::= {pr1646v2VrfLtdQmEntry 506074624}

pr1646v2VrfLtdQmUpDownJitterUpBinsPlusMax OBJECT-TYPE
   SYNTAX      Counter32
   MAX-ACCESS  read-only
   STATUS      current
   DESCRIPTION
      "Path: vrfRouterLtd.performance.qualityMonitor.upDown.jitterUpBins.plusMax

       32 bit unsigned wrappable counter."
   ::= {pr1646v2VrfLtdQmEntry 506071552}

pr1646v2VrfLtdQmUpDownLossDown OBJECT-TYPE
   SYNTAX      Counter32
   MAX-ACCESS  read-only
   STATUS      current
   DESCRIPTION
      "Path: vrfRouterLtd.performance.qualityMonitor.upDown.lossDown

       32 bit unsigned wrappable counter."
   ::= {pr1646v2VrfLtdQmEntry 504102912}

pr1646v2VrfLtdQmUpDownLossDelayDown OBJECT-TYPE
   SYNTAX      Counter32
   MAX-ACCESS  read-only
   STATUS      current
   DESCRIPTION
      "Path: vrfRouterLtd.performance.qualityMonitor.upDown.lossDelayDown

       32 bit unsigned wrappable counter."
   ::= {pr1646v2VrfLtdQmEntry 504168448}

pr1646v2VrfLtdQmUpDownDelayDownMin OBJECT-TYPE
   SYNTAX      Integer32
   MAX-ACCESS  read-only
   STATUS      current
   DESCRIPTION
      "Path: vrfRouterLtd.performance.qualityMonitor.upDown.delayDownMin

       unit name = sec
       formula = 1000 / ; 1000 *"
   ::= {pr1646v2VrfLtdQmEntry 505610240}

pr1646v2VrfLtdQmUpDownDelayDownAvrg OBJECT-TYPE
   SYNTAX      Integer32
   MAX-ACCESS  read-only
   STATUS      current
   DESCRIPTION
      "Path: vrfRouterLtd.performance.qualityMonitor.upDown.delayDownAvrg

       unit name = sec
       formula = 1000 / ; 1000 *"
   ::= {pr1646v2VrfLtdQmEntry 505675776}

pr1646v2VrfLtdQmUpDownDelayDownMax OBJECT-TYPE
   SYNTAX      Integer32
   MAX-ACCESS  read-only
   STATUS      current
   DESCRIPTION
      "Path: vrfRouterLtd.performance.qualityMonitor.upDown.delayDownMax

       unit name = sec
       formula = 1000 / ; 1000 *"
   ::= {pr1646v2VrfLtdQmEntry 505741312}

pr1646v2VrfLtdQmUpDownDelayDownBinsType OBJECT-TYPE
   SYNTAX      INTEGER
               {
               fd (1),
               fdr (2),
               notInUse (3),
               ifdv (4)
               }
   MAX-ACCESS  read-only
   STATUS      current
   DESCRIPTION
      "Path: vrfRouterLtd.performance.qualityMonitor.upDown.delayDownBins.type

       Possibilities:
               fd   (1)
               fdr   (2)
               notInUse   (3)
               ifdv   (4)"
   ::= {pr1646v2VrfLtdQmEntry 506009344}

pr1646v2VrfLtdQmUpDownDelayDownBinsMinMin OBJECT-TYPE
   SYNTAX      Counter32
   MAX-ACCESS  read-only
   STATUS      current
   DESCRIPTION
      "Path: vrfRouterLtd.performance.qualityMonitor.upDown.delayDownBins.minMin

       32 bit unsigned wrappable counter."
   ::= {pr1646v2VrfLtdQmEntry 506003712}

pr1646v2VrfLtdQmUpDownDelayDownBinsMin OBJECT-TYPE
   SYNTAX      Integer32
   MAX-ACCESS  read-only
   STATUS      current
   DESCRIPTION
      "Path: vrfRouterLtd.performance.qualityMonitor.upDown.delayDownBins.min

       unit name = sec
       formula = 1000 / ; 1000 *"
   ::= {pr1646v2VrfLtdQmEntry 506008832}

pr1646v2VrfLtdQmUpDownDelayDownBinsMinBin1 OBJECT-TYPE
   SYNTAX      Counter32
   MAX-ACCESS  read-only
   STATUS      current
   DESCRIPTION
      "Path: vrfRouterLtd.performance.qualityMonitor.upDown.delayDownBins.minBin1

       32 bit unsigned wrappable counter."
   ::= {pr1646v2VrfLtdQmEntry 506003968}

pr1646v2VrfLtdQmUpDownDelayDownBinsBin2 OBJECT-TYPE
   SYNTAX      Counter32
   MAX-ACCESS  read-only
   STATUS      current
   DESCRIPTION
      "Path: vrfRouterLtd.performance.qualityMonitor.upDown.delayDownBins.bin2

       32 bit unsigned wrappable counter."
   ::= {pr1646v2VrfLtdQmEntry 506004224}

pr1646v2VrfLtdQmUpDownDelayDownBinsBin3 OBJECT-TYPE
   SYNTAX      Counter32
   MAX-ACCESS  read-only
   STATUS      current
   DESCRIPTION
      "Path: vrfRouterLtd.performance.qualityMonitor.upDown.delayDownBins.bin3

       32 bit unsigned wrappable counter."
   ::= {pr1646v2VrfLtdQmEntry 506004480}

pr1646v2VrfLtdQmUpDownDelayDownBinsBin4 OBJECT-TYPE
   SYNTAX      Counter32
   MAX-ACCESS  read-only
   STATUS      current
   DESCRIPTION
      "Path: vrfRouterLtd.performance.qualityMonitor.upDown.delayDownBins.bin4

       32 bit unsigned wrappable counter."
   ::= {pr1646v2VrfLtdQmEntry 506004736}

pr1646v2VrfLtdQmUpDownDelayDownBinsBin5 OBJECT-TYPE
   SYNTAX      Counter32
   MAX-ACCESS  read-only
   STATUS      current
   DESCRIPTION
      "Path: vrfRouterLtd.performance.qualityMonitor.upDown.delayDownBins.bin5

       32 bit unsigned wrappable counter."
   ::= {pr1646v2VrfLtdQmEntry 506004992}

pr1646v2VrfLtdQmUpDownDelayDownBinsBin6 OBJECT-TYPE
   SYNTAX      Counter32
   MAX-ACCESS  read-only
   STATUS      current
   DESCRIPTION
      "Path: vrfRouterLtd.performance.qualityMonitor.upDown.delayDownBins.bin6

       32 bit unsigned wrappable counter."
   ::= {pr1646v2VrfLtdQmEntry 506005248}

pr1646v2VrfLtdQmUpDownDelayDownBinsBin7 OBJECT-TYPE
   SYNTAX      Counter32
   MAX-ACCESS  read-only
   STATUS      current
   DESCRIPTION
      "Path: vrfRouterLtd.performance.qualityMonitor.upDown.delayDownBins.bin7

       32 bit unsigned wrappable counter."
   ::= {pr1646v2VrfLtdQmEntry 506005504}

pr1646v2VrfLtdQmUpDownDelayDownBinsMaxBin8 OBJECT-TYPE
   SYNTAX      Counter32
   MAX-ACCESS  read-only
   STATUS      current
   DESCRIPTION
      "Path: vrfRouterLtd.performance.qualityMonitor.upDown.delayDownBins.maxBin8

       32 bit unsigned wrappable counter."
   ::= {pr1646v2VrfLtdQmEntry 506005760}

pr1646v2VrfLtdQmUpDownDelayDownBinsMax OBJECT-TYPE
   SYNTAX      Integer32
   MAX-ACCESS  read-only
   STATUS      current
   DESCRIPTION
      "Path: vrfRouterLtd.performance.qualityMonitor.upDown.delayDownBins.max

       unit name = sec
       formula = 1000 / ; 1000 *"
   ::= {pr1646v2VrfLtdQmEntry 506009088}

pr1646v2VrfLtdQmUpDownDelayDownBinsPlusMax OBJECT-TYPE
   SYNTAX      Counter32
   MAX-ACCESS  read-only
   STATUS      current
   DESCRIPTION
      "Path: vrfRouterLtd.performance.qualityMonitor.upDown.delayDownBins.plusMax

       32 bit unsigned wrappable counter."
   ::= {pr1646v2VrfLtdQmEntry 506006016}

pr1646v2VrfLtdQmUpDownJitterDown OBJECT-TYPE
   SYNTAX      Integer32
   MAX-ACCESS  read-only
   STATUS      current
   DESCRIPTION
      "Path: vrfRouterLtd.performance.qualityMonitor.upDown.jitterDown

       unit name = sec
       formula = 1000 / ; 1000 *"
   ::= {pr1646v2VrfLtdQmEntry 503840768}

pr1646v2VrfLtdQmUpDownJitterDownNegMax OBJECT-TYPE
   SYNTAX      Integer32
   MAX-ACCESS  read-only
   STATUS      current
   DESCRIPTION
      "Path: vrfRouterLtd.performance.qualityMonitor.upDown.jitterDownNegMax

       unit name = sec
       formula = 1000 / ; 1000 *"
   ::= {pr1646v2VrfLtdQmEntry 503578624}

pr1646v2VrfLtdQmUpDownJitterDownAvrg OBJECT-TYPE
   SYNTAX      Integer32
   MAX-ACCESS  read-only
   STATUS      current
   DESCRIPTION
      "Path: vrfRouterLtd.performance.qualityMonitor.upDown.jitterDownAvrg

       unit name = sec
       formula = 1000 / ; 1000 *"
   ::= {pr1646v2VrfLtdQmEntry 503644160}

pr1646v2VrfLtdQmUpDownJitterDownPosMax OBJECT-TYPE
   SYNTAX      Integer32
   MAX-ACCESS  read-only
   STATUS      current
   DESCRIPTION
      "Path: vrfRouterLtd.performance.qualityMonitor.upDown.jitterDownPosMax

       unit name = sec
       formula = 1000 / ; 1000 *"
   ::= {pr1646v2VrfLtdQmEntry 503709696}

pr1646v2VrfLtdQmUpDownJitterDownBinsType OBJECT-TYPE
   SYNTAX      INTEGER
               {
               fd (1),
               fdr (2),
               notInUse (3),
               ifdv (4)
               }
   MAX-ACCESS  read-only
   STATUS      current
   DESCRIPTION
      "Path: vrfRouterLtd.performance.qualityMonitor.upDown.jitterDownBins.type

       Possibilities:
               fd   (1)
               fdr   (2)
               notInUse   (3)
               ifdv   (4)"
   ::= {pr1646v2VrfLtdQmEntry 506205952}

pr1646v2VrfLtdQmUpDownJitterDownBinsMinMin OBJECT-TYPE
   SYNTAX      Counter32
   MAX-ACCESS  read-only
   STATUS      current
   DESCRIPTION
      "Path: vrfRouterLtd.performance.qualityMonitor.upDown.jitterDownBins.minMin

       32 bit unsigned wrappable counter."
   ::= {pr1646v2VrfLtdQmEntry 506200320}

pr1646v2VrfLtdQmUpDownJitterDownBinsMin OBJECT-TYPE
   SYNTAX      Integer32
   MAX-ACCESS  read-only
   STATUS      current
   DESCRIPTION
      "Path: vrfRouterLtd.performance.qualityMonitor.upDown.jitterDownBins.min

       unit name = sec
       formula = 1000 / ; 1000 *"
   ::= {pr1646v2VrfLtdQmEntry 506205440}

pr1646v2VrfLtdQmUpDownJitterDownBinsMinBin1 OBJECT-TYPE
   SYNTAX      Counter32
   MAX-ACCESS  read-only
   STATUS      current
   DESCRIPTION
      "Path: vrfRouterLtd.performance.qualityMonitor.upDown.jitterDownBins.minBin1

       32 bit unsigned wrappable counter."
   ::= {pr1646v2VrfLtdQmEntry 506200576}

pr1646v2VrfLtdQmUpDownJitterDownBinsBin2 OBJECT-TYPE
   SYNTAX      Counter32
   MAX-ACCESS  read-only
   STATUS      current
   DESCRIPTION
      "Path: vrfRouterLtd.performance.qualityMonitor.upDown.jitterDownBins.bin2

       32 bit unsigned wrappable counter."
   ::= {pr1646v2VrfLtdQmEntry 506200832}

pr1646v2VrfLtdQmUpDownJitterDownBinsBin3 OBJECT-TYPE
   SYNTAX      Counter32
   MAX-ACCESS  read-only
   STATUS      current
   DESCRIPTION
      "Path: vrfRouterLtd.performance.qualityMonitor.upDown.jitterDownBins.bin3

       32 bit unsigned wrappable counter."
   ::= {pr1646v2VrfLtdQmEntry 506201088}

pr1646v2VrfLtdQmUpDownJitterDownBinsBin4 OBJECT-TYPE
   SYNTAX      Counter32
   MAX-ACCESS  read-only
   STATUS      current
   DESCRIPTION
      "Path: vrfRouterLtd.performance.qualityMonitor.upDown.jitterDownBins.bin4

       32 bit unsigned wrappable counter."
   ::= {pr1646v2VrfLtdQmEntry 506201344}

pr1646v2VrfLtdQmUpDownJitterDownBinsBin5 OBJECT-TYPE
   SYNTAX      Counter32
   MAX-ACCESS  read-only
   STATUS      current
   DESCRIPTION
      "Path: vrfRouterLtd.performance.qualityMonitor.upDown.jitterDownBins.bin5

       32 bit unsigned wrappable counter."
   ::= {pr1646v2VrfLtdQmEntry 506201600}

pr1646v2VrfLtdQmUpDownJitterDownBinsBin6 OBJECT-TYPE
   SYNTAX      Counter32
   MAX-ACCESS  read-only
   STATUS      current
   DESCRIPTION
      "Path: vrfRouterLtd.performance.qualityMonitor.upDown.jitterDownBins.bin6

       32 bit unsigned wrappable counter."
   ::= {pr1646v2VrfLtdQmEntry 506201856}

pr1646v2VrfLtdQmUpDownJitterDownBinsBin7 OBJECT-TYPE
   SYNTAX      Counter32
   MAX-ACCESS  read-only
   STATUS      current
   DESCRIPTION
      "Path: vrfRouterLtd.performance.qualityMonitor.upDown.jitterDownBins.bin7

       32 bit unsigned wrappable counter."
   ::= {pr1646v2VrfLtdQmEntry 506202112}

pr1646v2VrfLtdQmUpDownJitterDownBinsMaxBin8 OBJECT-TYPE
   SYNTAX      Counter32
   MAX-ACCESS  read-only
   STATUS      current
   DESCRIPTION
      "Path: vrfRouterLtd.performance.qualityMonitor.upDown.jitterDownBins.maxBin8

       32 bit unsigned wrappable counter."
   ::= {pr1646v2VrfLtdQmEntry 506202368}

pr1646v2VrfLtdQmUpDownJitterDownBinsMax OBJECT-TYPE
   SYNTAX      Integer32
   MAX-ACCESS  read-only
   STATUS      current
   DESCRIPTION
      "Path: vrfRouterLtd.performance.qualityMonitor.upDown.jitterDownBins.max

       unit name = sec
       formula = 1000 / ; 1000 *"
   ::= {pr1646v2VrfLtdQmEntry 506205696}

pr1646v2VrfLtdQmUpDownJitterDownBinsPlusMax OBJECT-TYPE
   SYNTAX      Counter32
   MAX-ACCESS  read-only
   STATUS      current
   DESCRIPTION
      "Path: vrfRouterLtd.performance.qualityMonitor.upDown.jitterDownBins.plusMax

       32 bit unsigned wrappable counter."
   ::= {pr1646v2VrfLtdQmEntry 506202624}

pr1646v2VrfLtdQmLastLogSysUpTime OBJECT-TYPE
   SYNTAX      TimeTicks
   MAX-ACCESS  read-only
   STATUS      current
   DESCRIPTION
      "Path: vrfRouterLtd.performance.qualityMonitor.lastLog.sysUpTime

       Time in centi-second."
   ::= {pr1646v2VrfLtdQmEntry 671154176}

pr1646v2VrfLtdQmLastLogNbrTxPckt OBJECT-TYPE
   SYNTAX      Counter32
   MAX-ACCESS  read-only
   STATUS      current
   DESCRIPTION
      "Path: vrfRouterLtd.performance.qualityMonitor.lastLog.nbrOfTxPackets

       32 bit unsigned wrappable counter."
   ::= {pr1646v2VrfLtdQmEntry 671285248}

pr1646v2VrfLtdQmLastLogNbrRxPckt OBJECT-TYPE
   SYNTAX      Counter32
   MAX-ACCESS  read-only
   STATUS      current
   DESCRIPTION
      "Path: vrfRouterLtd.performance.qualityMonitor.lastLog.nbrOfRxPackets

       32 bit unsigned wrappable counter."
   ::= {pr1646v2VrfLtdQmEntry 671350784}

pr1646v2VrfLtdQmLastLogError OBJECT-TYPE
   SYNTAX      Counter32
   MAX-ACCESS  read-only
   STATUS      current
   DESCRIPTION
      "Path: vrfRouterLtd.performance.qualityMonitor.lastLog.error

       32 bit unsigned wrappable counter."
   ::= {pr1646v2VrfLtdQmEntry 672202752}

pr1646v2VrfLtdQmLastLogLoss OBJECT-TYPE
   SYNTAX      Counter32
   MAX-ACCESS  read-only
   STATUS      current
   DESCRIPTION
      "Path: vrfRouterLtd.performance.qualityMonitor.lastLog.loss

       32 bit unsigned wrappable counter."
   ::= {pr1646v2VrfLtdQmEntry 671481856}

pr1646v2VrfLtdQmLastLogLossDelay OBJECT-TYPE
   SYNTAX      Counter32
   MAX-ACCESS  read-only
   STATUS      current
   DESCRIPTION
      "Path: vrfRouterLtd.performance.qualityMonitor.lastLog.lossDelay

       32 bit unsigned wrappable counter."
   ::= {pr1646v2VrfLtdQmEntry 672137216}

pr1646v2VrfLtdQmLastLogDelayMin OBJECT-TYPE
   SYNTAX      Integer32
   MAX-ACCESS  read-only
   STATUS      current
   DESCRIPTION
      "Path: vrfRouterLtd.performance.qualityMonitor.lastLog.delayMin

       unit name = sec
       formula = 1000 / ; 1000 *"
   ::= {pr1646v2VrfLtdQmEntry 671809536}

pr1646v2VrfLtdQmLastLogDelayAvrg OBJECT-TYPE
   SYNTAX      Integer32
   MAX-ACCESS  read-only
   STATUS      current
   DESCRIPTION
      "Path: vrfRouterLtd.performance.qualityMonitor.lastLog.delayAvrg

       unit name = sec
       formula = 1000 / ; 1000 *"
   ::= {pr1646v2VrfLtdQmEntry 671547392}

pr1646v2VrfLtdQmLastLogDelayMax OBJECT-TYPE
   SYNTAX      Integer32
   MAX-ACCESS  read-only
   STATUS      current
   DESCRIPTION
      "Path: vrfRouterLtd.performance.qualityMonitor.lastLog.delayMax

       unit name = sec
       formula = 1000 / ; 1000 *"
   ::= {pr1646v2VrfLtdQmEntry 671612928}

pr1646v2VrfLtdQmLastLogJitterNegMax OBJECT-TYPE
   SYNTAX      Integer32
   MAX-ACCESS  read-only
   STATUS      current
   DESCRIPTION
      "Path: vrfRouterLtd.performance.qualityMonitor.lastLog.jitterNegMax

       unit name = sec
       formula = 1000 / ; 1000 *"
   ::= {pr1646v2VrfLtdQmEntry 672006144}

pr1646v2VrfLtdQmLastLogJitterAvrg OBJECT-TYPE
   SYNTAX      Integer32
   MAX-ACCESS  read-only
   STATUS      current
   DESCRIPTION
      "Path: vrfRouterLtd.performance.qualityMonitor.lastLog.jitterAvrg

       unit name = sec
       formula = 1000 / ; 1000 *"
   ::= {pr1646v2VrfLtdQmEntry 671678464}

pr1646v2VrfLtdQmLastLogJitterPosMax OBJECT-TYPE
   SYNTAX      Integer32
   MAX-ACCESS  read-only
   STATUS      current
   DESCRIPTION
      "Path: vrfRouterLtd.performance.qualityMonitor.lastLog.jitterPosMax

       unit name = sec
       formula = 1000 / ; 1000 *"
   ::= {pr1646v2VrfLtdQmEntry 671744000}

pr1646v2VrfLtdQmLastLogUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfRouterLtd.performance.qualityMonitor.lastLog.upDown.status

       Possibilities:
               notInUse   (3)
               onlyJitter   (1)
               jitterAndLoss   (2)
               all   (4)
               onlyLoss   (8)"
   ::= {pr1646v2VrfLtdQmEntry 673059840}

pr1646v2VrfLtdQmLastLogUpDownLossUp OBJECT-TYPE
   SYNTAX      Counter32
   MAX-ACCESS  read-only
   STATUS      current
   DESCRIPTION
      "Path: vrfRouterLtd.performance.qualityMonitor.lastLog.upDown.lossUp

       32 bit unsigned wrappable counter."
   ::= {pr1646v2VrfLtdQmEntry 673057280}

pr1646v2VrfLtdQmLastLogUpDownLossDelayUp OBJECT-TYPE
   SYNTAX      Counter32
   MAX-ACCESS  read-only
   STATUS      current
   DESCRIPTION
      "Path: vrfRouterLtd.performance.qualityMonitor.lastLog.upDown.lossDelayUp

       32 bit unsigned wrappable counter."
   ::= {pr1646v2VrfLtdQmEntry 673057536}

pr1646v2VrfLtdQmLastLogUpDownDelayUpMin OBJECT-TYPE
   SYNTAX      Integer32
   MAX-ACCESS  read-only
   STATUS      current
   DESCRIPTION
      "Path: vrfRouterLtd.performance.qualityMonitor.lastLog.upDown.delayUpMin

       unit name = sec
       formula = 1000 / ; 1000 *"
   ::= {pr1646v2VrfLtdQmEntry 673062400}

pr1646v2VrfLtdQmLastLogUpDownDelayUpAvrg OBJECT-TYPE
   SYNTAX      Integer32
   MAX-ACCESS  read-only
   STATUS      current
   DESCRIPTION
      "Path: vrfRouterLtd.performance.qualityMonitor.lastLog.upDown.delayUpAvrg

       unit name = sec
       formula = 1000 / ; 1000 *"
   ::= {pr1646v2VrfLtdQmEntry 673062656}

pr1646v2VrfLtdQmLastLogUpDownDelayUpMax OBJECT-TYPE
   SYNTAX      Integer32
   MAX-ACCESS  read-only
   STATUS      current
   DESCRIPTION
      "Path: vrfRouterLtd.performance.qualityMonitor.lastLog.upDown.delayUpMax

       unit name = sec
       formula = 1000 / ; 1000 *"
   ::= {pr1646v2VrfLtdQmEntry 673062912}

pr1646v2VrfLtdQmLastLogUpDownJitterUpNegMax OBJECT-TYPE
   SYNTAX      Integer32
   MAX-ACCESS  read-only
   STATUS      current
   DESCRIPTION
      "Path: vrfRouterLtd.performance.qualityMonitor.lastLog.upDown.jitterUpNegMax

       unit name = sec
       formula = 1000 / ; 1000 *"
   ::= {pr1646v2VrfLtdQmEntry 673054976}

pr1646v2VrfLtdQmLastLogUpDownJitterUpAvrg OBJECT-TYPE
   SYNTAX      Integer32
   MAX-ACCESS  read-only
   STATUS      current
   DESCRIPTION
      "Path: vrfRouterLtd.performance.qualityMonitor.lastLog.upDown.jitterUpAvrg

       unit name = sec
       formula = 1000 / ; 1000 *"
   ::= {pr1646v2VrfLtdQmEntry 673055232}

pr1646v2VrfLtdQmLastLogUpDownJitterUpPosMax OBJECT-TYPE
   SYNTAX      Integer32
   MAX-ACCESS  read-only
   STATUS      current
   DESCRIPTION
      "Path: vrfRouterLtd.performance.qualityMonitor.lastLog.upDown.jitterUpPosMax

       unit name = sec
       formula = 1000 / ; 1000 *"
   ::= {pr1646v2VrfLtdQmEntry 673055488}

pr1646v2VrfLtdQmLastLogUpDownLossDown OBJECT-TYPE
   SYNTAX      Counter32
   MAX-ACCESS  read-only
   STATUS      current
   DESCRIPTION
      "Path: vrfRouterLtd.performance.qualityMonitor.lastLog.upDown.lossDown

       32 bit unsigned wrappable counter."
   ::= {pr1646v2VrfLtdQmEntry 673057792}

pr1646v2VrfLtdQmLastLogUpDownLossDelayDown OBJECT-TYPE
   SYNTAX      Counter32
   MAX-ACCESS  read-only
   STATUS      current
   DESCRIPTION
      "Path: vrfRouterLtd.performance.qualityMonitor.lastLog.upDown.lossDelayDown

       32 bit unsigned wrappable counter."
   ::= {pr1646v2VrfLtdQmEntry 673058048}

pr1646v2VrfLtdQmLastLogUpDownDelayDownMin OBJECT-TYPE
   SYNTAX      Integer32
   MAX-ACCESS  read-only
   STATUS      current
   DESCRIPTION
      "Path: vrfRouterLtd.performance.qualityMonitor.lastLog.upDown.delayDownMin

       unit name = sec
       formula = 1000 / ; 1000 *"
   ::= {pr1646v2VrfLtdQmEntry 673063680}

pr1646v2VrfLtdQmLastLogUpDownDelayDownAvrg OBJECT-TYPE
   SYNTAX      Integer32
   MAX-ACCESS  read-only
   STATUS      current
   DESCRIPTION
      "Path: vrfRouterLtd.performance.qualityMonitor.lastLog.upDown.delayDownAvrg

       unit name = sec
       formula = 1000 / ; 1000 *"
   ::= {pr1646v2VrfLtdQmEntry 673063936}

pr1646v2VrfLtdQmLastLogUpDownDelayDownMax OBJECT-TYPE
   SYNTAX      Integer32
   MAX-ACCESS  read-only
   STATUS      current
   DESCRIPTION
      "Path: vrfRouterLtd.performance.qualityMonitor.lastLog.upDown.delayDownMax

       unit name = sec
       formula = 1000 / ; 1000 *"
   ::= {pr1646v2VrfLtdQmEntry 673064192}

pr1646v2VrfLtdQmLastLogUpDownJitterDownNegMax OBJECT-TYPE
   SYNTAX      Integer32
   MAX-ACCESS  read-only
   STATUS      current
   DESCRIPTION
      "Path: vrfRouterLtd.performance.qualityMonitor.lastLog.upDown.jitterDownNegMax

       unit name = sec
       formula = 1000 / ; 1000 *"
   ::= {pr1646v2VrfLtdQmEntry 673055744}

pr1646v2VrfLtdQmLastLogUpDownJitterDownAvrg OBJECT-TYPE
   SYNTAX      Integer32
   MAX-ACCESS  read-only
   STATUS      current
   DESCRIPTION
      "Path: vrfRouterLtd.performance.qualityMonitor.lastLog.upDown.jitterDownAvrg

       unit name = sec
       formula = 1000 / ; 1000 *"
   ::= {pr1646v2VrfLtdQmEntry 673056000}

pr1646v2VrfLtdQmLastLogUpDownJitterDownPosMax OBJECT-TYPE
   SYNTAX      Integer32
   MAX-ACCESS  read-only
   STATUS      current
   DESCRIPTION
      "Path: vrfRouterLtd.performance.qualityMonitor.lastLog.upDown.jitterDownPosMax

       unit name = sec
       formula = 1000 / ; 1000 *"
   ::= {pr1646v2VrfLtdQmEntry 673056256}

pr1646v2VrfLtdQmLastLogDate OBJECT-TYPE
   SYNTAX      DisplayString
   MAX-ACCESS  read-only
   STATUS      current
   DESCRIPTION
      "Path: vrfRouterLtd.performance.qualityMonitor.lastLog.date"
   ::= {pr1646v2VrfLtdQmEntry 673120256}

pr1646v2VrfLtdQmAlarm OBJECT-TYPE
   SYNTAX      Integer32
   MAX-ACCESS  read-only
   STATUS      current
   DESCRIPTION
      "Path: vrfRouterLtd.performance.qualityMonitor.alarm

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {pr1646v2VrfLtdQmEntry 251658240}

pr1646v2VrfLtdQmLastError OBJECT-TYPE
   SYNTAX      DisplayString
   MAX-ACCESS  read-only
   STATUS      current
   DESCRIPTION
      "Path: vrfRouterLtd.performance.qualityMonitor.lastError"
   ::= {pr1646v2VrfLtdQmEntry 318767104}

pr1646v2VrfLtdQmLogging OBJECT-TYPE
   SYNTAX      SEQUENCE OF Pr1646v2VrfLtdQmLoggingEntry
   MAX-ACCESS  not-accessible
   STATUS      current
   DESCRIPTION
      ""
   ::= {pr1646v2VrfLtdQm 335544320}

pr1646v2VrfLtdQmLoggingEntry OBJECT-TYPE
   SYNTAX      Pr1646v2VrfLtdQmLoggingEntry
   MAX-ACCESS  not-accessible
   STATUS      current
   DESCRIPTION
      ""
   INDEX      { pr1646v2VrfLtdQmLoggingGlobalIx,
                pr1646v2VrfLtdQmTableIx,
                pr1646v2VrfLtdQmLoggingTableIx }
   ::= {pr1646v2VrfLtdQmLogging 1}

Pr1646v2VrfLtdQmLoggingEntry ::=
   SEQUENCE
      {
      pr1646v2VrfLtdQmLoggingGlobalIx
         GlobalIndex,
      pr1646v2VrfLtdQmLoggingTableIx
         TableIndex,
      pr1646v2VrfLtdQmLoggingSysUpTime
         TimeTicks,
      pr1646v2VrfLtdQmLoggingNbrTxPckt
         Counter32,
      pr1646v2VrfLtdQmLoggingNbrRxPckt
         Counter32,
      pr1646v2VrfLtdQmLoggingError
         Counter32,
      pr1646v2VrfLtdQmLoggingLoss
         Counter32,
      pr1646v2VrfLtdQmLoggingLossDelay
         Counter32,
      pr1646v2VrfLtdQmLoggingDelayMin
         Integer32,
      pr1646v2VrfLtdQmLoggingDelayAvrg
         Integer32,
      pr1646v2VrfLtdQmLoggingDelayMax
         Integer32,
      pr1646v2VrfLtdQmLoggingJitterNegMax
         Integer32,
      pr1646v2VrfLtdQmLoggingJitterAvrg
         Integer32,
      pr1646v2VrfLtdQmLoggingJitterPosMax
         Integer32,
      pr1646v2VrfLtdQmLoggingUpDownStatus
         INTEGER,
      pr1646v2VrfLtdQmLoggingUpDownLossUp
         Counter32,
      pr1646v2VrfLtdQmLoggingUpDownLossDelayUp
         Counter32,
      pr1646v2VrfLtdQmLoggingUpDownDelayUpMin
         Integer32,
      pr1646v2VrfLtdQmLoggingUpDownDelayUpAvrg
         Integer32,
      pr1646v2VrfLtdQmLoggingUpDownDelayUpMax
         Integer32,
      pr1646v2VrfLtdQmLoggingUpDownJitterUpNegMax
         Integer32,
      pr1646v2VrfLtdQmLoggingUpDownJitterUpAvrg
         Integer32,
      pr1646v2VrfLtdQmLoggingUpDownJitterUpPosMax
         Integer32,
      pr1646v2VrfLtdQmLoggingUpDownLossDown
         Counter32,
      pr1646v2VrfLtdQmLoggingUpDownLossDelayDown
         Counter32,
      pr1646v2VrfLtdQmLoggingUpDownDelayDownMin
         Integer32,
      pr1646v2VrfLtdQmLoggingUpDownDelayDownAvrg
         Integer32,
      pr1646v2VrfLtdQmLoggingUpDownDelayDownMax
         Integer32,
      pr1646v2VrfLtdQmLoggingUpDownJitterDownNegMax
         Integer32,
      pr1646v2VrfLtdQmLoggingUpDownJitterDownAvrg
         Integer32,
      pr1646v2VrfLtdQmLoggingUpDownJitterDownPosMax
         Integer32,
      pr1646v2VrfLtdQmLoggingDate
         DisplayString
      }

pr1646v2VrfLtdQmLoggingGlobalIx OBJECT-TYPE
   SYNTAX      GlobalIndex
   MAX-ACCESS  not-accessible
   STATUS      current
   DESCRIPTION
      "The value of the tlsCntTreeGlobalIndex of the MANAGED OBJECT."
   ::= {pr1646v2VrfLtdQmLoggingEntry 10}

pr1646v2VrfLtdQmLoggingTableIx OBJECT-TYPE
   SYNTAX      TableIndex
   MAX-ACCESS  not-accessible
   STATUS      current
   DESCRIPTION
      ""
   ::= {pr1646v2VrfLtdQmLoggingEntry 11}

pr1646v2VrfLtdQmLoggingSysUpTime OBJECT-TYPE
   SYNTAX      TimeTicks
   MAX-ACCESS  read-only
   STATUS      current
   DESCRIPTION
      "Path: vrfRouterLtd.performance.qualityMonitor.logging.sysUpTime

       Time in centi-second."
   ::= {pr1646v2VrfLtdQmLoggingEntry 16777216}

pr1646v2VrfLtdQmLoggingNbrTxPckt OBJECT-TYPE
   SYNTAX      Counter32
   MAX-ACCESS  read-only
   STATUS      current
   DESCRIPTION
      "Path: vrfRouterLtd.performance.qualityMonitor.logging.nbrOfTxPackets

       32 bit unsigned wrappable counter."
   ::= {pr1646v2VrfLtdQmLoggingEntry 50331648}

pr1646v2VrfLtdQmLoggingNbrRxPckt OBJECT-TYPE
   SYNTAX      Counter32
   MAX-ACCESS  read-only
   STATUS      current
   DESCRIPTION
      "Path: vrfRouterLtd.performance.qualityMonitor.logging.nbrOfRxPackets

       32 bit unsigned wrappable counter."
   ::= {pr1646v2VrfLtdQmLoggingEntry 67108864}

pr1646v2VrfLtdQmLoggingError OBJECT-TYPE
   SYNTAX      Counter32
   MAX-ACCESS  read-only
   STATUS      current
   DESCRIPTION
      "Path: vrfRouterLtd.performance.qualityMonitor.logging.error

       32 bit unsigned wrappable counter."
   ::= {pr1646v2VrfLtdQmLoggingEntry 285212672}

pr1646v2VrfLtdQmLoggingLoss OBJECT-TYPE
   SYNTAX      Counter32
   MAX-ACCESS  read-only
   STATUS      current
   DESCRIPTION
      "Path: vrfRouterLtd.performance.qualityMonitor.logging.loss

       32 bit unsigned wrappable counter."
   ::= {pr1646v2VrfLtdQmLoggingEntry 100663296}

pr1646v2VrfLtdQmLoggingLossDelay OBJECT-TYPE
   SYNTAX      Counter32
   MAX-ACCESS  read-only
   STATUS      current
   DESCRIPTION
      "Path: vrfRouterLtd.performance.qualityMonitor.logging.lossDelay

       32 bit unsigned wrappable counter."
   ::= {pr1646v2VrfLtdQmLoggingEntry 268435456}

pr1646v2VrfLtdQmLoggingDelayMin OBJECT-TYPE
   SYNTAX      Integer32
   MAX-ACCESS  read-only
   STATUS      current
   DESCRIPTION
      "Path: vrfRouterLtd.performance.qualityMonitor.logging.delayMin

       unit name = sec
       formula = 1000 / ; 1000 *"
   ::= {pr1646v2VrfLtdQmLoggingEntry 184549376}

pr1646v2VrfLtdQmLoggingDelayAvrg OBJECT-TYPE
   SYNTAX      Integer32
   MAX-ACCESS  read-only
   STATUS      current
   DESCRIPTION
      "Path: vrfRouterLtd.performance.qualityMonitor.logging.delayAvrg

       unit name = sec
       formula = 1000 / ; 1000 *"
   ::= {pr1646v2VrfLtdQmLoggingEntry 117440512}

pr1646v2VrfLtdQmLoggingDelayMax OBJECT-TYPE
   SYNTAX      Integer32
   MAX-ACCESS  read-only
   STATUS      current
   DESCRIPTION
      "Path: vrfRouterLtd.performance.qualityMonitor.logging.delayMax

       unit name = sec
       formula = 1000 / ; 1000 *"
   ::= {pr1646v2VrfLtdQmLoggingEntry 134217728}

pr1646v2VrfLtdQmLoggingJitterNegMax OBJECT-TYPE
   SYNTAX      Integer32
   MAX-ACCESS  read-only
   STATUS      current
   DESCRIPTION
      "Path: vrfRouterLtd.performance.qualityMonitor.logging.jitterNegMax

       unit name = sec
       formula = 1000 / ; 1000 *"
   ::= {pr1646v2VrfLtdQmLoggingEntry 234881024}

pr1646v2VrfLtdQmLoggingJitterAvrg OBJECT-TYPE
   SYNTAX      Integer32
   MAX-ACCESS  read-only
   STATUS      current
   DESCRIPTION
      "Path: vrfRouterLtd.performance.qualityMonitor.logging.jitterAvrg

       unit name = sec
       formula = 1000 / ; 1000 *"
   ::= {pr1646v2VrfLtdQmLoggingEntry 150994944}

pr1646v2VrfLtdQmLoggingJitterPosMax OBJECT-TYPE
   SYNTAX      Integer32
   MAX-ACCESS  read-only
   STATUS      current
   DESCRIPTION
      "Path: vrfRouterLtd.performance.qualityMonitor.logging.jitterPosMax

       unit name = sec
       formula = 1000 / ; 1000 *"
   ::= {pr1646v2VrfLtdQmLoggingEntry 167772160}

pr1646v2VrfLtdQmLoggingUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfRouterLtd.performance.qualityMonitor.logging.upDown.status

       Possibilities:
               notInUse   (3)
               onlyJitter   (1)
               jitterAndLoss   (2)
               all   (4)
               onlyLoss   (8)"
   ::= {pr1646v2VrfLtdQmLoggingEntry 504627200}

pr1646v2VrfLtdQmLoggingUpDownLossUp OBJECT-TYPE
   SYNTAX      Counter32
   MAX-ACCESS  read-only
   STATUS      current
   DESCRIPTION
      "Path: vrfRouterLtd.performance.qualityMonitor.logging.upDown.lossUp

       32 bit unsigned wrappable counter."
   ::= {pr1646v2VrfLtdQmLoggingEntry 503971840}

pr1646v2VrfLtdQmLoggingUpDownLossDelayUp OBJECT-TYPE
   SYNTAX      Counter32
   MAX-ACCESS  read-only
   STATUS      current
   DESCRIPTION
      "Path: vrfRouterLtd.performance.qualityMonitor.logging.upDown.lossDelayUp

       32 bit unsigned wrappable counter."
   ::= {pr1646v2VrfLtdQmLoggingEntry 504037376}

pr1646v2VrfLtdQmLoggingUpDownDelayUpMin OBJECT-TYPE
   SYNTAX      Integer32
   MAX-ACCESS  read-only
   STATUS      current
   DESCRIPTION
      "Path: vrfRouterLtd.performance.qualityMonitor.logging.upDown.delayUpMin

       unit name = sec
       formula = 1000 / ; 1000 *"
   ::= {pr1646v2VrfLtdQmLoggingEntry 505282560}

pr1646v2VrfLtdQmLoggingUpDownDelayUpAvrg OBJECT-TYPE
   SYNTAX      Integer32
   MAX-ACCESS  read-only
   STATUS      current
   DESCRIPTION
      "Path: vrfRouterLtd.performance.qualityMonitor.logging.upDown.delayUpAvrg

       unit name = sec
       formula = 1000 / ; 1000 *"
   ::= {pr1646v2VrfLtdQmLoggingEntry 505348096}

pr1646v2VrfLtdQmLoggingUpDownDelayUpMax OBJECT-TYPE
   SYNTAX      Integer32
   MAX-ACCESS  read-only
   STATUS      current
   DESCRIPTION
      "Path: vrfRouterLtd.performance.qualityMonitor.logging.upDown.delayUpMax

       unit name = sec
       formula = 1000 / ; 1000 *"
   ::= {pr1646v2VrfLtdQmLoggingEntry 505413632}

pr1646v2VrfLtdQmLoggingUpDownJitterUpNegMax OBJECT-TYPE
   SYNTAX      Integer32
   MAX-ACCESS  read-only
   STATUS      current
   DESCRIPTION
      "Path: vrfRouterLtd.performance.qualityMonitor.logging.upDown.jitterUpNegMax

       unit name = sec
       formula = 1000 / ; 1000 *"
   ::= {pr1646v2VrfLtdQmLoggingEntry 503382016}

pr1646v2VrfLtdQmLoggingUpDownJitterUpAvrg OBJECT-TYPE
   SYNTAX      Integer32
   MAX-ACCESS  read-only
   STATUS      current
   DESCRIPTION
      "Path: vrfRouterLtd.performance.qualityMonitor.logging.upDown.jitterUpAvrg

       unit name = sec
       formula = 1000 / ; 1000 *"
   ::= {pr1646v2VrfLtdQmLoggingEntry 503447552}

pr1646v2VrfLtdQmLoggingUpDownJitterUpPosMax OBJECT-TYPE
   SYNTAX      Integer32
   MAX-ACCESS  read-only
   STATUS      current
   DESCRIPTION
      "Path: vrfRouterLtd.performance.qualityMonitor.logging.upDown.jitterUpPosMax

       unit name = sec
       formula = 1000 / ; 1000 *"
   ::= {pr1646v2VrfLtdQmLoggingEntry 503513088}

pr1646v2VrfLtdQmLoggingUpDownLossDown OBJECT-TYPE
   SYNTAX      Counter32
   MAX-ACCESS  read-only
   STATUS      current
   DESCRIPTION
      "Path: vrfRouterLtd.performance.qualityMonitor.logging.upDown.lossDown

       32 bit unsigned wrappable counter."
   ::= {pr1646v2VrfLtdQmLoggingEntry 504102912}

pr1646v2VrfLtdQmLoggingUpDownLossDelayDown OBJECT-TYPE
   SYNTAX      Counter32
   MAX-ACCESS  read-only
   STATUS      current
   DESCRIPTION
      "Path: vrfRouterLtd.performance.qualityMonitor.logging.upDown.lossDelayDown

       32 bit unsigned wrappable counter."
   ::= {pr1646v2VrfLtdQmLoggingEntry 504168448}

pr1646v2VrfLtdQmLoggingUpDownDelayDownMin OBJECT-TYPE
   SYNTAX      Integer32
   MAX-ACCESS  read-only
   STATUS      current
   DESCRIPTION
      "Path: vrfRouterLtd.performance.qualityMonitor.logging.upDown.delayDownMin

       unit name = sec
       formula = 1000 / ; 1000 *"
   ::= {pr1646v2VrfLtdQmLoggingEntry 505610240}

pr1646v2VrfLtdQmLoggingUpDownDelayDownAvrg OBJECT-TYPE
   SYNTAX      Integer32
   MAX-ACCESS  read-only
   STATUS      current
   DESCRIPTION
      "Path: vrfRouterLtd.performance.qualityMonitor.logging.upDown.delayDownAvrg

       unit name = sec
       formula = 1000 / ; 1000 *"
   ::= {pr1646v2VrfLtdQmLoggingEntry 505675776}

pr1646v2VrfLtdQmLoggingUpDownDelayDownMax OBJECT-TYPE
   SYNTAX      Integer32
   MAX-ACCESS  read-only
   STATUS      current
   DESCRIPTION
      "Path: vrfRouterLtd.performance.qualityMonitor.logging.upDown.delayDownMax

       unit name = sec
       formula = 1000 / ; 1000 *"
   ::= {pr1646v2VrfLtdQmLoggingEntry 505741312}

pr1646v2VrfLtdQmLoggingUpDownJitterDownNegMax OBJECT-TYPE
   SYNTAX      Integer32
   MAX-ACCESS  read-only
   STATUS      current
   DESCRIPTION
      "Path: vrfRouterLtd.performance.qualityMonitor.logging.upDown.jitterDownNegMax

       unit name = sec
       formula = 1000 / ; 1000 *"
   ::= {pr1646v2VrfLtdQmLoggingEntry 503578624}

pr1646v2VrfLtdQmLoggingUpDownJitterDownAvrg OBJECT-TYPE
   SYNTAX      Integer32
   MAX-ACCESS  read-only
   STATUS      current
   DESCRIPTION
      "Path: vrfRouterLtd.performance.qualityMonitor.logging.upDown.jitterDownAvrg

       unit name = sec
       formula = 1000 / ; 1000 *"
   ::= {pr1646v2VrfLtdQmLoggingEntry 503644160}

pr1646v2VrfLtdQmLoggingUpDownJitterDownPosMax OBJECT-TYPE
   SYNTAX      Integer32
   MAX-ACCESS  read-only
   STATUS      current
   DESCRIPTION
      "Path: vrfRouterLtd.performance.qualityMonitor.logging.upDown.jitterDownPosMax

       unit name = sec
       formula = 1000 / ; 1000 *"
   ::= {pr1646v2VrfLtdQmLoggingEntry 503709696}

pr1646v2VrfLtdQmLoggingDate OBJECT-TYPE
   SYNTAX      DisplayString
   MAX-ACCESS  read-only
   STATUS      current
   DESCRIPTION
      "Path: vrfRouterLtd.performance.qualityMonitor.logging.date"
   ::= {pr1646v2VrfLtdQmLoggingEntry 520093696}

pr1646v2VrfLtdQmLoggingBin OBJECT-TYPE
   SYNTAX      SEQUENCE OF Pr1646v2VrfLtdQmLoggingBinEntry
   MAX-ACCESS  not-accessible
   STATUS      current
   DESCRIPTION
      ""
   ::= {pr1646v2VrfLtdQm 337641472}

pr1646v2VrfLtdQmLoggingBinEntry OBJECT-TYPE
   SYNTAX      Pr1646v2VrfLtdQmLoggingBinEntry
   MAX-ACCESS  not-accessible
   STATUS      current
   DESCRIPTION
      ""
   INDEX      { pr1646v2VrfLtdQmLoggingBinGlobalIx,
                pr1646v2VrfLtdQmTableIx,
                pr1646v2VrfLtdQmLoggingTableIx,
                pr1646v2VrfLtdQmLoggingBinTableIx }
   ::= {pr1646v2VrfLtdQmLoggingBin 1}

Pr1646v2VrfLtdQmLoggingBinEntry ::=
   SEQUENCE
      {
      pr1646v2VrfLtdQmLoggingBinGlobalIx
         GlobalIndex,
      pr1646v2VrfLtdQmLoggingBinTableIx
         TableIndex,
      pr1646v2VrfLtdQmLoggingBinName
         INTEGER,
      pr1646v2VrfLtdQmLoggingBinType
         INTEGER,
      pr1646v2VrfLtdQmLoggingBinMinMin
         Counter32,
      pr1646v2VrfLtdQmLoggingBinMin
         Integer32,
      pr1646v2VrfLtdQmLoggingBinMinBin1
         Counter32,
      pr1646v2VrfLtdQmLoggingBinBin2
         Counter32,
      pr1646v2VrfLtdQmLoggingBinBin3
         Counter32,
      pr1646v2VrfLtdQmLoggingBinBin4
         Counter32,
      pr1646v2VrfLtdQmLoggingBinBin5
         Counter32,
      pr1646v2VrfLtdQmLoggingBinBin6
         Counter32,
      pr1646v2VrfLtdQmLoggingBinBin7
         Counter32,
      pr1646v2VrfLtdQmLoggingBinMaxBin8
         Counter32,
      pr1646v2VrfLtdQmLoggingBinMax
         Integer32,
      pr1646v2VrfLtdQmLoggingBinPlusMax
         Counter32
      }

pr1646v2VrfLtdQmLoggingBinGlobalIx OBJECT-TYPE
   SYNTAX      GlobalIndex
   MAX-ACCESS  not-accessible
   STATUS      current
   DESCRIPTION
      "The value of the tlsCntTreeGlobalIndex of the MANAGED OBJECT."
   ::= {pr1646v2VrfLtdQmLoggingBinEntry 10}

pr1646v2VrfLtdQmLoggingBinTableIx OBJECT-TYPE
   SYNTAX      TableIndex
   MAX-ACCESS  not-accessible
   STATUS      current
   DESCRIPTION
      ""
   ::= {pr1646v2VrfLtdQmLoggingBinEntry 11}

pr1646v2VrfLtdQmLoggingBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: vrfRouterLtd.performance.qualityMonitor.logging.bin.name

       Possibilities:
               delay   (1)
               delayUp   (2)
               delayDown   (3)
               jitter   (4)
               jitterUp   (5)
               jitterDown   (6)"
   ::= {pr1646v2VrfLtdQmLoggingBinEntry 503316480}

pr1646v2VrfLtdQmLoggingBinType OBJECT-TYPE
   SYNTAX      INTEGER
               {
               fd (1),
               fdr (2),
               notInUse (3),
               ifdv (4)
               }
   MAX-ACCESS  read-only
   STATUS      current
   DESCRIPTION
      "Path: vrfRouterLtd.performance.qualityMonitor.logging.bin.type

       Possibilities:
               fd   (1)
               fdr   (2)
               notInUse   (3)
               ifdv   (4)"
   ::= {pr1646v2VrfLtdQmLoggingBinEntry 520093696}

pr1646v2VrfLtdQmLoggingBinMinMin OBJECT-TYPE
   SYNTAX      Counter32
   MAX-ACCESS  read-only
   STATUS      current
   DESCRIPTION
      "Path: vrfRouterLtd.performance.qualityMonitor.logging.bin.minMin

       32 bit unsigned wrappable counter."
   ::= {pr1646v2VrfLtdQmLoggingBinEntry 16777216}

pr1646v2VrfLtdQmLoggingBinMin OBJECT-TYPE
   SYNTAX      Integer32
   MAX-ACCESS  read-only
   STATUS      current
   DESCRIPTION
      "Path: vrfRouterLtd.performance.qualityMonitor.logging.bin.min

       unit name = sec
       formula = 1000 / ; 1000 *"
   ::= {pr1646v2VrfLtdQmLoggingBinEntry 352321536}

pr1646v2VrfLtdQmLoggingBinMinBin1 OBJECT-TYPE
   SYNTAX      Counter32
   MAX-ACCESS  read-only
   STATUS      current
   DESCRIPTION
      "Path: vrfRouterLtd.performance.qualityMonitor.logging.bin.minBin1

       32 bit unsigned wrappable counter."
   ::= {pr1646v2VrfLtdQmLoggingBinEntry 33554432}

pr1646v2VrfLtdQmLoggingBinBin2 OBJECT-TYPE
   SYNTAX      Counter32
   MAX-ACCESS  read-only
   STATUS      current
   DESCRIPTION
      "Path: vrfRouterLtd.performance.qualityMonitor.logging.bin.bin2

       32 bit unsigned wrappable counter."
   ::= {pr1646v2VrfLtdQmLoggingBinEntry 50331648}

pr1646v2VrfLtdQmLoggingBinBin3 OBJECT-TYPE
   SYNTAX      Counter32
   MAX-ACCESS  read-only
   STATUS      current
   DESCRIPTION
      "Path: vrfRouterLtd.performance.qualityMonitor.logging.bin.bin3

       32 bit unsigned wrappable counter."
   ::= {pr1646v2VrfLtdQmLoggingBinEntry 67108864}

pr1646v2VrfLtdQmLoggingBinBin4 OBJECT-TYPE
   SYNTAX      Counter32
   MAX-ACCESS  read-only
   STATUS      current
   DESCRIPTION
      "Path: vrfRouterLtd.performance.qualityMonitor.logging.bin.bin4

       32 bit unsigned wrappable counter."
   ::= {pr1646v2VrfLtdQmLoggingBinEntry 83886080}

pr1646v2VrfLtdQmLoggingBinBin5 OBJECT-TYPE
   SYNTAX      Counter32
   MAX-ACCESS  read-only
   STATUS      current
   DESCRIPTION
      "Path: vrfRouterLtd.performance.qualityMonitor.logging.bin.bin5

       32 bit unsigned wrappable counter."
   ::= {pr1646v2VrfLtdQmLoggingBinEntry 100663296}

pr1646v2VrfLtdQmLoggingBinBin6 OBJECT-TYPE
   SYNTAX      Counter32
   MAX-ACCESS  read-only
   STATUS      current
   DESCRIPTION
      "Path: vrfRouterLtd.performance.qualityMonitor.logging.bin.bin6

       32 bit unsigned wrappable counter."
   ::= {pr1646v2VrfLtdQmLoggingBinEntry 117440512}

pr1646v2VrfLtdQmLoggingBinBin7 OBJECT-TYPE
   SYNTAX      Counter32
   MAX-ACCESS  read-only
   STATUS      current
   DESCRIPTION
      "Path: vrfRouterLtd.performance.qualityMonitor.logging.bin.bin7

       32 bit unsigned wrappable counter."
   ::= {pr1646v2VrfLtdQmLoggingBinEntry 134217728}

pr1646v2VrfLtdQmLoggingBinMaxBin8 OBJECT-TYPE
   SYNTAX      Counter32
   MAX-ACCESS  read-only
   STATUS      current
   DESCRIPTION
      "Path: vrfRouterLtd.performance.qualityMonitor.logging.bin.maxBin8

       32 bit unsigned wrappable counter."
   ::= {pr1646v2VrfLtdQmLoggingBinEntry 150994944}

pr1646v2VrfLtdQmLoggingBinMax OBJECT-TYPE
   SYNTAX      Integer32
   MAX-ACCESS  read-only
   STATUS      current
   DESCRIPTION
      "Path: vrfRouterLtd.performance.qualityMonitor.logging.bin.max

       unit name = sec
       formula = 1000 / ; 1000 *"
   ::= {pr1646v2VrfLtdQmLoggingBinEntry 369098752}

pr1646v2VrfLtdQmLoggingBinPlusMax OBJECT-TYPE
   SYNTAX      Counter32
   MAX-ACCESS  read-only
   STATUS      current
   DESCRIPTION
      "Path: vrfRouterLtd.performance.qualityMonitor.logging.bin.plusMax

       32 bit unsigned wrappable counter."
   ::= {pr1646v2VrfLtdQmLoggingBinEntry 167772160}

pr1646v2VrfLtdQmLastLogBin OBJECT-TYPE
   SYNTAX      SEQUENCE OF Pr1646v2VrfLtdQmLastLogBinEntry
   MAX-ACCESS  not-accessible
   STATUS      current
   DESCRIPTION
      ""
   ::= {pr1646v2VrfLtdQm 673185792}

pr1646v2VrfLtdQmLastLogBinEntry OBJECT-TYPE
   SYNTAX      Pr1646v2VrfLtdQmLastLogBinEntry
   MAX-ACCESS  not-accessible
   STATUS      current
   DESCRIPTION
      ""
   INDEX      { pr1646v2VrfLtdQmLastLogBinGlobalIx,
                pr1646v2VrfLtdQmTableIx,
                pr1646v2VrfLtdQmLastLogBinTableIx }
   ::= {pr1646v2VrfLtdQmLastLogBin 1}

Pr1646v2VrfLtdQmLastLogBinEntry ::=
   SEQUENCE
      {
      pr1646v2VrfLtdQmLastLogBinGlobalIx
         GlobalIndex,
      pr1646v2VrfLtdQmLastLogBinTableIx
         TableIndex,
      pr1646v2VrfLtdQmLastLogBinName
         INTEGER,
      pr1646v2VrfLtdQmLastLogBinType
         INTEGER,
      pr1646v2VrfLtdQmLastLogBinMinMin
         Counter32,
      pr1646v2VrfLtdQmLastLogBinMin
         Integer32,
      pr1646v2VrfLtdQmLastLogBinMinBin1
         Counter32,
      pr1646v2VrfLtdQmLastLogBinBin2
         Counter32,
      pr1646v2VrfLtdQmLastLogBinBin3
         Counter32,
      pr1646v2VrfLtdQmLastLogBinBin4
         Counter32,
      pr1646v2VrfLtdQmLastLogBinBin5
         Counter32,
      pr1646v2VrfLtdQmLastLogBinBin6
         Counter32,
      pr1646v2VrfLtdQmLastLogBinBin7
         Counter32,
      pr1646v2VrfLtdQmLastLogBinMaxBin8
         Counter32,
      pr1646v2VrfLtdQmLastLogBinMax
         Integer32,
      pr1646v2VrfLtdQmLastLogBinPlusMax
         Counter32
      }

pr1646v2VrfLtdQmLastLogBinGlobalIx OBJECT-TYPE
   SYNTAX      GlobalIndex
   MAX-ACCESS  not-accessible
   STATUS      current
   DESCRIPTION
      "The value of the tlsCntTreeGlobalIndex of the MANAGED OBJECT."
   ::= {pr1646v2VrfLtdQmLastLogBinEntry 10}

pr1646v2VrfLtdQmLastLogBinTableIx OBJECT-TYPE
   SYNTAX      TableIndex
   MAX-ACCESS  not-accessible
   STATUS      current
   DESCRIPTION
      ""
   ::= {pr1646v2VrfLtdQmLastLogBinEntry 11}

pr1646v2VrfLtdQmLastLogBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: vrfRouterLtd.performance.qualityMonitor.lastLog.bin.name

       Possibilities:
               delay   (1)
               delayUp   (2)
               delayDown   (3)
               jitter   (4)
               jitterUp   (5)
               jitterDown   (6)"
   ::= {pr1646v2VrfLtdQmLastLogBinEntry 503316480}

pr1646v2VrfLtdQmLastLogBinType OBJECT-TYPE
   SYNTAX      INTEGER
               {
               fd (1),
               fdr (2),
               notInUse (3),
               ifdv (4)
               }
   MAX-ACCESS  read-only
   STATUS      current
   DESCRIPTION
      "Path: vrfRouterLtd.performance.qualityMonitor.lastLog.bin.type

       Possibilities:
               fd   (1)
               fdr   (2)
               notInUse   (3)
               ifdv   (4)"
   ::= {pr1646v2VrfLtdQmLastLogBinEntry 520093696}

pr1646v2VrfLtdQmLastLogBinMinMin OBJECT-TYPE
   SYNTAX      Counter32
   MAX-ACCESS  read-only
   STATUS      current
   DESCRIPTION
      "Path: vrfRouterLtd.performance.qualityMonitor.lastLog.bin.minMin

       32 bit unsigned wrappable counter."
   ::= {pr1646v2VrfLtdQmLastLogBinEntry 16777216}

pr1646v2VrfLtdQmLastLogBinMin OBJECT-TYPE
   SYNTAX      Integer32
   MAX-ACCESS  read-only
   STATUS      current
   DESCRIPTION
      "Path: vrfRouterLtd.performance.qualityMonitor.lastLog.bin.min

       unit name = sec
       formula = 1000 / ; 1000 *"
   ::= {pr1646v2VrfLtdQmLastLogBinEntry 352321536}

pr1646v2VrfLtdQmLastLogBinMinBin1 OBJECT-TYPE
   SYNTAX      Counter32
   MAX-ACCESS  read-only
   STATUS      current
   DESCRIPTION
      "Path: vrfRouterLtd.performance.qualityMonitor.lastLog.bin.minBin1

       32 bit unsigned wrappable counter."
   ::= {pr1646v2VrfLtdQmLastLogBinEntry 33554432}

pr1646v2VrfLtdQmLastLogBinBin2 OBJECT-TYPE
   SYNTAX      Counter32
   MAX-ACCESS  read-only
   STATUS      current
   DESCRIPTION
      "Path: vrfRouterLtd.performance.qualityMonitor.lastLog.bin.bin2

       32 bit unsigned wrappable counter."
   ::= {pr1646v2VrfLtdQmLastLogBinEntry 50331648}

pr1646v2VrfLtdQmLastLogBinBin3 OBJECT-TYPE
   SYNTAX      Counter32
   MAX-ACCESS  read-only
   STATUS      current
   DESCRIPTION
      "Path: vrfRouterLtd.performance.qualityMonitor.lastLog.bin.bin3

       32 bit unsigned wrappable counter."
   ::= {pr1646v2VrfLtdQmLastLogBinEntry 67108864}

pr1646v2VrfLtdQmLastLogBinBin4 OBJECT-TYPE
   SYNTAX      Counter32
   MAX-ACCESS  read-only
   STATUS      current
   DESCRIPTION
      "Path: vrfRouterLtd.performance.qualityMonitor.lastLog.bin.bin4

       32 bit unsigned wrappable counter."
   ::= {pr1646v2VrfLtdQmLastLogBinEntry 83886080}

pr1646v2VrfLtdQmLastLogBinBin5 OBJECT-TYPE
   SYNTAX      Counter32
   MAX-ACCESS  read-only
   STATUS      current
   DESCRIPTION
      "Path: vrfRouterLtd.performance.qualityMonitor.lastLog.bin.bin5

       32 bit unsigned wrappable counter."
   ::= {pr1646v2VrfLtdQmLastLogBinEntry 100663296}

pr1646v2VrfLtdQmLastLogBinBin6 OBJECT-TYPE
   SYNTAX      Counter32
   MAX-ACCESS  read-only
   STATUS      current
   DESCRIPTION
      "Path: vrfRouterLtd.performance.qualityMonitor.lastLog.bin.bin6

       32 bit unsigned wrappable counter."
   ::= {pr1646v2VrfLtdQmLastLogBinEntry 117440512}

pr1646v2VrfLtdQmLastLogBinBin7 OBJECT-TYPE
   SYNTAX      Counter32
   MAX-ACCESS  read-only
   STATUS      current
   DESCRIPTION
      "Path: vrfRouterLtd.performance.qualityMonitor.lastLog.bin.bin7

       32 bit unsigned wrappable counter."
   ::= {pr1646v2VrfLtdQmLastLogBinEntry 134217728}

pr1646v2VrfLtdQmLastLogBinMaxBin8 OBJECT-TYPE
   SYNTAX      Counter32
   MAX-ACCESS  read-only
   STATUS      current
   DESCRIPTION
      "Path: vrfRouterLtd.performance.qualityMonitor.lastLog.bin.maxBin8

       32 bit unsigned wrappable counter."
   ::= {pr1646v2VrfLtdQmLastLogBinEntry 150994944}

pr1646v2VrfLtdQmLastLogBinMax OBJECT-TYPE
   SYNTAX      Integer32
   MAX-ACCESS  read-only
   STATUS      current
   DESCRIPTION
      "Path: vrfRouterLtd.performance.qualityMonitor.lastLog.bin.max

       unit name = sec
       formula = 1000 / ; 1000 *"
   ::= {pr1646v2VrfLtdQmLastLogBinEntry 369098752}

pr1646v2VrfLtdQmLastLogBinPlusMax OBJECT-TYPE
   SYNTAX      Counter32
   MAX-ACCESS  read-only
   STATUS      current
   DESCRIPTION
      "Path: vrfRouterLtd.performance.qualityMonitor.lastLog.bin.plusMax

       32 bit unsigned wrappable counter."
   ::= {pr1646v2VrfLtdQmLastLogBinEntry 167772160}


pr1646v2VrfLtdUdpServer OBJECT IDENTIFIER ::= {pr1646v2VrfLtd 16}

pr1646v2VrfLtdUdpServerSSCTable OBJECT-TYPE
   SYNTAX      SEQUENCE OF Pr1646v2VrfLtdUdpServerEntry
   MAX-ACCESS  not-accessible
   STATUS      current
   DESCRIPTION
      "udpServer"
   ::= {pr1646v2VrfLtdUdpServer 1}

pr1646v2VrfLtdUdpServerEntry OBJECT-TYPE
   SYNTAX      Pr1646v2VrfLtdUdpServerEntry
   MAX-ACCESS  not-accessible
   STATUS      current
   DESCRIPTION
      ""
   INDEX      { pr1646v2VrfLtdUdpServerGlobalIx,
                pr1646v2VrfLtdUdpServerTableIx }
   ::= {pr1646v2VrfLtdUdpServerSSCTable 1}

Pr1646v2VrfLtdUdpServerEntry ::=
   SEQUENCE
      {
      pr1646v2VrfLtdUdpServerGlobalIx
         GlobalIndex,
      pr1646v2VrfLtdUdpServerTableIx
         TableIndex,
      pr1646v2VrfLtdUdpServerDestinationPort
         Integer32,
      pr1646v2VrfLtdUdpServerActiveSessions
         Gauge32,
      pr1646v2VrfLtdUdpServerNbrPckt
         Counter64
      }

pr1646v2VrfLtdUdpServerGlobalIx OBJECT-TYPE
   SYNTAX      GlobalIndex
   MAX-ACCESS  not-accessible
   STATUS      current
   DESCRIPTION
      "The value of the tlsCntTreeGlobalIndex of the MANAGED OBJECT."
   ::= {pr1646v2VrfLtdUdpServerEntry 10}

pr1646v2VrfLtdUdpServerTableIx OBJECT-TYPE
   SYNTAX      TableIndex
   MAX-ACCESS  not-accessible
   STATUS      current
   DESCRIPTION
      ""
   ::= {pr1646v2VrfLtdUdpServerEntry 11}

pr1646v2VrfLtdUdpServerDestinationPort OBJECT-TYPE
   SYNTAX      Integer32
   MAX-ACCESS  read-only
   STATUS      current
   DESCRIPTION
      "Path: vrfRouterLtd.performance.udpServer.destinationPort"
   ::= {pr1646v2VrfLtdUdpServerEntry 16777216}

pr1646v2VrfLtdUdpServerActiveSessions OBJECT-TYPE
   SYNTAX      Gauge32
   MAX-ACCESS  read-only
   STATUS      current
   DESCRIPTION
      "Path: vrfRouterLtd.performance.udpServer.activeSessions

       32 bit unsigned gauge value."
   ::= {pr1646v2VrfLtdUdpServerEntry 33554432}

pr1646v2VrfLtdUdpServerNbrPckt OBJECT-TYPE
   SYNTAX      Counter64
   MAX-ACCESS  read-only
   STATUS      current
   DESCRIPTION
      "Path: vrfRouterLtd.performance.udpServer.nbrOfPackets

       64 bit unsigned wrappable counter."
   ::= {pr1646v2VrfLtdUdpServerEntry 50331648}

pr1646v2VrfLtdUdpServerSessions OBJECT-TYPE
   SYNTAX      SEQUENCE OF Pr1646v2VrfLtdUdpServerSessionsEntry
   MAX-ACCESS  not-accessible
   STATUS      current
   DESCRIPTION
      ""
   ::= {pr1646v2VrfLtdUdpServer 67108864}

pr1646v2VrfLtdUdpServerSessionsEntry OBJECT-TYPE
   SYNTAX      Pr1646v2VrfLtdUdpServerSessionsEntry
   MAX-ACCESS  not-accessible
   STATUS      current
   DESCRIPTION
      ""
   INDEX      { pr1646v2VrfLtdUdpServerSessionsGlobalIx,
                pr1646v2VrfLtdUdpServerTableIx,
                pr1646v2VrfLtdUdpServerSessionsTableIx }
   ::= {pr1646v2VrfLtdUdpServerSessions 1}

Pr1646v2VrfLtdUdpServerSessionsEntry ::=
   SEQUENCE
      {
      pr1646v2VrfLtdUdpServerSessionsGlobalIx
         GlobalIndex,
      pr1646v2VrfLtdUdpServerSessionsTableIx
         TableIndex,
      pr1646v2VrfLtdUdpServerSessionsSourceIpAddress
         IpAddress,
      pr1646v2VrfLtdUdpServerSessionsSourcePort
         Integer32,
      pr1646v2VrfLtdUdpServerSessionsNbrPckt
         Counter64,
      pr1646v2VrfLtdUdpServerSessionsFirstActivityTime
         TimeTicks,
      pr1646v2VrfLtdUdpServerSessionsLastActivityTime
         TimeTicks,
      pr1646v2VrfLtdUdpServerSessionsHalfWayStatus
         INTEGER,
      pr1646v2VrfLtdUdpServerSessionsHalfWayReceived
         Counter64,
      pr1646v2VrfLtdUdpServerSessionsHalfWayPacketLoss
         Counter64,
      pr1646v2VrfLtdUdpServerSessionsHalfWayOutOfSequence
         Counter64,
      pr1646v2VrfLtdUdpServerSessionsHalfWayCrcErrors
         Counter64,
      pr1646v2VrfLtdUdpServerSessionsHalfWayLengthErrors
         Counter64,
      pr1646v2VrfLtdUdpServerSessionsHalfWayJitter
         INTEGER,
      pr1646v2VrfLtdUdpServerSessionsHalfWayJitterAvrg
         INTEGER,
      pr1646v2VrfLtdUdpServerSessionsHalfWayJitterMax
         INTEGER,
      pr1646v2VrfLtdUdpServerSessionsHalfWayReceivedLength
         Counter64,
      pr1646v2VrfLtdUdpServerSessionsHalfWayLastFault
         Counter64,
      pr1646v2VrfLtdUdpServerSessionsHalfWayLastSeqnr
         Counter64
      }

pr1646v2VrfLtdUdpServerSessionsGlobalIx OBJECT-TYPE
   SYNTAX      GlobalIndex
   MAX-ACCESS  not-accessible
   STATUS      current
   DESCRIPTION
      "The value of the tlsCntTreeGlobalIndex of the MANAGED OBJECT."
   ::= {pr1646v2VrfLtdUdpServerSessionsEntry 10}

pr1646v2VrfLtdUdpServerSessionsTableIx OBJECT-TYPE
   SYNTAX      TableIndex
   MAX-ACCESS  not-accessible
   STATUS      current
   DESCRIPTION
      ""
   ::= {pr1646v2VrfLtdUdpServerSessionsEntry 11}

pr1646v2VrfLtdUdpServerSessionsSourceIpAddress OBJECT-TYPE
   SYNTAX      IpAddress
   MAX-ACCESS  read-only
   STATUS      current
   DESCRIPTION
      "Path: vrfRouterLtd.performance.udpServer.sessions.sourceIpAddress"
   ::= {pr1646v2VrfLtdUdpServerSessionsEntry 16777216}

pr1646v2VrfLtdUdpServerSessionsSourcePort OBJECT-TYPE
   SYNTAX      Integer32
   MAX-ACCESS  read-only
   STATUS      current
   DESCRIPTION
      "Path: vrfRouterLtd.performance.udpServer.sessions.sourcePort"
   ::= {pr1646v2VrfLtdUdpServerSessionsEntry 33554432}

pr1646v2VrfLtdUdpServerSessionsNbrPckt OBJECT-TYPE
   SYNTAX      Counter64
   MAX-ACCESS  read-only
   STATUS      current
   DESCRIPTION
      "Path: vrfRouterLtd.performance.udpServer.sessions.nbrOfPackets

       64 bit unsigned wrappable counter."
   ::= {pr1646v2VrfLtdUdpServerSessionsEntry 50331648}

pr1646v2VrfLtdUdpServerSessionsFirstActivityTime OBJECT-TYPE
   SYNTAX      TimeTicks
   MAX-ACCESS  read-only
   STATUS      current
   DESCRIPTION
      "Path: vrfRouterLtd.performance.udpServer.sessions.firstActivityTime

       Time in centi-second."
   ::= {pr1646v2VrfLtdUdpServerSessionsEntry 67108864}

pr1646v2VrfLtdUdpServerSessionsLastActivityTime OBJECT-TYPE
   SYNTAX      TimeTicks
   MAX-ACCESS  read-only
   STATUS      current
   DESCRIPTION
      "Path: vrfRouterLtd.performance.udpServer.sessions.lastActivityTime

       Time in centi-second."
   ::= {pr1646v2VrfLtdUdpServerSessionsEntry 83886080}

pr1646v2VrfLtdUdpServerSessionsHalfWayStatus OBJECT-TYPE
   SYNTAX      INTEGER
               {
               notInUse (1),
               inUse (2)
               }
   MAX-ACCESS  read-only
   STATUS      current
   DESCRIPTION
      "Path: vrfRouterLtd.performance.udpServer.sessions.halfWay.status

       Possibilities:
               notInUse   (1)
               inUse   (2)"
   ::= {pr1646v2VrfLtdUdpServerSessionsEntry 100728832}

pr1646v2VrfLtdUdpServerSessionsHalfWayReceived OBJECT-TYPE
   SYNTAX      Counter64
   MAX-ACCESS  read-only
   STATUS      current
   DESCRIPTION
      "Path: vrfRouterLtd.performance.udpServer.sessions.halfWay.received

       64 bit unsigned wrappable counter."
   ::= {pr1646v2VrfLtdUdpServerSessionsEntry 110166016}

pr1646v2VrfLtdUdpServerSessionsHalfWayPacketLoss OBJECT-TYPE
   SYNTAX      Counter64
   MAX-ACCESS  read-only
   STATUS      current
   DESCRIPTION
      "Path: vrfRouterLtd.performance.udpServer.sessions.halfWay.packetLoss

       64 bit unsigned wrappable counter."
   ::= {pr1646v2VrfLtdUdpServerSessionsEntry 110231552}

pr1646v2VrfLtdUdpServerSessionsHalfWayOutOfSequence OBJECT-TYPE
   SYNTAX      Counter64
   MAX-ACCESS  read-only
   STATUS      current
   DESCRIPTION
      "Path: vrfRouterLtd.performance.udpServer.sessions.halfWay.outOfSequence

       64 bit unsigned wrappable counter."
   ::= {pr1646v2VrfLtdUdpServerSessionsEntry 110362624}

pr1646v2VrfLtdUdpServerSessionsHalfWayCrcErrors OBJECT-TYPE
   SYNTAX      Counter64
   MAX-ACCESS  read-only
   STATUS      current
   DESCRIPTION
      "Path: vrfRouterLtd.performance.udpServer.sessions.halfWay.crcErrors

       64 bit unsigned wrappable counter."
   ::= {pr1646v2VrfLtdUdpServerSessionsEntry 110493696}

pr1646v2VrfLtdUdpServerSessionsHalfWayLengthErrors OBJECT-TYPE
   SYNTAX      Counter64
   MAX-ACCESS  read-only
   STATUS      current
   DESCRIPTION
      "Path: vrfRouterLtd.performance.udpServer.sessions.halfWay.lengthErrors

       64 bit unsigned wrappable counter."
   ::= {pr1646v2VrfLtdUdpServerSessionsEntry 110559232}

pr1646v2VrfLtdUdpServerSessionsHalfWayJitter OBJECT-TYPE
   SYNTAX      INTEGER
               {
               slnotsinsuseg (2147483647)
               }
   MAX-ACCESS  read-only
   STATUS      current
   DESCRIPTION
      "Path: vrfRouterLtd.performance.udpServer.sessions.halfWay.jitter

       unit name = ms
       formula = 10 / ; 10 *

       Possibilities:
               <not in use>   (2147483647)"
   ::= {pr1646v2VrfLtdUdpServerSessionsEntry 111280128}

pr1646v2VrfLtdUdpServerSessionsHalfWayJitterAvrg OBJECT-TYPE
   SYNTAX      INTEGER
               {
               slnotsinsuseg (2147483647)
               }
   MAX-ACCESS  read-only
   STATUS      current
   DESCRIPTION
      "Path: vrfRouterLtd.performance.udpServer.sessions.halfWay.jitterAvrg

       unit name = ms
       formula = 10 / ; 10 *

       Possibilities:
               <not in use>   (2147483647)"
   ::= {pr1646v2VrfLtdUdpServerSessionsEntry 111345664}

pr1646v2VrfLtdUdpServerSessionsHalfWayJitterMax OBJECT-TYPE
   SYNTAX      INTEGER
               {
               slnotsinsuseg (2147483647)
               }
   MAX-ACCESS  read-only
   STATUS      current
   DESCRIPTION
      "Path: vrfRouterLtd.performance.udpServer.sessions.halfWay.jitterMax

       unit name = ms
       formula = 10 / ; 10 *

       Possibilities:
               <not in use>   (2147483647)"
   ::= {pr1646v2VrfLtdUdpServerSessionsEntry 111411200}

pr1646v2VrfLtdUdpServerSessionsHalfWayReceivedLength OBJECT-TYPE
   SYNTAX      Counter64
   MAX-ACCESS  read-only
   STATUS      current
   DESCRIPTION
      "Path: vrfRouterLtd.performance.udpServer.sessions.halfWay.receivedLength

       64 bit unsigned wrappable counter."
   ::= {pr1646v2VrfLtdUdpServerSessionsEntry 111083520}

pr1646v2VrfLtdUdpServerSessionsHalfWayLastFault OBJECT-TYPE
   SYNTAX      Counter64
   MAX-ACCESS  read-only
   STATUS      current
   DESCRIPTION
      "Path: vrfRouterLtd.performance.udpServer.sessions.halfWay.lastFault

       64 bit unsigned wrappable counter."
   ::= {pr1646v2VrfLtdUdpServerSessionsEntry 111804416}

pr1646v2VrfLtdUdpServerSessionsHalfWayLastSeqnr OBJECT-TYPE
   SYNTAX      Counter64
   MAX-ACCESS  read-only
   STATUS      current
   DESCRIPTION
      "Path: vrfRouterLtd.performance.udpServer.sessions.halfWay.lastSeqnr

       64 bit unsigned wrappable counter."
   ::= {pr1646v2VrfLtdUdpServerSessionsEntry 111869952}


pr1646v2VrfLtdTracertResults OBJECT IDENTIFIER ::= {pr1646v2VrfLtd 153}

pr1646v2VrfLtdTracertResultsSSCTable OBJECT-TYPE
   SYNTAX      SEQUENCE OF Pr1646v2VrfLtdTracertResultsEntry
   MAX-ACCESS  not-accessible
   STATUS      current
   DESCRIPTION
      "Traceroute statistics"
   ::= {pr1646v2VrfLtdTracertResults 1}

pr1646v2VrfLtdTracertResultsEntry OBJECT-TYPE
   SYNTAX      Pr1646v2VrfLtdTracertResultsEntry
   MAX-ACCESS  not-accessible
   STATUS      current
   DESCRIPTION
      ""
   INDEX      { pr1646v2VrfLtdTracertResultsGlobalIx,
                pr1646v2VrfLtdTracertResultsTableIx }
   ::= {pr1646v2VrfLtdTracertResultsSSCTable 1}

Pr1646v2VrfLtdTracertResultsEntry ::=
   SEQUENCE
      {
      pr1646v2VrfLtdTracertResultsGlobalIx
         GlobalIndex,
      pr1646v2VrfLtdTracertResultsTableIx
         TableIndex,
      pr1646v2VrfLtdTracertResultsTtl
         Integer32,
      pr1646v2VrfLtdTracertResultsIpAddress
         IpAddress,
      pr1646v2VrfLtdTracertResultsHostName
         DisplayString,
      pr1646v2VrfLtdTracertResultsNrTx
         Counter32,
      pr1646v2VrfLtdTracertResultsNrRx
         Counter32,
      pr1646v2VrfLtdTracertResultsRepTimMin
         TimeTicks,
      pr1646v2VrfLtdTracertResultsRepTimMax
         TimeTicks,
      pr1646v2VrfLtdTracertResultsRepTimAvrg
         TimeTicks,
      pr1646v2VrfLtdTracertResultsSr
         Integer32,
      pr1646v2VrfLtdTracertResultsComment
         DisplayString
      }

pr1646v2VrfLtdTracertResultsGlobalIx OBJECT-TYPE
   SYNTAX      GlobalIndex
   MAX-ACCESS  not-accessible
   STATUS      current
   DESCRIPTION
      "The value of the tlsCntTreeGlobalIndex of the MANAGED OBJECT."
   ::= {pr1646v2VrfLtdTracertResultsEntry 10}

pr1646v2VrfLtdTracertResultsTableIx OBJECT-TYPE
   SYNTAX      TableIndex
   MAX-ACCESS  not-accessible
   STATUS      current
   DESCRIPTION
      ""
   ::= {pr1646v2VrfLtdTracertResultsEntry 11}

pr1646v2VrfLtdTracertResultsTtl OBJECT-TYPE
   SYNTAX      Integer32
   MAX-ACCESS  read-only
   STATUS      current
   DESCRIPTION
      "Path: vrfRouterLtd.performance.tracertResults.ttl"
   ::= {pr1646v2VrfLtdTracertResultsEntry 16777216}

pr1646v2VrfLtdTracertResultsIpAddress OBJECT-TYPE
   SYNTAX      IpAddress
   MAX-ACCESS  read-only
   STATUS      current
   DESCRIPTION
      "Path: vrfRouterLtd.performance.tracertResults.ipAddress"
   ::= {pr1646v2VrfLtdTracertResultsEntry 33554432}

pr1646v2VrfLtdTracertResultsHostName OBJECT-TYPE
   SYNTAX      DisplayString
   MAX-ACCESS  read-only
   STATUS      current
   DESCRIPTION
      "Path: vrfRouterLtd.performance.tracertResults.hostName"
   ::= {pr1646v2VrfLtdTracertResultsEntry 50331648}

pr1646v2VrfLtdTracertResultsNrTx OBJECT-TYPE
   SYNTAX      Counter32
   MAX-ACCESS  read-only
   STATUS      current
   DESCRIPTION
      "Path: vrfRouterLtd.performance.tracertResults.numOfTxPackets

       32 bit unsigned wrappable counter."
   ::= {pr1646v2VrfLtdTracertResultsEntry 67108864}

pr1646v2VrfLtdTracertResultsNrRx OBJECT-TYPE
   SYNTAX      Counter32
   MAX-ACCESS  read-only
   STATUS      current
   DESCRIPTION
      "Path: vrfRouterLtd.performance.tracertResults.numOfRxPackets

       32 bit unsigned wrappable counter."
   ::= {pr1646v2VrfLtdTracertResultsEntry 83886080}

pr1646v2VrfLtdTracertResultsRepTimMin OBJECT-TYPE
   SYNTAX      TimeTicks
   MAX-ACCESS  read-only
   STATUS      current
   DESCRIPTION
      "Path: vrfRouterLtd.performance.tracertResults.replyTimeMin

       Time in centi-second."
   ::= {pr1646v2VrfLtdTracertResultsEntry 100663296}

pr1646v2VrfLtdTracertResultsRepTimMax OBJECT-TYPE
   SYNTAX      TimeTicks
   MAX-ACCESS  read-only
   STATUS      current
   DESCRIPTION
      "Path: vrfRouterLtd.performance.tracertResults.replyTimeMax

       Time in centi-second."
   ::= {pr1646v2VrfLtdTracertResultsEntry 117440512}

pr1646v2VrfLtdTracertResultsRepTimAvrg OBJECT-TYPE
   SYNTAX      TimeTicks
   MAX-ACCESS  read-only
   STATUS      current
   DESCRIPTION
      "Path: vrfRouterLtd.performance.tracertResults.replyTimeAvrg

       Time in centi-second."
   ::= {pr1646v2VrfLtdTracertResultsEntry 134217728}

pr1646v2VrfLtdTracertResultsSr OBJECT-TYPE
   SYNTAX      Integer32
   UNITS       "%"
   MAX-ACCESS  read-only
   STATUS      current
   DESCRIPTION
      "Path: vrfRouterLtd.performance.tracertResults.successRate

       unit name = %"
   ::= {pr1646v2VrfLtdTracertResultsEntry 150994944}

pr1646v2VrfLtdTracertResultsComment OBJECT-TYPE
   SYNTAX      DisplayString
   MAX-ACCESS  read-only
   STATUS      current
   DESCRIPTION
      "Path: vrfRouterLtd.performance.tracertResults.comment"
   ::= {pr1646v2VrfLtdTracertResultsEntry 167772160}


pr1646v2VrfLtdIgmpProxy OBJECT IDENTIFIER ::= {pr1646v2VrfLtd 69}

pr1646v2VrfLtdIgmpProxySSCTable OBJECT-TYPE
   SYNTAX      SEQUENCE OF Pr1646v2VrfLtdIgmpProxyEntry
   MAX-ACCESS  not-accessible
   STATUS      current
   DESCRIPTION
      "igmp"
   ::= {pr1646v2VrfLtdIgmpProxy 1}

pr1646v2VrfLtdIgmpProxyEntry OBJECT-TYPE
   SYNTAX      Pr1646v2VrfLtdIgmpProxyEntry
   MAX-ACCESS  not-accessible
   STATUS      current
   DESCRIPTION
      ""
   INDEX      { pr1646v2VrfLtdIgmpProxyGlobalIx }
   ::= {pr1646v2VrfLtdIgmpProxySSCTable 1}

Pr1646v2VrfLtdIgmpProxyEntry ::=
   SEQUENCE
      {
      pr1646v2VrfLtdIgmpProxyGlobalIx
         GlobalIndex,
      pr1646v2VrfLtdIgmpProxyInIgmp
         Integer32,
      pr1646v2VrfLtdIgmpProxyOutIgmp
         Integer32,
      pr1646v2VrfLtdIgmpProxyInData
         Integer32,
      pr1646v2VrfLtdIgmpProxyInDiscards
         Integer32
      }

pr1646v2VrfLtdIgmpProxyGlobalIx OBJECT-TYPE
   SYNTAX      GlobalIndex
   MAX-ACCESS  not-accessible
   STATUS      current
   DESCRIPTION
      "The value of the tlsCntTreeGlobalIndex of the MANAGED OBJECT."
   ::= {pr1646v2VrfLtdIgmpProxyEntry 10}

pr1646v2VrfLtdIgmpProxyInIgmp OBJECT-TYPE
   SYNTAX      Integer32
   MAX-ACCESS  read-only
   STATUS      current
   DESCRIPTION
      "Path: vrfRouterLtd.performance.igmpProxy.inIgmp"
   ::= {pr1646v2VrfLtdIgmpProxyEntry 16777216}

pr1646v2VrfLtdIgmpProxyOutIgmp OBJECT-TYPE
   SYNTAX      Integer32
   MAX-ACCESS  read-only
   STATUS      current
   DESCRIPTION
      "Path: vrfRouterLtd.performance.igmpProxy.outIgmp"
   ::= {pr1646v2VrfLtdIgmpProxyEntry 33554432}

pr1646v2VrfLtdIgmpProxyInData OBJECT-TYPE
   SYNTAX      Integer32
   MAX-ACCESS  read-only
   STATUS      current
   DESCRIPTION
      "Path: vrfRouterLtd.performance.igmpProxy.inData"
   ::= {pr1646v2VrfLtdIgmpProxyEntry 50331648}

pr1646v2VrfLtdIgmpProxyInDiscards OBJECT-TYPE
   SYNTAX      Integer32
   MAX-ACCESS  read-only
   STATUS      current
   DESCRIPTION
      "Path: vrfRouterLtd.performance.igmpProxy.inDiscards"
   ::= {pr1646v2VrfLtdIgmpProxyEntry 67108864}


pr1646v2VrfLtdIpFragments OBJECT IDENTIFIER ::= {pr1646v2VrfLtd 87}

pr1646v2VrfLtdIpFragmentsSSCTable OBJECT-TYPE
   SYNTAX      SEQUENCE OF Pr1646v2VrfLtdIpFragmentsEntry
   MAX-ACCESS  not-accessible
   STATUS      current
   DESCRIPTION
      "info on IP fragments"
   ::= {pr1646v2VrfLtdIpFragments 1}

pr1646v2VrfLtdIpFragmentsEntry OBJECT-TYPE
   SYNTAX      Pr1646v2VrfLtdIpFragmentsEntry
   MAX-ACCESS  not-accessible
   STATUS      current
   DESCRIPTION
      ""
   INDEX      { pr1646v2VrfLtdIpFragmentsGlobalIx }
   ::= {pr1646v2VrfLtdIpFragmentsSSCTable 1}

Pr1646v2VrfLtdIpFragmentsEntry ::=
   SEQUENCE
      {
      pr1646v2VrfLtdIpFragmentsGlobalIx
         GlobalIndex,
      pr1646v2VrfLtdIpFragmentsReceivedFrames
         Counter64,
      pr1646v2VrfLtdIpFragmentsReassembledFrames
         Counter64,
      pr1646v2VrfLtdIpFragmentsExpiredFrames
         Counter64,
      pr1646v2VrfLtdIpFragmentsPendingFrames
         Gauge32,
      pr1646v2VrfLtdIpFragmentsReceivedPackets
         Counter64,
      pr1646v2VrfLtdIpFragmentsExcessivelyFragPackets
         Counter64
      }

pr1646v2VrfLtdIpFragmentsGlobalIx OBJECT-TYPE
   SYNTAX      GlobalIndex
   MAX-ACCESS  not-accessible
   STATUS      current
   DESCRIPTION
      "The value of the tlsCntTreeGlobalIndex of the MANAGED OBJECT."
   ::= {pr1646v2VrfLtdIpFragmentsEntry 10}

pr1646v2VrfLtdIpFragmentsReceivedFrames OBJECT-TYPE
   SYNTAX      Counter64
   MAX-ACCESS  read-only
   STATUS      current
   DESCRIPTION
      "Path: vrfRouterLtd.performance.ipFragments.receivedFrames

       64 bit unsigned wrappable counter."
   ::= {pr1646v2VrfLtdIpFragmentsEntry 16777216}

pr1646v2VrfLtdIpFragmentsReassembledFrames OBJECT-TYPE
   SYNTAX      Counter64
   MAX-ACCESS  read-only
   STATUS      current
   DESCRIPTION
      "Path: vrfRouterLtd.performance.ipFragments.reassembledFrames

       64 bit unsigned wrappable counter."
   ::= {pr1646v2VrfLtdIpFragmentsEntry 33554432}

pr1646v2VrfLtdIpFragmentsExpiredFrames OBJECT-TYPE
   SYNTAX      Counter64
   MAX-ACCESS  read-only
   STATUS      current
   DESCRIPTION
      "Path: vrfRouterLtd.performance.ipFragments.expiredFrames

       64 bit unsigned wrappable counter."
   ::= {pr1646v2VrfLtdIpFragmentsEntry 50331648}

pr1646v2VrfLtdIpFragmentsPendingFrames OBJECT-TYPE
   SYNTAX      Gauge32
   MAX-ACCESS  read-only
   STATUS      current
   DESCRIPTION
      "Path: vrfRouterLtd.performance.ipFragments.pendingFrames

       32 bit unsigned gauge value."
   ::= {pr1646v2VrfLtdIpFragmentsEntry 67108864}

pr1646v2VrfLtdIpFragmentsReceivedPackets OBJECT-TYPE
   SYNTAX      Counter64
   MAX-ACCESS  read-only
   STATUS      current
   DESCRIPTION
      "Path: vrfRouterLtd.performance.ipFragments.receivedPackets

       64 bit unsigned wrappable counter."
   ::= {pr1646v2VrfLtdIpFragmentsEntry 83886080}

pr1646v2VrfLtdIpFragmentsExcessivelyFragPackets OBJECT-TYPE
   SYNTAX      Counter64
   MAX-ACCESS  read-only
   STATUS      current
   DESCRIPTION
      "Path: vrfRouterLtd.performance.ipFragments.excessivelyFragPackets

       64 bit unsigned wrappable counter."
   ::= {pr1646v2VrfLtdIpFragmentsEntry 100663296}



fr1646v2VrfLtd OBJECT IDENTIFIER ::= {r1646v2VrfLtd 13}


fr1646v2VrfLtdAlarm OBJECT IDENTIFIER ::= {fr1646v2VrfLtd 202}

fr1646v2VrfLtdAlarmSSCTable OBJECT-TYPE
   SYNTAX      SEQUENCE OF Fr1646v2VrfLtdAlarmEntry
   MAX-ACCESS  not-accessible
   STATUS      current
   DESCRIPTION
      "routAlarmInfo"
   ::= {fr1646v2VrfLtdAlarm 1}

fr1646v2VrfLtdAlarmEntry OBJECT-TYPE
   SYNTAX      Fr1646v2VrfLtdAlarmEntry
   MAX-ACCESS  not-accessible
   STATUS      current
   DESCRIPTION
      ""
   INDEX      { fr1646v2VrfLtdAlarmGlobalIx }
   ::= {fr1646v2VrfLtdAlarmSSCTable 1}

Fr1646v2VrfLtdAlarmEntry ::=
   SEQUENCE
      {
      fr1646v2VrfLtdAlarmGlobalIx
         GlobalIndex,
      fr1646v2VrfLtdAlarmDiscriminator
         Integer32,
      fr1646v2VrfLtdAlarmCurrent
         Integer32,
      fr1646v2VrfLtdAlarmPrevious
         Integer32,
      fr1646v2VrfLtdAlarmMask
         Integer32,
      fr1646v2VrfLtdAlarmLevPingActive
         Integer32,
      fr1646v2VrfLtdAlarmLevQMonLoss
         Integer32,
      fr1646v2VrfLtdAlarmLevQMonDelay
         Integer32,
      fr1646v2VrfLtdAlarmLevQMonJitter
         Integer32
      }

fr1646v2VrfLtdAlarmGlobalIx OBJECT-TYPE
   SYNTAX      GlobalIndex
   MAX-ACCESS  not-accessible
   STATUS      current
   DESCRIPTION
      "The value of the tlsCntTreeGlobalIndex of the MANAGED OBJECT."
   ::= {fr1646v2VrfLtdAlarmEntry 10}

fr1646v2VrfLtdAlarmDiscriminator OBJECT-TYPE
   SYNTAX      Integer32
   MAX-ACCESS  read-only
   STATUS      current
   DESCRIPTION
      "Path: vrfRouterLtd.alarms.alarmInfo.discriminator"
   ::= {fr1646v2VrfLtdAlarmEntry 16777216}

fr1646v2VrfLtdAlarmCurrent OBJECT-TYPE
   SYNTAX      Integer32
   MAX-ACCESS  read-only
   STATUS      current
   DESCRIPTION
      "Path: vrfRouterLtd.alarms.alarmInfo.currentAlarms

       Bit meanings:
               bit 0 = pingActive,
               bit 1 = qMonLoss,
               bit 2 = qMonDelay,
               bit 3 = qMonJitter"
   ::= {fr1646v2VrfLtdAlarmEntry 33554432}

fr1646v2VrfLtdAlarmPrevious OBJECT-TYPE
   SYNTAX      Integer32
   MAX-ACCESS  read-only
   STATUS      current
   DESCRIPTION
      "Path: vrfRouterLtd.alarms.alarmInfo.previousAlarms

       Bit meanings:
               bit 0 = pingActive,
               bit 1 = qMonLoss,
               bit 2 = qMonDelay,
               bit 3 = qMonJitter"
   ::= {fr1646v2VrfLtdAlarmEntry 50331648}

fr1646v2VrfLtdAlarmMask OBJECT-TYPE
   SYNTAX      Integer32
   MAX-ACCESS  read-only
   STATUS      current
   DESCRIPTION
      "Path: vrfRouterLtd.alarms.alarmInfo.alarmMask

       Bit meanings:
               bit 0 = pingActive,
               bit 1 = qMonLoss,
               bit 2 = qMonDelay,
               bit 3 = qMonJitter"
   ::= {fr1646v2VrfLtdAlarmEntry 67108864}

fr1646v2VrfLtdAlarmLevPingActive OBJECT-TYPE
   SYNTAX      Integer32
   MAX-ACCESS  read-only
   STATUS      current
   DESCRIPTION
      "Path: vrfRouterLtd.alarms.alarmInfo.alarmLevel.pingActive"
   ::= {fr1646v2VrfLtdAlarmEntry 83951616}

fr1646v2VrfLtdAlarmLevQMonLoss OBJECT-TYPE
   SYNTAX      Integer32
   MAX-ACCESS  read-only
   STATUS      current
   DESCRIPTION
      "Path: vrfRouterLtd.alarms.alarmInfo.alarmLevel.qMonLoss"
   ::= {fr1646v2VrfLtdAlarmEntry 84017152}

fr1646v2VrfLtdAlarmLevQMonDelay OBJECT-TYPE
   SYNTAX      Integer32
   MAX-ACCESS  read-only
   STATUS      current
   DESCRIPTION
      "Path: vrfRouterLtd.alarms.alarmInfo.alarmLevel.qMonDelay"
   ::= {fr1646v2VrfLtdAlarmEntry 84082688}

fr1646v2VrfLtdAlarmLevQMonJitter OBJECT-TYPE
   SYNTAX      Integer32
   MAX-ACCESS  read-only
   STATUS      current
   DESCRIPTION
      "Path: vrfRouterLtd.alarms.alarmInfo.alarmLevel.qMonJitter"
   ::= {fr1646v2VrfLtdAlarmEntry 84148224}


fr1646v2VrfLtdAlarmE2 OBJECT IDENTIFIER ::= {fr1646v2VrfLtdAlarm 2}

fr1646v2VrfLtdAlarmE2Entry OBJECT IDENTIFIER ::= {fr1646v2VrfLtdAlarmE2 1}

fr1646v2VrfLtdAlarmE2PingActive OBJECT IDENTIFIER ::= {fr1646v2VrfLtdAlarmE2Entry 10}

fr1646v2VrfLtdAlarmE2PingActivePfx OBJECT IDENTIFIER ::= {fr1646v2VrfLtdAlarmE2PingActive 0}

fr1646v2VrfLtdAlarmE2PingActiveOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'vrfRouterLtd'
                (root='router1646') has changed from the ON to the OFF state."
   ::= {fr1646v2VrfLtdAlarmE2PingActivePfx 1}

fr1646v2VrfLtdAlarmE2PingActiveOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'vrfRouterLtd'
                (root='router1646') has changed from the OFF to the ON state."
   ::= {fr1646v2VrfLtdAlarmE2PingActivePfx 2}

fr1646v2VrfLtdAlarmE2QMonLoss OBJECT IDENTIFIER ::= {fr1646v2VrfLtdAlarmE2Entry 11}

fr1646v2VrfLtdAlarmE2QMonLossPfx OBJECT IDENTIFIER ::= {fr1646v2VrfLtdAlarmE2QMonLoss 0}

fr1646v2VrfLtdAlarmE2QMonLossOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'vrfRouterLtd'
                (root='router1646') has changed from the ON to the OFF state."
   ::= {fr1646v2VrfLtdAlarmE2QMonLossPfx 1}

fr1646v2VrfLtdAlarmE2QMonLossOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'vrfRouterLtd'
                (root='router1646') has changed from the OFF to the ON state."
   ::= {fr1646v2VrfLtdAlarmE2QMonLossPfx 2}

fr1646v2VrfLtdAlarmE2QMonDelay OBJECT IDENTIFIER ::= {fr1646v2VrfLtdAlarmE2Entry 12}

fr1646v2VrfLtdAlarmE2QMonDelayPfx OBJECT IDENTIFIER ::= {fr1646v2VrfLtdAlarmE2QMonDelay 0}

fr1646v2VrfLtdAlarmE2QMonDelayOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'vrfRouterLtd'
                (root='router1646') has changed from the ON to the OFF state."
   ::= {fr1646v2VrfLtdAlarmE2QMonDelayPfx 1}

fr1646v2VrfLtdAlarmE2QMonDelayOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'vrfRouterLtd'
                (root='router1646') has changed from the OFF to the ON state."
   ::= {fr1646v2VrfLtdAlarmE2QMonDelayPfx 2}

fr1646v2VrfLtdAlarmE2QMonJitter OBJECT IDENTIFIER ::= {fr1646v2VrfLtdAlarmE2Entry 13}

fr1646v2VrfLtdAlarmE2QMonJitterPfx OBJECT IDENTIFIER ::= {fr1646v2VrfLtdAlarmE2QMonJitter 0}

fr1646v2VrfLtdAlarmE2QMonJitterOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'vrfRouterLtd'
                (root='router1646') has changed from the ON to the OFF state."
   ::= {fr1646v2VrfLtdAlarmE2QMonJitterPfx 1}

fr1646v2VrfLtdAlarmE2QMonJitterOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'vrfRouterLtd'
                (root='router1646') has changed from the OFF to the ON state."
   ::= {fr1646v2VrfLtdAlarmE2QMonJitterPfx 2}



ar1646v2VrfLtd OBJECT IDENTIFIER ::= {r1646v2VrfLtd 16}


ar1646v2VrfLtdRestartDhcpClient OBJECT IDENTIFIER ::= {ar1646v2VrfLtd 88}

ar1646v2VrfLtdRestartDhcpClientTable OBJECT-TYPE
   SYNTAX      SEQUENCE OF Ar1646v2VrfLtdRestartDhcpClientEntry
   MAX-ACCESS  not-accessible
   STATUS      current
   DESCRIPTION
      "restart the dhcp client"
   ::= {ar1646v2VrfLtdRestartDhcpClient 1}

ar1646v2VrfLtdRestartDhcpClientEntry OBJECT-TYPE
   SYNTAX      Ar1646v2VrfLtdRestartDhcpClientEntry
   MAX-ACCESS  not-accessible
   STATUS      current
   DESCRIPTION
      ""
   INDEX      { ar1646v2VrfLtdRestartDhcpClientGlobalIx }
   ::= {ar1646v2VrfLtdRestartDhcpClientTable 1}

Ar1646v2VrfLtdRestartDhcpClientEntry ::=
   SEQUENCE
      {
      ar1646v2VrfLtdRestartDhcpClientGlobalIx
         GlobalIndex,
      ar1646v2VrfLtdRestartDhcpClientValue
         Integer32
      }

ar1646v2VrfLtdRestartDhcpClientGlobalIx OBJECT-TYPE
   SYNTAX      GlobalIndex
   MAX-ACCESS  not-accessible
   STATUS      current
   DESCRIPTION
      "The value of the tlsCntTreeGlobalIndex of the MANAGED OBJECT."
   ::= {ar1646v2VrfLtdRestartDhcpClientEntry 10}

ar1646v2VrfLtdRestartDhcpClientValue OBJECT-TYPE
   SYNTAX      Integer32
   MAX-ACCESS  read-write
   STATUS      current
   DESCRIPTION
      "Path: vrfRouterLtd.actions.restartDhcpClient"
   ::= {ar1646v2VrfLtdRestartDhcpClientEntry 2147483648}


ar1646v2VrfLtdInterfaceName OBJECT IDENTIFIER ::= {ar1646v2VrfLtd 89}

ar1646v2VrfLtdInterfaceNameTable OBJECT-TYPE
   SYNTAX      SEQUENCE OF Ar1646v2VrfLtdInterfaceNameEntry
   MAX-ACCESS  not-accessible
   STATUS      current
   DESCRIPTION
      "Name of the interface"
   ::= {ar1646v2VrfLtdInterfaceName 1}

ar1646v2VrfLtdInterfaceNameEntry OBJECT-TYPE
   SYNTAX      Ar1646v2VrfLtdInterfaceNameEntry
   MAX-ACCESS  not-accessible
   STATUS      current
   DESCRIPTION
      ""
   INDEX      { ar1646v2VrfLtdInterfaceNameGlobalIx }
   ::= {ar1646v2VrfLtdInterfaceNameTable 1}

Ar1646v2VrfLtdInterfaceNameEntry ::=
   SEQUENCE
      {
      ar1646v2VrfLtdInterfaceNameGlobalIx
         GlobalIndex,
      ar1646v2VrfLtdInterfaceNameValue
         DisplayString
      }

ar1646v2VrfLtdInterfaceNameGlobalIx OBJECT-TYPE
   SYNTAX      GlobalIndex
   MAX-ACCESS  not-accessible
   STATUS      current
   DESCRIPTION
      "The value of the tlsCntTreeGlobalIndex of the MANAGED OBJECT."
   ::= {ar1646v2VrfLtdInterfaceNameEntry 10}

ar1646v2VrfLtdInterfaceNameValue OBJECT-TYPE
   SYNTAX      DisplayString
   MAX-ACCESS  read-write
   STATUS      current
   DESCRIPTION
      "Path: vrfRouterLtd.actions.interfaceName"
   ::= {ar1646v2VrfLtdInterfaceNameEntry 2147483648}


ar1646v2VrfLtdSendIgmpLeave OBJECT IDENTIFIER ::= {ar1646v2VrfLtd 114}

ar1646v2VrfLtdSendIgmpLeaveTable OBJECT-TYPE
   SYNTAX      SEQUENCE OF Ar1646v2VrfLtdSendIgmpLeaveEntry
   MAX-ACCESS  not-accessible
   STATUS      current
   DESCRIPTION
      "send igmp leave over selected interfaces"
   ::= {ar1646v2VrfLtdSendIgmpLeave 1}

ar1646v2VrfLtdSendIgmpLeaveEntry OBJECT-TYPE
   SYNTAX      Ar1646v2VrfLtdSendIgmpLeaveEntry
   MAX-ACCESS  not-accessible
   STATUS      current
   DESCRIPTION
      ""
   INDEX      { ar1646v2VrfLtdSendIgmpLeaveGlobalIx }
   ::= {ar1646v2VrfLtdSendIgmpLeaveTable 1}

Ar1646v2VrfLtdSendIgmpLeaveEntry ::=
   SEQUENCE
      {
      ar1646v2VrfLtdSendIgmpLeaveGlobalIx
         GlobalIndex,
      ar1646v2VrfLtdSendIgmpLeaveValue
         Integer32
      }

ar1646v2VrfLtdSendIgmpLeaveGlobalIx OBJECT-TYPE
   SYNTAX      GlobalIndex
   MAX-ACCESS  not-accessible
   STATUS      current
   DESCRIPTION
      "The value of the tlsCntTreeGlobalIndex of the MANAGED OBJECT."
   ::= {ar1646v2VrfLtdSendIgmpLeaveEntry 10}

ar1646v2VrfLtdSendIgmpLeaveValue OBJECT-TYPE
   SYNTAX      Integer32
   MAX-ACCESS  read-write
   STATUS      current
   DESCRIPTION
      "Path: vrfRouterLtd.actions.sendIgmpLeave"
   ::= {ar1646v2VrfLtdSendIgmpLeaveEntry 2147483648}


ar1646v2VrfLtdIgmpDataLeave OBJECT IDENTIFIER ::= {ar1646v2VrfLtd 115}

ar1646v2VrfLtdIgmpDataLeaveSSCTable OBJECT-TYPE
   SYNTAX      SEQUENCE OF Ar1646v2VrfLtdIgmpDataLeaveEntry
   MAX-ACCESS  not-accessible
   STATUS      current
   DESCRIPTION
      "data needed for igmp"
   ::= {ar1646v2VrfLtdIgmpDataLeave 1}

ar1646v2VrfLtdIgmpDataLeaveEntry OBJECT-TYPE
   SYNTAX      Ar1646v2VrfLtdIgmpDataLeaveEntry
   MAX-ACCESS  not-accessible
   STATUS      current
   DESCRIPTION
      ""
   INDEX      { ar1646v2VrfLtdIgmpDataLeaveGlobalIx }
   ::= {ar1646v2VrfLtdIgmpDataLeaveSSCTable 1}

Ar1646v2VrfLtdIgmpDataLeaveEntry ::=
   SEQUENCE
      {
      ar1646v2VrfLtdIgmpDataLeaveGlobalIx
         GlobalIndex,
      ar1646v2VrfLtdIgmpDataLeaveInterfaces
         DisplayString,
      ar1646v2VrfLtdIgmpDataLeaveIpAddress
         IpAddress
      }

ar1646v2VrfLtdIgmpDataLeaveGlobalIx OBJECT-TYPE
   SYNTAX      GlobalIndex
   MAX-ACCESS  not-accessible
   STATUS      current
   DESCRIPTION
      "The value of the tlsCntTreeGlobalIndex of the MANAGED OBJECT."
   ::= {ar1646v2VrfLtdIgmpDataLeaveEntry 10}

ar1646v2VrfLtdIgmpDataLeaveInterfaces OBJECT-TYPE
   SYNTAX      DisplayString
   MAX-ACCESS  read-write
   STATUS      current
   DESCRIPTION
      "Path: vrfRouterLtd.actions.igmpDataLeave.interfaces"
   ::= {ar1646v2VrfLtdIgmpDataLeaveEntry 16777216}

ar1646v2VrfLtdIgmpDataLeaveIpAddress OBJECT-TYPE
   SYNTAX      IpAddress
   MAX-ACCESS  read-write
   STATUS      current
   DESCRIPTION
      "Path: vrfRouterLtd.actions.igmpDataLeave.ipAddress"
   ::= {ar1646v2VrfLtdIgmpDataLeaveEntry 33554432}


ar1646v2VrfLtdSendIgmpRep OBJECT IDENTIFIER ::= {ar1646v2VrfLtd 112}

ar1646v2VrfLtdSendIgmpRepTable OBJECT-TYPE
   SYNTAX      SEQUENCE OF Ar1646v2VrfLtdSendIgmpRepEntry
   MAX-ACCESS  not-accessible
   STATUS      current
   DESCRIPTION
      "send igmp report over selected interfaces"
   ::= {ar1646v2VrfLtdSendIgmpRep 1}

ar1646v2VrfLtdSendIgmpRepEntry OBJECT-TYPE
   SYNTAX      Ar1646v2VrfLtdSendIgmpRepEntry
   MAX-ACCESS  not-accessible
   STATUS      current
   DESCRIPTION
      ""
   INDEX      { ar1646v2VrfLtdSendIgmpRepGlobalIx }
   ::= {ar1646v2VrfLtdSendIgmpRepTable 1}

Ar1646v2VrfLtdSendIgmpRepEntry ::=
   SEQUENCE
      {
      ar1646v2VrfLtdSendIgmpRepGlobalIx
         GlobalIndex,
      ar1646v2VrfLtdSendIgmpRepValue
         Integer32
      }

ar1646v2VrfLtdSendIgmpRepGlobalIx OBJECT-TYPE
   SYNTAX      GlobalIndex
   MAX-ACCESS  not-accessible
   STATUS      current
   DESCRIPTION
      "The value of the tlsCntTreeGlobalIndex of the MANAGED OBJECT."
   ::= {ar1646v2VrfLtdSendIgmpRepEntry 10}

ar1646v2VrfLtdSendIgmpRepValue OBJECT-TYPE
   SYNTAX      Integer32
   MAX-ACCESS  read-write
   STATUS      current
   DESCRIPTION
      "Path: vrfRouterLtd.actions.sendIgmpRep"
   ::= {ar1646v2VrfLtdSendIgmpRepEntry 2147483648}


ar1646v2VrfLtdIgmpDataRep OBJECT IDENTIFIER ::= {ar1646v2VrfLtd 113}

ar1646v2VrfLtdIgmpDataRepSSCTable OBJECT-TYPE
   SYNTAX      SEQUENCE OF Ar1646v2VrfLtdIgmpDataRepEntry
   MAX-ACCESS  not-accessible
   STATUS      current
   DESCRIPTION
      "data needed for igmp"
   ::= {ar1646v2VrfLtdIgmpDataRep 1}

ar1646v2VrfLtdIgmpDataRepEntry OBJECT-TYPE
   SYNTAX      Ar1646v2VrfLtdIgmpDataRepEntry
   MAX-ACCESS  not-accessible
   STATUS      current
   DESCRIPTION
      ""
   INDEX      { ar1646v2VrfLtdIgmpDataRepGlobalIx }
   ::= {ar1646v2VrfLtdIgmpDataRepSSCTable 1}

Ar1646v2VrfLtdIgmpDataRepEntry ::=
   SEQUENCE
      {
      ar1646v2VrfLtdIgmpDataRepGlobalIx
         GlobalIndex,
      ar1646v2VrfLtdIgmpDataRepInterfaces
         DisplayString,
      ar1646v2VrfLtdIgmpDataRepIpAddress
         IpAddress
      }

ar1646v2VrfLtdIgmpDataRepGlobalIx OBJECT-TYPE
   SYNTAX      GlobalIndex
   MAX-ACCESS  not-accessible
   STATUS      current
   DESCRIPTION
      "The value of the tlsCntTreeGlobalIndex of the MANAGED OBJECT."
   ::= {ar1646v2VrfLtdIgmpDataRepEntry 10}

ar1646v2VrfLtdIgmpDataRepInterfaces OBJECT-TYPE
   SYNTAX      DisplayString
   MAX-ACCESS  read-write
   STATUS      current
   DESCRIPTION
      "Path: vrfRouterLtd.actions.igmpDataRep.interfaces"
   ::= {ar1646v2VrfLtdIgmpDataRepEntry 16777216}

ar1646v2VrfLtdIgmpDataRepIpAddress OBJECT-TYPE
   SYNTAX      IpAddress
   MAX-ACCESS  read-write
   STATUS      current
   DESCRIPTION
      "Path: vrfRouterLtd.actions.igmpDataRep.ipAddress"
   ::= {ar1646v2VrfLtdIgmpDataRepEntry 33554432}


ar1646v2VrfLtdSendRipReqAction OBJECT IDENTIFIER ::= {ar1646v2VrfLtd 301}

ar1646v2VrfLtdSendRipReqActionTable OBJECT-TYPE
   SYNTAX      SEQUENCE OF Ar1646v2VrfLtdSendRipReqActionEntry
   MAX-ACCESS  not-accessible
   STATUS      current
   DESCRIPTION
      "send RIP request to specific router"
   ::= {ar1646v2VrfLtdSendRipReqAction 1}

ar1646v2VrfLtdSendRipReqActionEntry OBJECT-TYPE
   SYNTAX      Ar1646v2VrfLtdSendRipReqActionEntry
   MAX-ACCESS  not-accessible
   STATUS      current
   DESCRIPTION
      ""
   INDEX      { ar1646v2VrfLtdSendRipReqActionGlobalIx }
   ::= {ar1646v2VrfLtdSendRipReqActionTable 1}

Ar1646v2VrfLtdSendRipReqActionEntry ::=
   SEQUENCE
      {
      ar1646v2VrfLtdSendRipReqActionGlobalIx
         GlobalIndex,
      ar1646v2VrfLtdSendRipReqActionValue
         Integer32
      }

ar1646v2VrfLtdSendRipReqActionGlobalIx OBJECT-TYPE
   SYNTAX      GlobalIndex
   MAX-ACCESS  not-accessible
   STATUS      current
   DESCRIPTION
      "The value of the tlsCntTreeGlobalIndex of the MANAGED OBJECT."
   ::= {ar1646v2VrfLtdSendRipReqActionEntry 10}

ar1646v2VrfLtdSendRipReqActionValue OBJECT-TYPE
   SYNTAX      Integer32
   MAX-ACCESS  read-write
   STATUS      current
   DESCRIPTION
      "Path: vrfRouterLtd.actions.sendRipReqAction"
   ::= {ar1646v2VrfLtdSendRipReqActionEntry 2147483648}


ar1646v2VrfLtdRequestArguments OBJECT IDENTIFIER ::= {ar1646v2VrfLtd 302}

ar1646v2VrfLtdRequestArgumentsSSCTable OBJECT-TYPE
   SYNTAX      SEQUENCE OF Ar1646v2VrfLtdRequestArgumentsEntry
   MAX-ACCESS  not-accessible
   STATUS      current
   DESCRIPTION
      "attributes for the sendRipRequest action"
   ::= {ar1646v2VrfLtdRequestArguments 1}

ar1646v2VrfLtdRequestArgumentsEntry OBJECT-TYPE
   SYNTAX      Ar1646v2VrfLtdRequestArgumentsEntry
   MAX-ACCESS  not-accessible
   STATUS      current
   DESCRIPTION
      ""
   INDEX      { ar1646v2VrfLtdRequestArgumentsGlobalIx }
   ::= {ar1646v2VrfLtdRequestArgumentsSSCTable 1}

Ar1646v2VrfLtdRequestArgumentsEntry ::=
   SEQUENCE
      {
      ar1646v2VrfLtdRequestArgumentsGlobalIx
         GlobalIndex,
      ar1646v2VrfLtdRequestArgumentsRouterIp
         IpAddress,
      ar1646v2VrfLtdRequestArgumentsOutIf
         DisplayString
      }

ar1646v2VrfLtdRequestArgumentsGlobalIx OBJECT-TYPE
   SYNTAX      GlobalIndex
   MAX-ACCESS  not-accessible
   STATUS      current
   DESCRIPTION
      "The value of the tlsCntTreeGlobalIndex of the MANAGED OBJECT."
   ::= {ar1646v2VrfLtdRequestArgumentsEntry 10}

ar1646v2VrfLtdRequestArgumentsRouterIp OBJECT-TYPE
   SYNTAX      IpAddress
   MAX-ACCESS  read-write
   STATUS      current
   DESCRIPTION
      "Path: vrfRouterLtd.actions.requestArguments.routerIp"
   ::= {ar1646v2VrfLtdRequestArgumentsEntry 16777216}

ar1646v2VrfLtdRequestArgumentsOutIf OBJECT-TYPE
   SYNTAX      DisplayString
   MAX-ACCESS  read-write
   STATUS      current
   DESCRIPTION
      "Path: vrfRouterLtd.actions.requestArguments.outgoingInterface"
   ::= {ar1646v2VrfLtdRequestArgumentsEntry 33554432}


ar1646v2VrfLtdFreeIpAddress OBJECT IDENTIFIER ::= {ar1646v2VrfLtd 106}

ar1646v2VrfLtdFreeIpAddressTable OBJECT-TYPE
   SYNTAX      SEQUENCE OF Ar1646v2VrfLtdFreeIpAddressEntry
   MAX-ACCESS  not-accessible
   STATUS      current
   DESCRIPTION
      "Free ip address"
   ::= {ar1646v2VrfLtdFreeIpAddress 1}

ar1646v2VrfLtdFreeIpAddressEntry OBJECT-TYPE
   SYNTAX      Ar1646v2VrfLtdFreeIpAddressEntry
   MAX-ACCESS  not-accessible
   STATUS      current
   DESCRIPTION
      ""
   INDEX      { ar1646v2VrfLtdFreeIpAddressGlobalIx }
   ::= {ar1646v2VrfLtdFreeIpAddressTable 1}

Ar1646v2VrfLtdFreeIpAddressEntry ::=
   SEQUENCE
      {
      ar1646v2VrfLtdFreeIpAddressGlobalIx
         GlobalIndex,
      ar1646v2VrfLtdFreeIpAddressValue
         Integer32
      }

ar1646v2VrfLtdFreeIpAddressGlobalIx OBJECT-TYPE
   SYNTAX      GlobalIndex
   MAX-ACCESS  not-accessible
   STATUS      current
   DESCRIPTION
      "The value of the tlsCntTreeGlobalIndex of the MANAGED OBJECT."
   ::= {ar1646v2VrfLtdFreeIpAddressEntry 10}

ar1646v2VrfLtdFreeIpAddressValue OBJECT-TYPE
   SYNTAX      Integer32
   MAX-ACCESS  read-write
   STATUS      current
   DESCRIPTION
      "Path: vrfRouterLtd.actions.freeIpAddress"
   ::= {ar1646v2VrfLtdFreeIpAddressEntry 2147483648}


ar1646v2VrfLtdAddr OBJECT IDENTIFIER ::= {ar1646v2VrfLtd 107}

ar1646v2VrfLtdAddrTable OBJECT-TYPE
   SYNTAX      SEQUENCE OF Ar1646v2VrfLtdAddrEntry
   MAX-ACCESS  not-accessible
   STATUS      current
   DESCRIPTION
      "ip address attribute"
   ::= {ar1646v2VrfLtdAddr 1}

ar1646v2VrfLtdAddrEntry OBJECT-TYPE
   SYNTAX      Ar1646v2VrfLtdAddrEntry
   MAX-ACCESS  not-accessible
   STATUS      current
   DESCRIPTION
      ""
   INDEX      { ar1646v2VrfLtdAddrGlobalIx }
   ::= {ar1646v2VrfLtdAddrTable 1}

Ar1646v2VrfLtdAddrEntry ::=
   SEQUENCE
      {
      ar1646v2VrfLtdAddrGlobalIx
         GlobalIndex,
      ar1646v2VrfLtdAddrValue
         IpAddress
      }

ar1646v2VrfLtdAddrGlobalIx OBJECT-TYPE
   SYNTAX      GlobalIndex
   MAX-ACCESS  not-accessible
   STATUS      current
   DESCRIPTION
      "The value of the tlsCntTreeGlobalIndex of the MANAGED OBJECT."
   ::= {ar1646v2VrfLtdAddrEntry 10}

ar1646v2VrfLtdAddrValue OBJECT-TYPE
   SYNTAX      IpAddress
   MAX-ACCESS  read-write
   STATUS      current
   DESCRIPTION
      "Path: vrfRouterLtd.actions.address"
   ::= {ar1646v2VrfLtdAddrEntry 2147483648}


ar1646v2VrfLtdTakeIpAddress OBJECT IDENTIFIER ::= {ar1646v2VrfLtd 104}

ar1646v2VrfLtdTakeIpAddressTable OBJECT-TYPE
   SYNTAX      SEQUENCE OF Ar1646v2VrfLtdTakeIpAddressEntry
   MAX-ACCESS  not-accessible
   STATUS      current
   DESCRIPTION
      "Take ip address from pool"
   ::= {ar1646v2VrfLtdTakeIpAddress 1}

ar1646v2VrfLtdTakeIpAddressEntry OBJECT-TYPE
   SYNTAX      Ar1646v2VrfLtdTakeIpAddressEntry
   MAX-ACCESS  not-accessible
   STATUS      current
   DESCRIPTION
      ""
   INDEX      { ar1646v2VrfLtdTakeIpAddressGlobalIx }
   ::= {ar1646v2VrfLtdTakeIpAddressTable 1}

Ar1646v2VrfLtdTakeIpAddressEntry ::=
   SEQUENCE
      {
      ar1646v2VrfLtdTakeIpAddressGlobalIx
         GlobalIndex,
      ar1646v2VrfLtdTakeIpAddressValue
         Integer32
      }

ar1646v2VrfLtdTakeIpAddressGlobalIx OBJECT-TYPE
   SYNTAX      GlobalIndex
   MAX-ACCESS  not-accessible
   STATUS      current
   DESCRIPTION
      "The value of the tlsCntTreeGlobalIndex of the MANAGED OBJECT."
   ::= {ar1646v2VrfLtdTakeIpAddressEntry 10}

ar1646v2VrfLtdTakeIpAddressValue OBJECT-TYPE
   SYNTAX      Integer32
   MAX-ACCESS  read-write
   STATUS      current
   DESCRIPTION
      "Path: vrfRouterLtd.actions.takeIpAddress"
   ::= {ar1646v2VrfLtdTakeIpAddressEntry 2147483648}


ar1646v2VrfLtdPool OBJECT IDENTIFIER ::= {ar1646v2VrfLtd 105}

ar1646v2VrfLtdPoolSSCTable OBJECT-TYPE
   SYNTAX      SEQUENCE OF Ar1646v2VrfLtdPoolEntry
   MAX-ACCESS  not-accessible
   STATUS      current
   DESCRIPTION
      "address pool type and name"
   ::= {ar1646v2VrfLtdPool 1}

ar1646v2VrfLtdPoolEntry OBJECT-TYPE
   SYNTAX      Ar1646v2VrfLtdPoolEntry
   MAX-ACCESS  not-accessible
   STATUS      current
   DESCRIPTION
      ""
   INDEX      { ar1646v2VrfLtdPoolGlobalIx }
   ::= {ar1646v2VrfLtdPoolSSCTable 1}

Ar1646v2VrfLtdPoolEntry ::=
   SEQUENCE
      {
      ar1646v2VrfLtdPoolGlobalIx
         GlobalIndex,
      ar1646v2VrfLtdPoolPoolType
         INTEGER,
      ar1646v2VrfLtdPoolPoolName
         DisplayString
      }

ar1646v2VrfLtdPoolGlobalIx OBJECT-TYPE
   SYNTAX      GlobalIndex
   MAX-ACCESS  not-accessible
   STATUS      current
   DESCRIPTION
      "The value of the tlsCntTreeGlobalIndex of the MANAGED OBJECT."
   ::= {ar1646v2VrfLtdPoolEntry 10}

ar1646v2VrfLtdPoolPoolType OBJECT-TYPE
   SYNTAX      INTEGER
               {
               list (1),
               interval (2)
               }
   MAX-ACCESS  read-write
   STATUS      current
   DESCRIPTION
      "Path: vrfRouterLtd.actions.poolTypeName.poolType

       Possibilities:
               list   (1)
               interval   (2)"
   ::= {ar1646v2VrfLtdPoolEntry 16777216}

ar1646v2VrfLtdPoolPoolName OBJECT-TYPE
   SYNTAX      DisplayString
   MAX-ACCESS  read-write
   STATUS      current
   DESCRIPTION
      "Path: vrfRouterLtd.actions.poolTypeName.poolName"
   ::= {ar1646v2VrfLtdPoolEntry 33554432}


ar1646v2VrfLtdQmOnDemand OBJECT IDENTIFIER ::= {ar1646v2VrfLtd 8043}

ar1646v2VrfLtdQmOnDemandTable OBJECT-TYPE
   SYNTAX      SEQUENCE OF Ar1646v2VrfLtdQmOnDemandEntry
   MAX-ACCESS  not-accessible
   STATUS      current
   DESCRIPTION
      "start sending pings"
   ::= {ar1646v2VrfLtdQmOnDemand 1}

ar1646v2VrfLtdQmOnDemandEntry OBJECT-TYPE
   SYNTAX      Ar1646v2VrfLtdQmOnDemandEntry
   MAX-ACCESS  not-accessible
   STATUS      current
   DESCRIPTION
      ""
   INDEX      { ar1646v2VrfLtdQmOnDemandGlobalIx }
   ::= {ar1646v2VrfLtdQmOnDemandTable 1}

Ar1646v2VrfLtdQmOnDemandEntry ::=
   SEQUENCE
      {
      ar1646v2VrfLtdQmOnDemandGlobalIx
         GlobalIndex,
      ar1646v2VrfLtdQmOnDemandValue
         Integer32
      }

ar1646v2VrfLtdQmOnDemandGlobalIx OBJECT-TYPE
   SYNTAX      GlobalIndex
   MAX-ACCESS  not-accessible
   STATUS      current
   DESCRIPTION
      "The value of the tlsCntTreeGlobalIndex of the MANAGED OBJECT."
   ::= {ar1646v2VrfLtdQmOnDemandEntry 10}

ar1646v2VrfLtdQmOnDemandValue OBJECT-TYPE
   SYNTAX      Integer32
   MAX-ACCESS  read-write
   STATUS      current
   DESCRIPTION
      "Path: vrfRouterLtd.actions.qmOnDemand"
   ::= {ar1646v2VrfLtdQmOnDemandEntry 2147483648}


ar1646v2VrfLtdAction OBJECT IDENTIFIER ::= {ar1646v2VrfLtd 8044}

ar1646v2VrfLtdActionSSCTable OBJECT-TYPE
   SYNTAX      SEQUENCE OF Ar1646v2VrfLtdActionEntry
   MAX-ACCESS  not-accessible
   STATUS      current
   DESCRIPTION
      "data needed for ping"
   ::= {ar1646v2VrfLtdAction 1}

ar1646v2VrfLtdActionEntry OBJECT-TYPE
   SYNTAX      Ar1646v2VrfLtdActionEntry
   MAX-ACCESS  not-accessible
   STATUS      current
   DESCRIPTION
      ""
   INDEX      { ar1646v2VrfLtdActionGlobalIx }
   ::= {ar1646v2VrfLtdActionSSCTable 1}

Ar1646v2VrfLtdActionEntry ::=
   SEQUENCE
      {
      ar1646v2VrfLtdActionGlobalIx
         GlobalIndex,
      ar1646v2VrfLtdActionAction
         INTEGER,
      ar1646v2VrfLtdActionName
         DisplayString
      }

ar1646v2VrfLtdActionGlobalIx OBJECT-TYPE
   SYNTAX      GlobalIndex
   MAX-ACCESS  not-accessible
   STATUS      current
   DESCRIPTION
      "The value of the tlsCntTreeGlobalIndex of the MANAGED OBJECT."
   ::= {ar1646v2VrfLtdActionEntry 10}

ar1646v2VrfLtdActionAction OBJECT-TYPE
   SYNTAX      INTEGER
               {
               restart (1),
               restartLossWindow (2),
               stop (3),
               stopAndClear (4)
               }
   MAX-ACCESS  read-write
   STATUS      current
   DESCRIPTION
      "Path: vrfRouterLtd.actions.action.action

       Possibilities:
               restart   (1)
               restartLossWindow   (2)
               stop   (3)
               stopAndClear   (4)"
   ::= {ar1646v2VrfLtdActionEntry 16777216}

ar1646v2VrfLtdActionName OBJECT-TYPE
   SYNTAX      DisplayString
   MAX-ACCESS  read-write
   STATUS      current
   DESCRIPTION
      "Path: vrfRouterLtd.actions.action.name"
   ::= {ar1646v2VrfLtdActionEntry 33554432}


ar1646v2VrfLtdClearTracert OBJECT IDENTIFIER ::= {ar1646v2VrfLtd 154}

ar1646v2VrfLtdClearTracertTable OBJECT-TYPE
   SYNTAX      SEQUENCE OF Ar1646v2VrfLtdClearTracertEntry
   MAX-ACCESS  not-accessible
   STATUS      current
   DESCRIPTION
      "Clear traceroute results"
   ::= {ar1646v2VrfLtdClearTracert 1}

ar1646v2VrfLtdClearTracertEntry OBJECT-TYPE
   SYNTAX      Ar1646v2VrfLtdClearTracertEntry
   MAX-ACCESS  not-accessible
   STATUS      current
   DESCRIPTION
      ""
   INDEX      { ar1646v2VrfLtdClearTracertGlobalIx }
   ::= {ar1646v2VrfLtdClearTracertTable 1}

Ar1646v2VrfLtdClearTracertEntry ::=
   SEQUENCE
      {
      ar1646v2VrfLtdClearTracertGlobalIx
         GlobalIndex,
      ar1646v2VrfLtdClearTracertValue
         Integer32
      }

ar1646v2VrfLtdClearTracertGlobalIx OBJECT-TYPE
   SYNTAX      GlobalIndex
   MAX-ACCESS  not-accessible
   STATUS      current
   DESCRIPTION
      "The value of the tlsCntTreeGlobalIndex of the MANAGED OBJECT."
   ::= {ar1646v2VrfLtdClearTracertEntry 10}

ar1646v2VrfLtdClearTracertValue OBJECT-TYPE
   SYNTAX      Integer32
   MAX-ACCESS  read-write
   STATUS      current
   DESCRIPTION
      "Path: vrfRouterLtd.actions.clearTracert"
   ::= {ar1646v2VrfLtdClearTracertEntry 2147483648}


ar1646v2VrfLtdStopTracert OBJECT IDENTIFIER ::= {ar1646v2VrfLtd 152}

ar1646v2VrfLtdStopTracertTable OBJECT-TYPE
   SYNTAX      SEQUENCE OF Ar1646v2VrfLtdStopTracertEntry
   MAX-ACCESS  not-accessible
   STATUS      current
   DESCRIPTION
      "stop ongoing traceroutes"
   ::= {ar1646v2VrfLtdStopTracert 1}

ar1646v2VrfLtdStopTracertEntry OBJECT-TYPE
   SYNTAX      Ar1646v2VrfLtdStopTracertEntry
   MAX-ACCESS  not-accessible
   STATUS      current
   DESCRIPTION
      ""
   INDEX      { ar1646v2VrfLtdStopTracertGlobalIx }
   ::= {ar1646v2VrfLtdStopTracertTable 1}

Ar1646v2VrfLtdStopTracertEntry ::=
   SEQUENCE
      {
      ar1646v2VrfLtdStopTracertGlobalIx
         GlobalIndex,
      ar1646v2VrfLtdStopTracertValue
         Integer32
      }

ar1646v2VrfLtdStopTracertGlobalIx OBJECT-TYPE
   SYNTAX      GlobalIndex
   MAX-ACCESS  not-accessible
   STATUS      current
   DESCRIPTION
      "The value of the tlsCntTreeGlobalIndex of the MANAGED OBJECT."
   ::= {ar1646v2VrfLtdStopTracertEntry 10}

ar1646v2VrfLtdStopTracertValue OBJECT-TYPE
   SYNTAX      Integer32
   MAX-ACCESS  read-write
   STATUS      current
   DESCRIPTION
      "Path: vrfRouterLtd.actions.stopTracert"
   ::= {ar1646v2VrfLtdStopTracertEntry 2147483648}


ar1646v2VrfLtdStartTracert OBJECT IDENTIFIER ::= {ar1646v2VrfLtd 150}

ar1646v2VrfLtdStartTracertTable OBJECT-TYPE
   SYNTAX      SEQUENCE OF Ar1646v2VrfLtdStartTracertEntry
   MAX-ACCESS  not-accessible
   STATUS      current
   DESCRIPTION
      "start traceroute"
   ::= {ar1646v2VrfLtdStartTracert 1}

ar1646v2VrfLtdStartTracertEntry OBJECT-TYPE
   SYNTAX      Ar1646v2VrfLtdStartTracertEntry
   MAX-ACCESS  not-accessible
   STATUS      current
   DESCRIPTION
      ""
   INDEX      { ar1646v2VrfLtdStartTracertGlobalIx }
   ::= {ar1646v2VrfLtdStartTracertTable 1}

Ar1646v2VrfLtdStartTracertEntry ::=
   SEQUENCE
      {
      ar1646v2VrfLtdStartTracertGlobalIx
         GlobalIndex,
      ar1646v2VrfLtdStartTracertValue
         Integer32
      }

ar1646v2VrfLtdStartTracertGlobalIx OBJECT-TYPE
   SYNTAX      GlobalIndex
   MAX-ACCESS  not-accessible
   STATUS      current
   DESCRIPTION
      "The value of the tlsCntTreeGlobalIndex of the MANAGED OBJECT."
   ::= {ar1646v2VrfLtdStartTracertEntry 10}

ar1646v2VrfLtdStartTracertValue OBJECT-TYPE
   SYNTAX      Integer32
   MAX-ACCESS  read-write
   STATUS      current
   DESCRIPTION
      "Path: vrfRouterLtd.actions.startTracert"
   ::= {ar1646v2VrfLtdStartTracertEntry 2147483648}


ar1646v2VrfLtdTracertData OBJECT IDENTIFIER ::= {ar1646v2VrfLtd 151}

ar1646v2VrfLtdTracertDataSSCTable OBJECT-TYPE
   SYNTAX      SEQUENCE OF Ar1646v2VrfLtdTracertDataEntry
   MAX-ACCESS  not-accessible
   STATUS      current
   DESCRIPTION
      "data needed for tracert"
   ::= {ar1646v2VrfLtdTracertData 1}

ar1646v2VrfLtdTracertDataEntry OBJECT-TYPE
   SYNTAX      Ar1646v2VrfLtdTracertDataEntry
   MAX-ACCESS  not-accessible
   STATUS      current
   DESCRIPTION
      ""
   INDEX      { ar1646v2VrfLtdTracertDataGlobalIx }
   ::= {ar1646v2VrfLtdTracertDataSSCTable 1}

Ar1646v2VrfLtdTracertDataEntry ::=
   SEQUENCE
      {
      ar1646v2VrfLtdTracertDataGlobalIx
         GlobalIndex,
      ar1646v2VrfLtdTracertDataIpAddress
         IpAddress,
      ar1646v2VrfLtdTracertDataHostName
         DisplayString,
      ar1646v2VrfLtdTracertDataSourceIp
         IpAddress,
      ar1646v2VrfLtdTracertDataStartTtl
         Integer32,
      ar1646v2VrfLtdTracertDataMaxHops
         Integer32,
      ar1646v2VrfLtdTracertDataQueriesPerHop
         Integer32,
      ar1646v2VrfLtdTracertDataResolveHosts
         INTEGER,
      ar1646v2VrfLtdTracertDataDnsTimeOut
         TimeTicks,
      ar1646v2VrfLtdTracertDataIcmpTimeOut
         TimeTicks,
      ar1646v2VrfLtdTracertDataTos
         INTEGER,
      ar1646v2VrfLtdTracertDataDataLength
         Integer32
      }

ar1646v2VrfLtdTracertDataGlobalIx OBJECT-TYPE
   SYNTAX      GlobalIndex
   MAX-ACCESS  not-accessible
   STATUS      current
   DESCRIPTION
      "The value of the tlsCntTreeGlobalIndex of the MANAGED OBJECT."
   ::= {ar1646v2VrfLtdTracertDataEntry 10}

ar1646v2VrfLtdTracertDataIpAddress OBJECT-TYPE
   SYNTAX      IpAddress
   MAX-ACCESS  read-write
   STATUS      current
   DESCRIPTION
      "Path: vrfRouterLtd.actions.tracertData.ipAddress"
   ::= {ar1646v2VrfLtdTracertDataEntry 16777216}

ar1646v2VrfLtdTracertDataHostName OBJECT-TYPE
   SYNTAX      DisplayString
   MAX-ACCESS  read-write
   STATUS      current
   DESCRIPTION
      "Path: vrfRouterLtd.actions.tracertData.hostName"
   ::= {ar1646v2VrfLtdTracertDataEntry 33554432}

ar1646v2VrfLtdTracertDataSourceIp OBJECT-TYPE
   SYNTAX      IpAddress
   MAX-ACCESS  read-write
   STATUS      current
   DESCRIPTION
      "Path: vrfRouterLtd.actions.tracertData.sourceIp"
   ::= {ar1646v2VrfLtdTracertDataEntry 50331648}

ar1646v2VrfLtdTracertDataStartTtl OBJECT-TYPE
   SYNTAX      Integer32
   MAX-ACCESS  read-write
   STATUS      current
   DESCRIPTION
      "Path: vrfRouterLtd.actions.tracertData.startTtl"
   ::= {ar1646v2VrfLtdTracertDataEntry 67108864}

ar1646v2VrfLtdTracertDataMaxHops OBJECT-TYPE
   SYNTAX      Integer32
   MAX-ACCESS  read-write
   STATUS      current
   DESCRIPTION
      "Path: vrfRouterLtd.actions.tracertData.maxHops"
   ::= {ar1646v2VrfLtdTracertDataEntry 83886080}

ar1646v2VrfLtdTracertDataQueriesPerHop OBJECT-TYPE
   SYNTAX      Integer32
   MAX-ACCESS  read-write
   STATUS      current
   DESCRIPTION
      "Path: vrfRouterLtd.actions.tracertData.queriesPerHop"
   ::= {ar1646v2VrfLtdTracertDataEntry 100663296}

ar1646v2VrfLtdTracertDataResolveHosts OBJECT-TYPE
   SYNTAX      INTEGER
               {
               disabled (0),
               enabled (1)
               }
   MAX-ACCESS  read-write
   STATUS      current
   DESCRIPTION
      "Path: vrfRouterLtd.actions.tracertData.resolveHosts

       Possibilities:
               disabled   (0)
               enabled   (1)"
   ::= {ar1646v2VrfLtdTracertDataEntry 117440512}

ar1646v2VrfLtdTracertDataDnsTimeOut OBJECT-TYPE
   SYNTAX      TimeTicks
   MAX-ACCESS  read-write
   STATUS      current
   DESCRIPTION
      "Path: vrfRouterLtd.actions.tracertData.dnsTimeOut

       Time in centi-second."
   ::= {ar1646v2VrfLtdTracertDataEntry 134217728}

ar1646v2VrfLtdTracertDataIcmpTimeOut OBJECT-TYPE
   SYNTAX      TimeTicks
   MAX-ACCESS  read-write
   STATUS      current
   DESCRIPTION
      "Path: vrfRouterLtd.actions.tracertData.icmpTimeOut

       Time in centi-second."
   ::= {ar1646v2VrfLtdTracertDataEntry 150994944}

ar1646v2VrfLtdTracertDataTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfRouterLtd.actions.tracertData.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {ar1646v2VrfLtdTracertDataEntry 167772160}

ar1646v2VrfLtdTracertDataDataLength OBJECT-TYPE
   SYNTAX      Integer32
   MAX-ACCESS  read-write
   STATUS      current
   DESCRIPTION
      "Path: vrfRouterLtd.actions.tracertData.dataLength"
   ::= {ar1646v2VrfLtdTracertDataEntry 184549376}


ar1646v2VrfLtdStopPing OBJECT IDENTIFIER ::= {ar1646v2VrfLtd 45}

ar1646v2VrfLtdStopPingTable OBJECT-TYPE
   SYNTAX      SEQUENCE OF Ar1646v2VrfLtdStopPingEntry
   MAX-ACCESS  not-accessible
   STATUS      current
   DESCRIPTION
      "stop sending pings"
   ::= {ar1646v2VrfLtdStopPing 1}

ar1646v2VrfLtdStopPingEntry OBJECT-TYPE
   SYNTAX      Ar1646v2VrfLtdStopPingEntry
   MAX-ACCESS  not-accessible
   STATUS      current
   DESCRIPTION
      ""
   INDEX      { ar1646v2VrfLtdStopPingGlobalIx }
   ::= {ar1646v2VrfLtdStopPingTable 1}

Ar1646v2VrfLtdStopPingEntry ::=
   SEQUENCE
      {
      ar1646v2VrfLtdStopPingGlobalIx
         GlobalIndex,
      ar1646v2VrfLtdStopPingValue
         Integer32
      }

ar1646v2VrfLtdStopPingGlobalIx OBJECT-TYPE
   SYNTAX      GlobalIndex
   MAX-ACCESS  not-accessible
   STATUS      current
   DESCRIPTION
      "The value of the tlsCntTreeGlobalIndex of the MANAGED OBJECT."
   ::= {ar1646v2VrfLtdStopPingEntry 10}

ar1646v2VrfLtdStopPingValue OBJECT-TYPE
   SYNTAX      Integer32
   MAX-ACCESS  read-write
   STATUS      current
   DESCRIPTION
      "Path: vrfRouterLtd.actions.stopPing"
   ::= {ar1646v2VrfLtdStopPingEntry 2147483648}


ar1646v2VrfLtdStartPing OBJECT IDENTIFIER ::= {ar1646v2VrfLtd 43}

ar1646v2VrfLtdStartPingTable OBJECT-TYPE
   SYNTAX      SEQUENCE OF Ar1646v2VrfLtdStartPingEntry
   MAX-ACCESS  not-accessible
   STATUS      current
   DESCRIPTION
      "start sending pings"
   ::= {ar1646v2VrfLtdStartPing 1}

ar1646v2VrfLtdStartPingEntry OBJECT-TYPE
   SYNTAX      Ar1646v2VrfLtdStartPingEntry
   MAX-ACCESS  not-accessible
   STATUS      current
   DESCRIPTION
      ""
   INDEX      { ar1646v2VrfLtdStartPingGlobalIx }
   ::= {ar1646v2VrfLtdStartPingTable 1}

Ar1646v2VrfLtdStartPingEntry ::=
   SEQUENCE
      {
      ar1646v2VrfLtdStartPingGlobalIx
         GlobalIndex,
      ar1646v2VrfLtdStartPingValue
         Integer32
      }

ar1646v2VrfLtdStartPingGlobalIx OBJECT-TYPE
   SYNTAX      GlobalIndex
   MAX-ACCESS  not-accessible
   STATUS      current
   DESCRIPTION
      "The value of the tlsCntTreeGlobalIndex of the MANAGED OBJECT."
   ::= {ar1646v2VrfLtdStartPingEntry 10}

ar1646v2VrfLtdStartPingValue OBJECT-TYPE
   SYNTAX      Integer32
   MAX-ACCESS  read-write
   STATUS      current
   DESCRIPTION
      "Path: vrfRouterLtd.actions.startPing"
   ::= {ar1646v2VrfLtdStartPingEntry 2147483648}


ar1646v2VrfLtdPingData OBJECT IDENTIFIER ::= {ar1646v2VrfLtd 44}

ar1646v2VrfLtdPingDataSSCTable OBJECT-TYPE
   SYNTAX      SEQUENCE OF Ar1646v2VrfLtdPingDataEntry
   MAX-ACCESS  not-accessible
   STATUS      current
   DESCRIPTION
      "data needed for ping"
   ::= {ar1646v2VrfLtdPingData 1}

ar1646v2VrfLtdPingDataEntry OBJECT-TYPE
   SYNTAX      Ar1646v2VrfLtdPingDataEntry
   MAX-ACCESS  not-accessible
   STATUS      current
   DESCRIPTION
      ""
   INDEX      { ar1646v2VrfLtdPingDataGlobalIx }
   ::= {ar1646v2VrfLtdPingDataSSCTable 1}

Ar1646v2VrfLtdPingDataEntry ::=
   SEQUENCE
      {
      ar1646v2VrfLtdPingDataGlobalIx
         GlobalIndex,
      ar1646v2VrfLtdPingDataIpAddress
         IpAddress,
      ar1646v2VrfLtdPingDataHostName
         DisplayString,
      ar1646v2VrfLtdPingDataSourceIp
         IpAddress,
      ar1646v2VrfLtdPingDataTos
         INTEGER,
      ar1646v2VrfLtdPingDataFragment
         INTEGER,
      ar1646v2VrfLtdPingDataTtl
         Integer32,
      ar1646v2VrfLtdPingDataIterations
         INTEGER,
      ar1646v2VrfLtdPingDataInterval
         Integer32,
      ar1646v2VrfLtdPingDataDataLength
         Integer32,
      ar1646v2VrfLtdPingDataTimeOut
         TimeTicks
      }

ar1646v2VrfLtdPingDataGlobalIx OBJECT-TYPE
   SYNTAX      GlobalIndex
   MAX-ACCESS  not-accessible
   STATUS      current
   DESCRIPTION
      "The value of the tlsCntTreeGlobalIndex of the MANAGED OBJECT."
   ::= {ar1646v2VrfLtdPingDataEntry 10}

ar1646v2VrfLtdPingDataIpAddress OBJECT-TYPE
   SYNTAX      IpAddress
   MAX-ACCESS  read-write
   STATUS      current
   DESCRIPTION
      "Path: vrfRouterLtd.actions.pingData.ipAddress"
   ::= {ar1646v2VrfLtdPingDataEntry 16777216}

ar1646v2VrfLtdPingDataHostName OBJECT-TYPE
   SYNTAX      DisplayString
   MAX-ACCESS  read-write
   STATUS      current
   DESCRIPTION
      "Path: vrfRouterLtd.actions.pingData.hostName"
   ::= {ar1646v2VrfLtdPingDataEntry 100663296}

ar1646v2VrfLtdPingDataSourceIp OBJECT-TYPE
   SYNTAX      IpAddress
   MAX-ACCESS  read-write
   STATUS      current
   DESCRIPTION
      "Path: vrfRouterLtd.actions.pingData.sourceIp"
   ::= {ar1646v2VrfLtdPingDataEntry 117440512}

ar1646v2VrfLtdPingDataTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfRouterLtd.actions.pingData.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {ar1646v2VrfLtdPingDataEntry 134217728}

ar1646v2VrfLtdPingDataFragment OBJECT-TYPE
   SYNTAX      INTEGER
               {
               yes (1),
               no (2)
               }
   MAX-ACCESS  read-write
   STATUS      current
   DESCRIPTION
      "Path: vrfRouterLtd.actions.pingData.fragment

       Possibilities:
               yes   (1)
               no   (2)"
   ::= {ar1646v2VrfLtdPingDataEntry 150994944}

ar1646v2VrfLtdPingDataTtl OBJECT-TYPE
   SYNTAX      Integer32
   MAX-ACCESS  read-write
   STATUS      current
   DESCRIPTION
      "Path: vrfRouterLtd.actions.pingData.ttl"
   ::= {ar1646v2VrfLtdPingDataEntry 167772160}

ar1646v2VrfLtdPingDataIterations OBJECT-TYPE
   SYNTAX      INTEGER
               {
               unlimited (0)
               }
   MAX-ACCESS  read-write
   STATUS      current
   DESCRIPTION
      "Path: vrfRouterLtd.actions.pingData.iterations

       Possibilities:
               unlimited   (0)"
   ::= {ar1646v2VrfLtdPingDataEntry 33554432}

ar1646v2VrfLtdPingDataInterval OBJECT-TYPE
   SYNTAX      Integer32
   MAX-ACCESS  read-write
   STATUS      current
   DESCRIPTION
      "Path: vrfRouterLtd.actions.pingData.interval"
   ::= {ar1646v2VrfLtdPingDataEntry 50331648}

ar1646v2VrfLtdPingDataDataLength OBJECT-TYPE
   SYNTAX      Integer32
   MAX-ACCESS  read-write
   STATUS      current
   DESCRIPTION
      "Path: vrfRouterLtd.actions.pingData.dataLength"
   ::= {ar1646v2VrfLtdPingDataEntry 67108864}

ar1646v2VrfLtdPingDataTimeOut OBJECT-TYPE
   SYNTAX      TimeTicks
   MAX-ACCESS  read-write
   STATUS      current
   DESCRIPTION
      "Path: vrfRouterLtd.actions.pingData.timeOut

       Time in centi-second."
   ::= {ar1646v2VrfLtdPingDataEntry 83886080}


ar1646v2VrfLtdClearCounters OBJECT IDENTIFIER ::= {ar1646v2VrfLtd 263}

ar1646v2VrfLtdClearCountersTable OBJECT-TYPE
   SYNTAX      SEQUENCE OF Ar1646v2VrfLtdClearCountersEntry
   MAX-ACCESS  not-accessible
   STATUS      current
   DESCRIPTION
      "reset counters"
   ::= {ar1646v2VrfLtdClearCounters 1}

ar1646v2VrfLtdClearCountersEntry OBJECT-TYPE
   SYNTAX      Ar1646v2VrfLtdClearCountersEntry
   MAX-ACCESS  not-accessible
   STATUS      current
   DESCRIPTION
      ""
   INDEX      { ar1646v2VrfLtdClearCountersGlobalIx }
   ::= {ar1646v2VrfLtdClearCountersTable 1}

Ar1646v2VrfLtdClearCountersEntry ::=
   SEQUENCE
      {
      ar1646v2VrfLtdClearCountersGlobalIx
         GlobalIndex,
      ar1646v2VrfLtdClearCountersValue
         Integer32
      }

ar1646v2VrfLtdClearCountersGlobalIx OBJECT-TYPE
   SYNTAX      GlobalIndex
   MAX-ACCESS  not-accessible
   STATUS      current
   DESCRIPTION
      "The value of the tlsCntTreeGlobalIndex of the MANAGED OBJECT."
   ::= {ar1646v2VrfLtdClearCountersEntry 10}

ar1646v2VrfLtdClearCountersValue OBJECT-TYPE
   SYNTAX      Integer32
   MAX-ACCESS  read-write
   STATUS      current
   DESCRIPTION
      "Path: vrfRouterLtd.actions.clearCounters"
   ::= {ar1646v2VrfLtdClearCountersEntry 2147483648}


ar1646v2VrfLtdClearDnsCache OBJECT IDENTIFIER ::= {ar1646v2VrfLtd 155}

ar1646v2VrfLtdClearDnsCacheTable OBJECT-TYPE
   SYNTAX      SEQUENCE OF Ar1646v2VrfLtdClearDnsCacheEntry
   MAX-ACCESS  not-accessible
   STATUS      current
   DESCRIPTION
      "clear the DNS cache table"
   ::= {ar1646v2VrfLtdClearDnsCache 1}

ar1646v2VrfLtdClearDnsCacheEntry OBJECT-TYPE
   SYNTAX      Ar1646v2VrfLtdClearDnsCacheEntry
   MAX-ACCESS  not-accessible
   STATUS      current
   DESCRIPTION
      ""
   INDEX      { ar1646v2VrfLtdClearDnsCacheGlobalIx }
   ::= {ar1646v2VrfLtdClearDnsCacheTable 1}

Ar1646v2VrfLtdClearDnsCacheEntry ::=
   SEQUENCE
      {
      ar1646v2VrfLtdClearDnsCacheGlobalIx
         GlobalIndex,
      ar1646v2VrfLtdClearDnsCacheValue
         Integer32
      }

ar1646v2VrfLtdClearDnsCacheGlobalIx OBJECT-TYPE
   SYNTAX      GlobalIndex
   MAX-ACCESS  not-accessible
   STATUS      current
   DESCRIPTION
      "The value of the tlsCntTreeGlobalIndex of the MANAGED OBJECT."
   ::= {ar1646v2VrfLtdClearDnsCacheEntry 10}

ar1646v2VrfLtdClearDnsCacheValue OBJECT-TYPE
   SYNTAX      Integer32
   MAX-ACCESS  read-write
   STATUS      current
   DESCRIPTION
      "Path: vrfRouterLtd.actions.clearDnsCache"
   ::= {ar1646v2VrfLtdClearDnsCacheEntry 2147483648}



END
