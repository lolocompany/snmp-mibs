OneAccess-R1646v2-4487-ATMFw DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2ATMFw OBJECT IDENTIFIER ::= {r1646Rootv2 4487}

r1646v2ATMFwMOProp OBJECT-TYPE
   SYNTAX      SEQUENCE OF R1646v2ATMFwMOPropEntry
   MAX-ACCESS  not-accessible
   STATUS      current
   DESCRIPTION
      ""
   ::= {r1646v2ATMFw 1}

r1646v2ATMFwMOPropEntry OBJECT-TYPE
   SYNTAX      R1646v2ATMFwMOPropEntry
   MAX-ACCESS  not-accessible
   STATUS      current
   DESCRIPTION
      ""
   INDEX      { r1646v2ATMFwMOPropGlobalIx }
   ::= {r1646v2ATMFwMOProp 1}

R1646v2ATMFwMOPropEntry ::=
   SEQUENCE
      {
      r1646v2ATMFwMOPropPath
         ContainmentPath,
      r1646v2ATMFwMOPropRev
         ObjectRevision,
      r1646v2ATMFwMOPropGlobalIx
         GlobalIndex
      }

r1646v2ATMFwMOPropPath OBJECT-TYPE
   SYNTAX      ContainmentPath
   MAX-ACCESS  read-only
   STATUS      current
   DESCRIPTION
      "Textual description of the containment tree from the instance of
       the root object down to the instance of the current object."
   ::= {r1646v2ATMFwMOPropEntry 3}

r1646v2ATMFwMOPropRev OBJECT-TYPE
   SYNTAX      ObjectRevision
   MAX-ACCESS  read-only
   STATUS      current
   DESCRIPTION
      "This value corresponds with the revision of the MANAGED OBJECT."
   ::= {r1646v2ATMFwMOPropEntry 4}

r1646v2ATMFwMOPropGlobalIx OBJECT-TYPE
   SYNTAX      GlobalIndex
   MAX-ACCESS  read-only
   STATUS      current
   DESCRIPTION
      "The value of the tlsCntTreeGlobalIndex of the MANAGED OBJECT."
   ::= {r1646v2ATMFwMOPropEntry 10}



er1646v2ATMFw OBJECT IDENTIFIER ::= {r1646v2ATMFw 11}


er1646v2ATMFwVp OBJECT IDENTIFIER ::= {er1646v2ATMFw 92}

er1646v2ATMFwVpSSCTable OBJECT-TYPE
   SYNTAX      SEQUENCE OF Er1646v2ATMFwVpEntry
   MAX-ACCESS  not-accessible
   STATUS      current
   DESCRIPTION
      ""
   ::= {er1646v2ATMFwVp 1}

er1646v2ATMFwVpEntry OBJECT-TYPE
   SYNTAX      Er1646v2ATMFwVpEntry
   MAX-ACCESS  not-accessible
   STATUS      current
   DESCRIPTION
      ""
   INDEX      { er1646v2ATMFwVpGlobalIx,
                er1646v2ATMFwVpTableIx }
   ::= {er1646v2ATMFwVpSSCTable 1}

Er1646v2ATMFwVpEntry ::=
   SEQUENCE
      {
      er1646v2ATMFwVpActions
         VariableLengthTableActions,
      er1646v2ATMFwVpGlobalIx
         GlobalIndex,
      er1646v2ATMFwVpTableIx
         TableIndex,
      er1646v2ATMFwVpVpi
         Integer32,
      er1646v2ATMFwVpLbOper
         INTEGER,
      er1646v2ATMFwVpLbInterval
         TimeTicks,
      er1646v2ATMFwVpLbFailsPerm
         Integer32,
      er1646v2ATMFwVpLbTar
         INTEGER,
      er1646v2ATMFwVpCcDir
         INTEGER,
      er1646v2ATMFwVpCcTar
         INTEGER,
      er1646v2ATMFwVpCcTxMode
         INTEGER,
      er1646v2ATMFwVpCcTxTxPer
         TimeTicks,
      er1646v2ATMFwVpCcRxRcvTim
         TimeTicks,
      er1646v2ATMFwVpCcActProc
         INTEGER,
      er1646v2ATMFwVpCcActTim
         TimeTicks,
      er1646v2ATMFwVpCcActCnt
         Integer32,
      er1646v2ATMFwVpPmDir
         INTEGER,
      er1646v2ATMFwVpPmTar
         INTEGER,
      er1646v2ATMFwVpPmType
         INTEGER,
      er1646v2ATMFwVpPmPolicy
         INTEGER,
      er1646v2ATMFwVpPmBsizeamb
         INTEGER,
      er1646v2ATMFwVpPmBsizebma
         INTEGER,
      er1646v2ATMFwVpPmActProc
         INTEGER,
      er1646v2ATMFwVpPmActTim
         TimeTicks,
      er1646v2ATMFwVpPmActCnt
         Integer32,
      er1646v2ATMFwVpCpt
         INTEGER
      }

er1646v2ATMFwVpActions OBJECT-TYPE
   SYNTAX      VariableLengthTableActions
   MAX-ACCESS  read-write
   STATUS      current
   DESCRIPTION
      "By way of this field, some manipulations
       on this table may be performed."
   ::= {er1646v2ATMFwVpEntry 2}

er1646v2ATMFwVpGlobalIx OBJECT-TYPE
   SYNTAX      GlobalIndex
   MAX-ACCESS  not-accessible
   STATUS      current
   DESCRIPTION
      "The value of the tlsCntTreeGlobalIndex of the MANAGED OBJECT."
   ::= {er1646v2ATMFwVpEntry 10}

er1646v2ATMFwVpTableIx OBJECT-TYPE
   SYNTAX      TableIndex
   MAX-ACCESS  not-accessible
   STATUS      current
   DESCRIPTION
      ""
   ::= {er1646v2ATMFwVpEntry 11}

er1646v2ATMFwVpVpi OBJECT-TYPE
   SYNTAX      Integer32
   MAX-ACCESS  read-write
   STATUS      current
   DESCRIPTION
      "Path: atm.editConf.vp.vpi"
   ::= {er1646v2ATMFwVpEntry 16777216}

er1646v2ATMFwVpLbOper OBJECT-TYPE
   SYNTAX      INTEGER
               {
               disabled (0),
               enabled (1)
               }
   MAX-ACCESS  read-write
   STATUS      current
   DESCRIPTION
      "Path: atm.editConf.vp.oamF4Loopback.operation

       Possibilities:
               disabled   (0)
               enabled   (1)"
   ::= {er1646v2ATMFwVpEntry 33619968}

er1646v2ATMFwVpLbInterval OBJECT-TYPE
   SYNTAX      TimeTicks
   MAX-ACCESS  read-write
   STATUS      current
   DESCRIPTION
      "Path: atm.editConf.vp.oamF4Loopback.interval

       Time in centi-second."
   ::= {er1646v2ATMFwVpEntry 33685504}

er1646v2ATMFwVpLbFailsPerm OBJECT-TYPE
   SYNTAX      Integer32
   MAX-ACCESS  read-write
   STATUS      current
   DESCRIPTION
      "Path: atm.editConf.vp.oamF4Loopback.failsPermitted"
   ::= {er1646v2ATMFwVpEntry 33816576}

er1646v2ATMFwVpLbTar OBJECT-TYPE
   SYNTAX      INTEGER
               {
               endToEnd (0),
               segment (1),
               both (2)
               }
   MAX-ACCESS  read-write
   STATUS      current
   DESCRIPTION
      "Path: atm.editConf.vp.oamF4Loopback.target

       Possibilities:
               endToEnd   (0)
               segment   (1)
               both   (2)"
   ::= {er1646v2ATMFwVpEntry 33882112}

er1646v2ATMFwVpCcDir OBJECT-TYPE
   SYNTAX      INTEGER
               {
               sink (1),
               source (2),
               both (3)
               }
   MAX-ACCESS  read-write
   STATUS      current
   DESCRIPTION
      "Path: atm.editConf.vp.oamF4CC.direction

       Possibilities:
               sink   (1)
               source   (2)
               both   (3)"
   ::= {er1646v2ATMFwVpEntry 50397184}

er1646v2ATMFwVpCcTar OBJECT-TYPE
   SYNTAX      INTEGER
               {
               endToEnd (0),
               segment (1),
               both (2)
               }
   MAX-ACCESS  read-write
   STATUS      current
   DESCRIPTION
      "Path: atm.editConf.vp.oamF4CC.target

       Possibilities:
               endToEnd   (0)
               segment   (1)
               both   (2)"
   ::= {er1646v2ATMFwVpEntry 50462720}

er1646v2ATMFwVpCcTxMode OBJECT-TYPE
   SYNTAX      INTEGER
               {
               continuously (0),
               onIdle (1)
               }
   MAX-ACCESS  read-write
   STATUS      current
   DESCRIPTION
      "Path: atm.editConf.vp.oamF4CC.tx.mode

       Possibilities:
               continuously   (0)
               onIdle   (1)"
   ::= {er1646v2ATMFwVpEntry 50528512}

er1646v2ATMFwVpCcTxTxPer OBJECT-TYPE
   SYNTAX      TimeTicks
   MAX-ACCESS  read-write
   STATUS      current
   DESCRIPTION
      "Path: atm.editConf.vp.oamF4CC.tx.interval

       Time in centi-second."
   ::= {er1646v2ATMFwVpEntry 50528768}

er1646v2ATMFwVpCcRxRcvTim OBJECT-TYPE
   SYNTAX      TimeTicks
   MAX-ACCESS  read-write
   STATUS      current
   DESCRIPTION
      "Path: atm.editConf.vp.oamF4CC.rx.timeOut

       Time in centi-second."
   ::= {er1646v2ATMFwVpEntry 50725120}

er1646v2ATMFwVpCcActProc OBJECT-TYPE
   SYNTAX      INTEGER
               {
               passive (0),
               activated (1),
               deactivated (2),
               initActivation (3)
               }
   MAX-ACCESS  read-write
   STATUS      current
   DESCRIPTION
      "Path: atm.editConf.vp.oamF4CC.actDeact.initProcedure

       Possibilities:
               passive   (0)
               activated   (1)
               deactivated   (2)
               initActivation   (3)"
   ::= {er1646v2ATMFwVpEntry 50594048}

er1646v2ATMFwVpCcActTim OBJECT-TYPE
   SYNTAX      TimeTicks
   MAX-ACCESS  read-write
   STATUS      current
   DESCRIPTION
      "Path: atm.editConf.vp.oamF4CC.actDeact.retryInterval

       Time in centi-second."
   ::= {er1646v2ATMFwVpEntry 50594304}

er1646v2ATMFwVpCcActCnt OBJECT-TYPE
   SYNTAX      Integer32
   MAX-ACCESS  read-write
   STATUS      current
   DESCRIPTION
      "Path: atm.editConf.vp.oamF4CC.actDeact.retryCount"
   ::= {er1646v2ATMFwVpEntry 50594560}

er1646v2ATMFwVpPmDir OBJECT-TYPE
   SYNTAX      INTEGER
               {
               sink (1),
               source (2),
               both (3)
               }
   MAX-ACCESS  read-write
   STATUS      current
   DESCRIPTION
      "Path: atm.editConf.vp.oamF4PM.direction

       Possibilities:
               sink   (1)
               source   (2)
               both   (3)"
   ::= {er1646v2ATMFwVpEntry 67174400}

er1646v2ATMFwVpPmTar OBJECT-TYPE
   SYNTAX      INTEGER
               {
               endToEnd (0),
               segment (1)
               }
   MAX-ACCESS  read-write
   STATUS      current
   DESCRIPTION
      "Path: atm.editConf.vp.oamF4PM.target

       Possibilities:
               endToEnd   (0)
               segment   (1)"
   ::= {er1646v2ATMFwVpEntry 67239936}

er1646v2ATMFwVpPmType OBJECT-TYPE
   SYNTAX      INTEGER
               {
               fpm (0),
               fpmWithBr (1)
               }
   MAX-ACCESS  read-write
   STATUS      current
   DESCRIPTION
      "Path: atm.editConf.vp.oamF4PM.type

       Possibilities:
               fpm   (0)
               fpmWithBr   (1)"
   ::= {er1646v2ATMFwVpEntry 67305472}

er1646v2ATMFwVpPmPolicy OBJECT-TYPE
   SYNTAX      INTEGER
               {
               inband (0),
               outband (1)
               }
   MAX-ACCESS  read-write
   STATUS      current
   DESCRIPTION
      "Path: atm.editConf.vp.oamF4PM.policy

       Possibilities:
               inband   (0)
               outband   (1)"
   ::= {er1646v2ATMFwVpEntry 67371008}

er1646v2ATMFwVpPmBsizeamb OBJECT-TYPE
   SYNTAX      INTEGER
               {
               s128 (0),
               s256 (1),
               s512 (2),
               s1024 (3),
               s2048 (4),
               s4096 (5),
               s8192 (6),
               s16384 (7),
               s32768 (8)
               }
   MAX-ACCESS  read-write
   STATUS      current
   DESCRIPTION
      "Path: atm.editConf.vp.oamF4PM.blockSizeAB

       Possibilities:
               128   (0)
               256   (1)
               512   (2)
               1024   (3)
               2048   (4)
               4096   (5)
               8192   (6)
               16384   (7)
               32768   (8)"
   ::= {er1646v2ATMFwVpEntry 67436544}

er1646v2ATMFwVpPmBsizebma OBJECT-TYPE
   SYNTAX      INTEGER
               {
               s128 (0),
               s256 (1),
               s512 (2),
               s1024 (3),
               s2048 (4),
               s4096 (5),
               s8192 (6),
               s16384 (7),
               s32768 (8)
               }
   MAX-ACCESS  read-write
   STATUS      current
   DESCRIPTION
      "Path: atm.editConf.vp.oamF4PM.blockSizeBA

       Possibilities:
               128   (0)
               256   (1)
               512   (2)
               1024   (3)
               2048   (4)
               4096   (5)
               8192   (6)
               16384   (7)
               32768   (8)"
   ::= {er1646v2ATMFwVpEntry 67502080}

er1646v2ATMFwVpPmActProc OBJECT-TYPE
   SYNTAX      INTEGER
               {
               passive (0),
               activated (1),
               deactivated (2),
               initActivation (3)
               }
   MAX-ACCESS  read-write
   STATUS      current
   DESCRIPTION
      "Path: atm.editConf.vp.oamF4PM.actDeact.initProcedure

       Possibilities:
               passive   (0)
               activated   (1)
               deactivated   (2)
               initActivation   (3)"
   ::= {er1646v2ATMFwVpEntry 67567872}

er1646v2ATMFwVpPmActTim OBJECT-TYPE
   SYNTAX      TimeTicks
   MAX-ACCESS  read-write
   STATUS      current
   DESCRIPTION
      "Path: atm.editConf.vp.oamF4PM.actDeact.retryInterval

       Time in centi-second."
   ::= {er1646v2ATMFwVpEntry 67568128}

er1646v2ATMFwVpPmActCnt OBJECT-TYPE
   SYNTAX      Integer32
   MAX-ACCESS  read-write
   STATUS      current
   DESCRIPTION
      "Path: atm.editConf.vp.oamF4PM.actDeact.retryCount"
   ::= {er1646v2ATMFwVpEntry 67568384}

er1646v2ATMFwVpCpt OBJECT-TYPE
   SYNTAX      INTEGER
               {
               no (0),
               yes (1)
               }
   MAX-ACCESS  read-write
   STATUS      current
   DESCRIPTION
      "Path: atm.editConf.vp.segmentEndPoint

       Possibilities:
               no   (0)
               yes   (1)"
   ::= {er1646v2ATMFwVpEntry 83886080}


er1646v2ATMFwCfg OBJECT IDENTIFIER ::= {er1646v2ATMFw 1}

er1646v2ATMFwCfgSSCTable OBJECT-TYPE
   SYNTAX      SEQUENCE OF Er1646v2ATMFwCfgEntry
   MAX-ACCESS  not-accessible
   STATUS      current
   DESCRIPTION
      ""
   ::= {er1646v2ATMFwCfg 1}

er1646v2ATMFwCfgEntry OBJECT-TYPE
   SYNTAX      Er1646v2ATMFwCfgEntry
   MAX-ACCESS  not-accessible
   STATUS      current
   DESCRIPTION
      ""
   INDEX      { er1646v2ATMFwCfgGlobalIx,
                er1646v2ATMFwCfgTableIx }
   ::= {er1646v2ATMFwCfgSSCTable 1}

Er1646v2ATMFwCfgEntry ::=
   SEQUENCE
      {
      er1646v2ATMFwCfgActions
         VariableLengthTableActions,
      er1646v2ATMFwCfgGlobalIx
         GlobalIndex,
      er1646v2ATMFwCfgTableIx
         TableIndex,
      er1646v2ATMFwCfgName
         DisplayString,
      er1646v2ATMFwCfgRemark
         DisplayString,
      er1646v2ATMFwCfgAdminStatus
         INTEGER,
      er1646v2ATMFwCfgMode
         INTEGER,
      er1646v2ATMFwCfgPriorityPolicy
         DisplayString,
      er1646v2ATMFwCfgDelayOptimisation
         INTEGER,
      er1646v2ATMFwCfgIpVrfRouter
         DisplayString,
      er1646v2ATMFwCfgIpAdr
         IpAddress,
      er1646v2ATMFwCfgIpNetm
         IpAddress,
      er1646v2ATMFwCfgIpSNetName
         INTEGER,
      er1646v2ATMFwCfgIpSNetCust
         DisplayString,
      er1646v2ATMFwCfgIpRem
         IpAddress,
      er1646v2ATMFwCfgIpUnnumbered
         DisplayString,
      er1646v2ATMFwCfgIpGwPref
         Integer32,
      er1646v2ATMFwCfgIpRsn
         INTEGER,
      er1646v2ATMFwCfgIpMtu
         Integer32,
      er1646v2ATMFwCfgIpMssAdjust
         INTEGER,
      er1646v2ATMFwCfgIpRipMetric
         Integer32,
      er1646v2ATMFwCfgIpRipMetricOut
         Integer32,
      er1646v2ATMFwCfgIpRipMode
         INTEGER,
      er1646v2ATMFwCfgIpRipTxVer
         INTEGER,
      er1646v2ATMFwCfgIpRipRxVer
         INTEGER,
      er1646v2ATMFwCfgIpRipSplitH
         INTEGER,
      er1646v2ATMFwCfgIpRipAuth
         INTEGER,
      er1646v2ATMFwCfgIpRipFilter
         DisplayString,
      er1646v2ATMFwCfgIpRipFilterIn
         DisplayString,
      er1646v2ATMFwCfgIpRipClearNextHop
         INTEGER,
      er1646v2ATMFwCfgIpAccPol
         DisplayString,
      er1646v2ATMFwCfgIpAB
         DisplayString,
      er1646v2ATMFwCfgIpMA
         INTEGER,
      er1646v2ATMFwCfgIpMF
         Integer32,
      er1646v2ATMFwCfgIpDB
         INTEGER,
      er1646v2ATMFwCfgIpIR
         INTEGER,
      er1646v2ATMFwCfgIpIgmp
         INTEGER,
      er1646v2ATMFwCfgIpNN
         DisplayString,
      er1646v2ATMFwCfgIpPimMode
         INTEGER,
      er1646v2ATMFwCfgIpPimDrPriority
         Counter32,
      er1646v2ATMFwCfgIpPimHelloTime
         TimeTicks,
      er1646v2ATMFwCfgIpPimPropagationDelay
         TimeTicks,
      er1646v2ATMFwCfgIpPimOverrideInterval
         TimeTicks,
      er1646v2ATMFwCfgIpPimBsrBorder
         INTEGER,
      er1646v2ATMFwCfgIpPimTtlThreshold
         Integer32,
      er1646v2ATMFwCfgIpIMNetworkUnreachable
         INTEGER,
      er1646v2ATMFwCfgIpIMHostUnreachable
         INTEGER,
      er1646v2ATMFwCfgIpIMProtocolUnreachable
         INTEGER,
      er1646v2ATMFwCfgIpIMPortUnreachable
         INTEGER,
      er1646v2ATMFwCfgIpIMMtuExceeded
         INTEGER,
      er1646v2ATMFwCfgIpIMAdminProhibited
         INTEGER,
      er1646v2ATMFwCfgIpIMTtlExceeded
         INTEGER,
      er1646v2ATMFwCfgIpIMRedirect
         INTEGER,
      er1646v2ATMFwCfgIpV6VrfRouter
         DisplayString,
      er1646v2ATMFwCfgIpV6AddrAutoConfigNrDupAddrDetects
         Integer32,
      er1646v2ATMFwCfgIpV6AddrAutoConfigAcceptRa
         INTEGER,
      er1646v2ATMFwCfgIpV6AddrAutoConfigAcceptRaRdnss
         INTEGER,
      er1646v2ATMFwCfgIpV6AddrAutoConfigAcceptRaDnssl
         INTEGER,
      er1646v2ATMFwCfgIpV6DefaultRoute
         INTEGER,
      er1646v2ATMFwCfgIpV6RaSend
         INTEGER,
      er1646v2ATMFwCfgIpV6RaMinInterval
         TimeTicks,
      er1646v2ATMFwCfgIpV6RaMaxInterval
         TimeTicks,
      er1646v2ATMFwCfgIpV6RaManagedFlag
         INTEGER,
      er1646v2ATMFwCfgIpV6RaOtherConfFlag
         INTEGER,
      er1646v2ATMFwCfgIpV6RaLinkMtu
         Integer32,
      er1646v2ATMFwCfgIpV6RaReachableTime
         TimeTicks,
      er1646v2ATMFwCfgIpV6RaRetransmitTime
         TimeTicks,
      er1646v2ATMFwCfgIpV6RaHopLimit
         Integer32,
      er1646v2ATMFwCfgIpV6RaDefaultLifeTime
         TimeTicks,
      er1646v2ATMFwCfgIpV6RaDnsOptionsRdnssLifeTime
         TimeTicks,
      er1646v2ATMFwCfgIpV6RaDnsOptionsRdnssImportServers
         INTEGER,
      er1646v2ATMFwCfgIpV6RaDnsOptionsDnsslLifeTime
         TimeTicks,
      er1646v2ATMFwCfgIpV6RaDnsOptionsDnsslImportDomains
         INTEGER,
      er1646v2ATMFwCfgIpV6RsSend
         INTEGER,
      er1646v2ATMFwCfgIpV6RsMaxRandomDelay
         TimeTicks,
      er1646v2ATMFwCfgIpV6RsInterval
         TimeTicks,
      er1646v2ATMFwCfgIpV6RsMaxSolicitations
         Integer32,
      er1646v2ATMFwCfgIpV6TrafficPolicyInbound
         DisplayString,
      er1646v2ATMFwCfgIpV6TrafficPolicyOutbound
         DisplayString,
      er1646v2ATMFwCfgIpV6FirewallZone
         DisplayString,
      er1646v2ATMFwCfgIpV6DhcpClientAddrAC
         INTEGER,
      er1646v2ATMFwCfgIpV6DhcpClientPrDelMode
         INTEGER,
      er1646v2ATMFwCfgIpV6DhcpClientPrDelPool
         DisplayString,
      er1646v2ATMFwCfgIpV6DhcpClientPrDelPdExclOpt
         INTEGER,
      er1646v2ATMFwCfgIpV6DhcpClientDnsServerPref
         Integer32,
      er1646v2ATMFwCfgIpV6DhcpClientRapidCommit
         INTEGER,
      er1646v2ATMFwCfgIpV6DhcpClientTimersSolTimeOut
         TimeTicks,
      er1646v2ATMFwCfgIpV6DhcpClientTimersSolMaxRt
         TimeTicks,
      er1646v2ATMFwCfgIpV6DhcpClientTimersInfoRefresh
         TimeTicks,
      er1646v2ATMFwCfgIpV6DhcpServerMode
         INTEGER,
      er1646v2ATMFwCfgIpV6DhcpServerPreference
         Integer32,
      er1646v2ATMFwCfgIpV6DhcpServerPool
         DisplayString,
      er1646v2ATMFwCfgIpV6DhcpServerRapidCommit
         INTEGER,
      er1646v2ATMFwCfgIpV6DhcpServerTimersInfoRefresh
         TimeTicks,
      er1646v2ATMFwCfgIpV6DhcpRelayMode
         INTEGER,
      er1646v2ATMFwCfgIpV6SendRedirect
         INTEGER,
      er1646v2ATMFwCfgIpV6LinkMtu
         Integer32,
      er1646v2ATMFwCfgIpV6InterfaceId
         OCTET STRING,
      er1646v2ATMFwCfgIpV6MF
         Integer32,
      er1646v2ATMFwCfgIpV6IcmpMessagesNoRoute
         INTEGER,
      er1646v2ATMFwCfgIpV6IcmpMessagesBeyondScope
         INTEGER,
      er1646v2ATMFwCfgIpV6IcmpMessagesAddressUnreachable
         INTEGER,
      er1646v2ATMFwCfgIpV6IcmpMessagesPortUnreachable
         INTEGER,
      er1646v2ATMFwCfgIpV6IcmpMessagesPacketTooBig
         INTEGER,
      er1646v2ATMFwCfgIpV6IcmpMessagesHopLimitExceeded
         INTEGER,
      er1646v2ATMFwCfgIpV6IcmpMessagesFragTimeExceeded
         INTEGER,
      er1646v2ATMFwCfgIpV6IcmpMessagesHeaderFieldErr
         INTEGER,
      er1646v2ATMFwCfgIpV6IcmpMessagesOptionUnrecognized
         INTEGER,
      er1646v2ATMFwCfgIpV6IcmpMessagesRedirect
         INTEGER,
      er1646v2ATMFwCfgBridgingAccList
         DisplayString,
      er1646v2ATMFwCfgBridgingInACL
         DisplayString,
      er1646v2ATMFwCfgBridgingTp
         DisplayString,
      er1646v2ATMFwCfgBridgingBrGrp
         DisplayString,
      er1646v2ATMFwCfgBridgingLimBC
         INTEGER,
      er1646v2ATMFwCfgBridgingPrivateMode
         INTEGER,
      er1646v2ATMFwCfgBridgingLearning
         INTEGER,
      er1646v2ATMFwCfgBridgingMaxCacheSize
         INTEGER,
      er1646v2ATMFwCfgBridgingRelearnDropOnRelearn
         INTEGER,
      er1646v2ATMFwCfgBridgingRelearnShutdownThreshold
         Integer32,
      er1646v2ATMFwCfgBridgingRelearnShutdownTime
         TimeTicks,
      er1646v2ATMFwCfgBridgingRelearnLoopDetection
         INTEGER,
      er1646v2ATMFwCfgBridgingRelearnLoopDetectionInterval
         TimeTicks,
      er1646v2ATMFwCfgBridgingVlanMemberShip
         INTEGER,
      er1646v2ATMFwCfgBridgingVlTUntaggedAction
         INTEGER,
      er1646v2ATMFwCfgBridgingVlTUntaggedTagInfoTpid
         INTEGER,
      er1646v2ATMFwCfgBridgingVlTUntaggedTagInfoVid
         Integer32,
      er1646v2ATMFwCfgBridgingVlTUnknownVlansAction
         INTEGER,
      er1646v2ATMFwCfgBridgingVlTUnknownVlansTagInfoTpid
         INTEGER,
      er1646v2ATMFwCfgBridgingVlTUnknownVlansTagInfoVid
         Integer32,
      er1646v2ATMFwCfgBridgingDot1adType
         INTEGER,
      er1646v2ATMFwCfgBridgingPriority
         Integer32,
      er1646v2ATMFwCfgBridgingPathCost
         Integer32,
      er1646v2ATMFwCfgBridgingInternalPathCost
         Integer32,
      er1646v2ATMFwCfgBridgingTCD
         INTEGER,
      er1646v2ATMFwCfgBridgingRestrictedRole
         INTEGER,
      er1646v2ATMFwCfgBridgingAdminEdge
         INTEGER,
      er1646v2ATMFwCfgBridgingOamMacDeviceMac
         DisplayString,
      er1646v2ATMFwCfgBridgingOamMacUserMac
         OCTET STRING,
      er1646v2ATMFwCfgBridgingOamMacBridgeMac
         DisplayString,
      er1646v2ATMFwCfgBridgingMgmtInline
         INTEGER,
      er1646v2ATMFwCfgBridgingL2ptMode
         INTEGER,
      er1646v2ATMFwCfgBridgingL2ptProtocols
         Integer32,
      er1646v2ATMFwCfgBridgingL2ptDestMac
         OCTET STRING,
      er1646v2ATMFwCfgBridgingL2ptCos
         INTEGER,
      er1646v2ATMFwCfgBridgingL2ptDropThrStp
         INTEGER,
      er1646v2ATMFwCfgBridgingL2ptDropThrLldp
         INTEGER,
      er1646v2ATMFwCfgBridgingL2ptDropThrOam
         INTEGER,
      er1646v2ATMFwCfgBridgingL2ptDropThrCdp
         INTEGER,
      er1646v2ATMFwCfgBridgingL2ptDropThrVtp
         INTEGER,
      er1646v2ATMFwCfgBridgingL2ptDropThrLacp
         INTEGER,
      er1646v2ATMFwCfgBridgingL2ptDropThrEfmOam
         INTEGER,
      er1646v2ATMFwCfgBridgingL2ptDropThrPvst
         INTEGER,
      er1646v2ATMFwCfgBridgingL2ptDropThrMmrp
         INTEGER,
      er1646v2ATMFwCfgBridgingL2ptDropThrMvrp
         INTEGER,
      er1646v2ATMFwCfgBridgingL2ptDropThrGvrp
         INTEGER,
      er1646v2ATMFwCfgBridgingL2ptDropThrGmrp
         INTEGER,
      er1646v2ATMFwCfgBridgingL2ptDropThrDtp
         INTEGER,
      er1646v2ATMFwCfgBridgingL2ptDropThrPagp
         INTEGER,
      er1646v2ATMFwCfgBridgingL2ptDropThrUdld
         INTEGER,
      er1646v2ATMFwCfgVirtEthernetVirtualEthernet
         DisplayString,
      er1646v2ATMFwCfgAtmVpi
         Integer32,
      er1646v2ATMFwCfgAtmVci
         Integer32,
      er1646v2ATMFwCfgAtmHighLayProt
         INTEGER,
      er1646v2ATMFwCfgAtmMultiProt
         INTEGER,
      er1646v2ATMFwCfgAtmServCat
         INTEGER,
      er1646v2ATMFwCfgAtmPeakCellRate
         INTEGER,
      er1646v2ATMFwCfgAtmSustCellRate
         INTEGER,
      er1646v2ATMFwCfgAtmMaxBurstSize
         Integer32,
      er1646v2ATMFwCfgAtmInArpTimeOut
         TimeTicks,
      er1646v2ATMFwCfgAtmF5LbOper
         INTEGER,
      er1646v2ATMFwCfgAtmF5LbInterval
         TimeTicks,
      er1646v2ATMFwCfgAtmF5LbFailsPerm
         Integer32,
      er1646v2ATMFwCfgAtmF5LbTar
         INTEGER,
      er1646v2ATMFwCfgAtmF5ccDir
         INTEGER,
      er1646v2ATMFwCfgAtmF5ccTar
         INTEGER,
      er1646v2ATMFwCfgAtmF5ccTxMode
         INTEGER,
      er1646v2ATMFwCfgAtmF5ccTxTxPer
         TimeTicks,
      er1646v2ATMFwCfgAtmF5ccRxRcvTim
         TimeTicks,
      er1646v2ATMFwCfgAtmF5ccActProc
         INTEGER,
      er1646v2ATMFwCfgAtmF5ccActTim
         TimeTicks,
      er1646v2ATMFwCfgAtmF5ccActCnt
         Integer32,
      er1646v2ATMFwCfgAtmF5pmDir
         INTEGER,
      er1646v2ATMFwCfgAtmF5pmTar
         INTEGER,
      er1646v2ATMFwCfgAtmF5pmType
         INTEGER,
      er1646v2ATMFwCfgAtmF5pmPolicy
         INTEGER,
      er1646v2ATMFwCfgAtmF5pmBsizeamb
         INTEGER,
      er1646v2ATMFwCfgAtmF5pmBsizebma
         INTEGER,
      er1646v2ATMFwCfgAtmF5pmActProc
         INTEGER,
      er1646v2ATMFwCfgAtmF5pmActTim
         TimeTicks,
      er1646v2ATMFwCfgAtmF5pmActCnt
         Integer32,
      er1646v2ATMFwCfgAtmCpt
         INTEGER,
      er1646v2ATMFwCfgPppLnkMOperation
         INTEGER,
      er1646v2ATMFwCfgPppLnkMInterval
         TimeTicks,
      er1646v2ATMFwCfgPppLnkMRepTimeOut
         TimeTicks,
      er1646v2ATMFwCfgPppLnkMFailsPrmt
         Integer32,
      er1646v2ATMFwCfgPppAuthentication
         INTEGER,
      er1646v2ATMFwCfgPppAuthenPeriod
         TimeTicks,
      er1646v2ATMFwCfgPppCompression
         INTEGER,
      er1646v2ATMFwCfgPppSessionName
         DisplayString,
      er1646v2ATMFwCfgPppSessionSecret
         DisplayString,
      er1646v2ATMFwCfgPppEncModeSessionSecret
         INTEGER,
      er1646v2ATMFwCfgPppEncSessionSecret
         DisplayString,
      er1646v2ATMFwCfgPppServiceName
         DisplayString,
      er1646v2ATMFwCfgFrComLmiMode
         INTEGER,
      er1646v2ATMFwCfgFrComLmiType
         INTEGER,
      er1646v2ATMFwCfgFrComLmiPollInt
         TimeTicks,
      er1646v2ATMFwCfgFrComLmiErrThres
         Integer32,
      er1646v2ATMFwCfgFrComLmiMonEvt
         Integer32,
      er1646v2ATMFwCfgFrComLmiExpPollInt
         TimeTicks,
      er1646v2ATMFwCfgFrComLmiFullEnqInt
         Integer32,
      er1646v2ATMFwCfgFrComFragIMode
         INTEGER,
      er1646v2ATMFwCfgFrComMLD
         INTEGER,
      er1646v2ATMFwCfgInbBwCir
         Integer32,
      er1646v2ATMFwCfgInbBwTc
         INTEGER,
      er1646v2ATMFwCfgInbBwCorrType
         INTEGER,
      er1646v2ATMFwCfgInbBwCorrPredefEncapsFrameRelay
         DisplayString,
      er1646v2ATMFwCfgInbBwCorrPredefEncapsPpp
         DisplayString,
      er1646v2ATMFwCfgInbBwCorrPredefEncapsAtmHl
         INTEGER,
      er1646v2ATMFwCfgInbBwCorrPredefEncapsAtmMp
         INTEGER,
      er1646v2ATMFwCfgInbBwCorrPredefEncapsHdlc
         DisplayString,
      er1646v2ATMFwCfgInbBwCorrPredefEncapsEfmFs
         Integer32,
      er1646v2ATMFwCfgInbBwCorrPredefEncapsEfmIb
         Integer32,
      er1646v2ATMFwCfgInbBwCorrPredefMode
         INTEGER,
      er1646v2ATMFwCfgInbBwCorrManualOverhead
         Integer32,
      er1646v2ATMFwCfgInbBwCorrManualFrameData
         Counter32,
      er1646v2ATMFwCfgInbBwCorrManualFrameHeader
         Counter32,
      er1646v2ATMFwCfgInbBwMaxFifoQLen
         Integer32,
      er1646v2ATMFwCfgInbBwPriorityPolicy
         DisplayString
      }

er1646v2ATMFwCfgActions OBJECT-TYPE
   SYNTAX      VariableLengthTableActions
   MAX-ACCESS  read-write
   STATUS      current
   DESCRIPTION
      "By way of this field, some manipulations
       on this table may be performed."
   ::= {er1646v2ATMFwCfgEntry 2}

er1646v2ATMFwCfgGlobalIx OBJECT-TYPE
   SYNTAX      GlobalIndex
   MAX-ACCESS  not-accessible
   STATUS      current
   DESCRIPTION
      "The value of the tlsCntTreeGlobalIndex of the MANAGED OBJECT."
   ::= {er1646v2ATMFwCfgEntry 10}

er1646v2ATMFwCfgTableIx OBJECT-TYPE
   SYNTAX      TableIndex
   MAX-ACCESS  not-accessible
   STATUS      current
   DESCRIPTION
      ""
   ::= {er1646v2ATMFwCfgEntry 11}

er1646v2ATMFwCfgName OBJECT-TYPE
   SYNTAX      DisplayString
   MAX-ACCESS  read-write
   STATUS      current
   DESCRIPTION
      "Path: atm.editConf.pvcTable.name"
   ::= {er1646v2ATMFwCfgEntry 16777216}

er1646v2ATMFwCfgRemark OBJECT-TYPE
   SYNTAX      DisplayString
   MAX-ACCESS  read-write
   STATUS      current
   DESCRIPTION
      "Path: atm.editConf.pvcTable.remark"
   ::= {er1646v2ATMFwCfgEntry 1157627904}

er1646v2ATMFwCfgAdminStatus OBJECT-TYPE
   SYNTAX      INTEGER
               {
               up (1),
               down (2)
               }
   MAX-ACCESS  read-write
   STATUS      current
   DESCRIPTION
      "Path: atm.editConf.pvcTable.adminStatus

       Possibilities:
               up   (1)
               down   (2)"
   ::= {er1646v2ATMFwCfgEntry 33554432}

er1646v2ATMFwCfgMode OBJECT-TYPE
   SYNTAX      INTEGER
               {
               routing (1),
               ipV6 (16),
               ipV6ipV4 (17),
               bridging (2),
               routingAndBridging (3),
               multiLink (8),
               virtEthernet (32),
               iwf (128)
               }
   MAX-ACCESS  read-write
   STATUS      current
   DESCRIPTION
      "Path: atm.editConf.pvcTable.mode

       Possibilities:
               routing   (1)
               ipV6   (16)
               ipV6/ipV4   (17)
               bridging   (2)
               routingAndBridging   (3)
               multiLink   (8)
               virtEthernet   (32)
               iwf   (128)"
   ::= {er1646v2ATMFwCfgEntry 67108864}

er1646v2ATMFwCfgPriorityPolicy OBJECT-TYPE
   SYNTAX      DisplayString
   MAX-ACCESS  read-write
   STATUS      current
   DESCRIPTION
      "Path: atm.editConf.pvcTable.priorityPolicy"
   ::= {er1646v2ATMFwCfgEntry 83886080}

er1646v2ATMFwCfgDelayOptimisation OBJECT-TYPE
   SYNTAX      INTEGER
               {
               disabled (0),
               enabled (1)
               }
   MAX-ACCESS  read-write
   STATUS      current
   DESCRIPTION
      "Path: atm.editConf.pvcTable.delayOptimisation

       Possibilities:
               disabled   (0)
               enabled   (1)"
   ::= {er1646v2ATMFwCfgEntry 553648128}

er1646v2ATMFwCfgIpVrfRouter OBJECT-TYPE
   SYNTAX      DisplayString
   MAX-ACCESS  read-write
   STATUS      current
   DESCRIPTION
      "Path: atm.editConf.pvcTable.ip.vrfRouter"
   ::= {er1646v2ATMFwCfgEntry 53215232}

er1646v2ATMFwCfgIpAdr OBJECT-TYPE
   SYNTAX      IpAddress
   MAX-ACCESS  read-write
   STATUS      current
   DESCRIPTION
      "Path: atm.editConf.pvcTable.ip.address"
   ::= {er1646v2ATMFwCfgEntry 58261504}

er1646v2ATMFwCfgIpNetm OBJECT-TYPE
   SYNTAX      IpAddress
   MAX-ACCESS  read-write
   STATUS      current
   DESCRIPTION
      "Path: atm.editConf.pvcTable.ip.netMask"
   ::= {er1646v2ATMFwCfgEntry 58392576}

er1646v2ATMFwCfgIpSNetName OBJECT-TYPE
   SYNTAX      INTEGER
               {
               slOPTg (0),
               corp (2),
               dmz (3),
               internet (1)
               }
   MAX-ACCESS  read-write
   STATUS      current
   DESCRIPTION
      "Path: atm.editConf.pvcTable.ip.sNet.name

       Possibilities:
               <OPT>   (0)
               corp   (2)
               dmz   (3)
               internet   (1)"
   ::= {er1646v2ATMFwCfgEntry 53674240}

er1646v2ATMFwCfgIpSNetCust OBJECT-TYPE
   SYNTAX      DisplayString
   MAX-ACCESS  read-write
   STATUS      current
   DESCRIPTION
      "Path: atm.editConf.pvcTable.ip.sNet.custom"
   ::= {er1646v2ATMFwCfgEntry 53674496}

er1646v2ATMFwCfgIpRem OBJECT-TYPE
   SYNTAX      IpAddress
   MAX-ACCESS  read-write
   STATUS      current
   DESCRIPTION
      "Path: atm.editConf.pvcTable.ip.remote"
   ::= {er1646v2ATMFwCfgEntry 58458112}

er1646v2ATMFwCfgIpUnnumbered OBJECT-TYPE
   SYNTAX      DisplayString
   MAX-ACCESS  read-write
   STATUS      current
   DESCRIPTION
      "Path: atm.editConf.pvcTable.ip.unnumbered"
   ::= {er1646v2ATMFwCfgEntry 52625408}

er1646v2ATMFwCfgIpGwPref OBJECT-TYPE
   SYNTAX      Integer32
   MAX-ACCESS  read-write
   STATUS      current
   DESCRIPTION
      "Path: atm.editConf.pvcTable.ip.gatewayPreference"
   ::= {er1646v2ATMFwCfgEntry 52690944}

er1646v2ATMFwCfgIpRsn OBJECT-TYPE
   SYNTAX      INTEGER
               {
               disabled (0),
               enabled (1)
               }
   MAX-ACCESS  read-write
   STATUS      current
   DESCRIPTION
      "Path: atm.editConf.pvcTable.ip.requestSubnet

       Possibilities:
               disabled   (0)
               enabled   (1)"
   ::= {er1646v2ATMFwCfgEntry 56688640}

er1646v2ATMFwCfgIpMtu OBJECT-TYPE
   SYNTAX      Integer32
   MAX-ACCESS  read-write
   STATUS      current
   DESCRIPTION
      "Path: atm.editConf.pvcTable.ip.mtu"
   ::= {er1646v2ATMFwCfgEntry 52953088}

er1646v2ATMFwCfgIpMssAdjust OBJECT-TYPE
   SYNTAX      INTEGER
               {
               disabled (0),
               auto (65536)
               }
   MAX-ACCESS  read-write
   STATUS      current
   DESCRIPTION
      "Path: atm.editConf.pvcTable.ip.mssAdjust

       Possibilities:
               disabled   (0)
               auto   (65536)"
   ::= {er1646v2ATMFwCfgEntry 53280768}

er1646v2ATMFwCfgIpRipMetric OBJECT-TYPE
   SYNTAX      Integer32
   MAX-ACCESS  read-write
   STATUS      current
   DESCRIPTION
      "Path: atm.editConf.pvcTable.ip.rip.metric"
   ::= {er1646v2ATMFwCfgEntry 51712768}

er1646v2ATMFwCfgIpRipMetricOut OBJECT-TYPE
   SYNTAX      Integer32
   MAX-ACCESS  read-write
   STATUS      current
   DESCRIPTION
      "Path: atm.editConf.pvcTable.ip.rip.metricOut"
   ::= {er1646v2ATMFwCfgEntry 51713024}

er1646v2ATMFwCfgIpRipMode OBJECT-TYPE
   SYNTAX      INTEGER
               {
               disabled (0),
               passive (1),
               active (2)
               }
   MAX-ACCESS  read-write
   STATUS      current
   DESCRIPTION
      "Path: atm.editConf.pvcTable.ip.rip.mode

       Possibilities:
               disabled   (0)
               passive   (1)
               active   (2)"
   ::= {er1646v2ATMFwCfgEntry 51713280}

er1646v2ATMFwCfgIpRipTxVer OBJECT-TYPE
   SYNTAX      INTEGER
               {
               rip1 (0),
               rip2 (1),
               rip1mcompatible (2)
               }
   MAX-ACCESS  read-write
   STATUS      current
   DESCRIPTION
      "Path: atm.editConf.pvcTable.ip.rip.txVersion

       Possibilities:
               rip1   (0)
               rip2   (1)
               rip1-compatible   (2)"
   ::= {er1646v2ATMFwCfgEntry 51716864}

er1646v2ATMFwCfgIpRipRxVer OBJECT-TYPE
   SYNTAX      INTEGER
               {
               rip1only (0),
               rip2only (1),
               rip12 (2)
               }
   MAX-ACCESS  read-write
   STATUS      current
   DESCRIPTION
      "Path: atm.editConf.pvcTable.ip.rip.rxVersion

       Possibilities:
               rip1only   (0)
               rip2only   (1)
               rip1&2   (2)"
   ::= {er1646v2ATMFwCfgEntry 51717120}

er1646v2ATMFwCfgIpRipSplitH OBJECT-TYPE
   SYNTAX      INTEGER
               {
               disabled (0),
               enabled (1),
               poisonedReverse (2)
               }
   MAX-ACCESS  read-write
   STATUS      current
   DESCRIPTION
      "Path: atm.editConf.pvcTable.ip.rip.splitHorizon

       Possibilities:
               disabled   (0)
               enabled   (1)
               poisonedReverse   (2)"
   ::= {er1646v2ATMFwCfgEntry 51713792}

er1646v2ATMFwCfgIpRipAuth OBJECT-TYPE
   SYNTAX      INTEGER
               {
               disabled (0),
               texts (1),
               md5 (2)
               }
   MAX-ACCESS  read-write
   STATUS      current
   DESCRIPTION
      "Path: atm.editConf.pvcTable.ip.rip.authentication

       Possibilities:
               disabled   (0)
               text    (1)
               md5   (2)"
   ::= {er1646v2ATMFwCfgEntry 51712512}

er1646v2ATMFwCfgIpRipFilter OBJECT-TYPE
   SYNTAX      DisplayString
   MAX-ACCESS  read-write
   STATUS      current
   DESCRIPTION
      "Path: atm.editConf.pvcTable.ip.rip.filter"
   ::= {er1646v2ATMFwCfgEntry 51716096}

er1646v2ATMFwCfgIpRipFilterIn OBJECT-TYPE
   SYNTAX      DisplayString
   MAX-ACCESS  read-write
   STATUS      current
   DESCRIPTION
      "Path: atm.editConf.pvcTable.ip.rip.filterIn"
   ::= {er1646v2ATMFwCfgEntry 51716352}

er1646v2ATMFwCfgIpRipClearNextHop OBJECT-TYPE
   SYNTAX      INTEGER
               {
               disabled (0),
               enabled (1)
               }
   MAX-ACCESS  read-write
   STATUS      current
   DESCRIPTION
      "Path: atm.editConf.pvcTable.ip.rip.clearNextHop

       Possibilities:
               disabled   (0)
               enabled   (1)"
   ::= {er1646v2ATMFwCfgEntry 51708416}

er1646v2ATMFwCfgIpAccPol OBJECT-TYPE
   SYNTAX      DisplayString
   MAX-ACCESS  read-write
   STATUS      current
   DESCRIPTION
      "Path: atm.editConf.pvcTable.ip.accessPolicy"
   ::= {er1646v2ATMFwCfgEntry 53084160}

er1646v2ATMFwCfgIpAB OBJECT-TYPE
   SYNTAX      DisplayString
   MAX-ACCESS  read-write
   STATUS      current
   DESCRIPTION
      "Path: atm.editConf.pvcTable.ip.trafficPolicy"
   ::= {er1646v2ATMFwCfgEntry 51249152}

er1646v2ATMFwCfgIpMA OBJECT-TYPE
   SYNTAX      INTEGER
               {
               disabled (0),
               enabled (1)
               }
   MAX-ACCESS  read-write
   STATUS      current
   DESCRIPTION
      "Path: atm.editConf.pvcTable.ip.mgmtAccess

       Possibilities:
               disabled   (0)
               enabled   (1)"
   ::= {er1646v2ATMFwCfgEntry 51380224}

er1646v2ATMFwCfgIpMF OBJECT-TYPE
   SYNTAX      Integer32
   MAX-ACCESS  read-write
   STATUS      current
   DESCRIPTION
      "Path: atm.editConf.pvcTable.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2ATMFwCfgEntry 51445760}

er1646v2ATMFwCfgIpDB OBJECT-TYPE
   SYNTAX      INTEGER
               {
               disabled (0),
               enabled (1)
               }
   MAX-ACCESS  read-write
   STATUS      current
   DESCRIPTION
      "Path: atm.editConf.pvcTable.ip.directedBroadcasts

       Possibilities:
               disabled   (0)
               enabled   (1)"
   ::= {er1646v2ATMFwCfgEntry 51773440}

er1646v2ATMFwCfgIpIR OBJECT-TYPE
   SYNTAX      INTEGER
               {
               disabled (0),
               enabled (1)
               }
   MAX-ACCESS  read-write
   STATUS      current
   DESCRIPTION
      "Path: atm.editConf.pvcTable.ip.icmpRedirects

       Possibilities:
               disabled   (0)
               enabled   (1)"
   ::= {er1646v2ATMFwCfgEntry 52035584}

er1646v2ATMFwCfgIpIgmp OBJECT-TYPE
   SYNTAX      INTEGER
               {
               disabled (0),
               proxy (1),
               router (2),
               v3Router (5)
               }
   MAX-ACCESS  read-write
   STATUS      current
   DESCRIPTION
      "Path: atm.editConf.pvcTable.ip.igmp

       Possibilities:
               disabled   (0)
               proxy   (1)
               router   (2)
               v3Router   (5)"
   ::= {er1646v2ATMFwCfgEntry 52428800}

er1646v2ATMFwCfgIpNN OBJECT-TYPE
   SYNTAX      DisplayString
   MAX-ACCESS  read-write
   STATUS      current
   DESCRIPTION
      "Path: atm.editConf.pvcTable.ip.nat"
   ::= {er1646v2ATMFwCfgEntry 52101120}

er1646v2ATMFwCfgIpPimMode OBJECT-TYPE
   SYNTAX      INTEGER
               {
               disabled (0),
               sparse (1),
               passive (2)
               }
   MAX-ACCESS  read-write
   STATUS      current
   DESCRIPTION
      "Path: atm.editConf.pvcTable.ip.pim.mode

       Possibilities:
               disabled   (0)
               sparse   (1)
               passive   (2)"
   ::= {er1646v2ATMFwCfgEntry 53346560}

er1646v2ATMFwCfgIpPimDrPriority OBJECT-TYPE
   SYNTAX      Counter32
   MAX-ACCESS  read-write
   STATUS      current
   DESCRIPTION
      "Path: atm.editConf.pvcTable.ip.pim.drPriority

       32 bit unsigned wrappable counter."
   ::= {er1646v2ATMFwCfgEntry 53346816}

er1646v2ATMFwCfgIpPimHelloTime OBJECT-TYPE
   SYNTAX      TimeTicks
   MAX-ACCESS  read-write
   STATUS      current
   DESCRIPTION
      "Path: atm.editConf.pvcTable.ip.pim.helloTime

       Time in centi-second."
   ::= {er1646v2ATMFwCfgEntry 53347072}

er1646v2ATMFwCfgIpPimPropagationDelay OBJECT-TYPE
   SYNTAX      TimeTicks
   MAX-ACCESS  read-write
   STATUS      current
   DESCRIPTION
      "Path: atm.editConf.pvcTable.ip.pim.propagationDelay

       Time in centi-second."
   ::= {er1646v2ATMFwCfgEntry 53347328}

er1646v2ATMFwCfgIpPimOverrideInterval OBJECT-TYPE
   SYNTAX      TimeTicks
   MAX-ACCESS  read-write
   STATUS      current
   DESCRIPTION
      "Path: atm.editConf.pvcTable.ip.pim.overrideInterval

       Time in centi-second."
   ::= {er1646v2ATMFwCfgEntry 53347584}

er1646v2ATMFwCfgIpPimBsrBorder OBJECT-TYPE
   SYNTAX      INTEGER
               {
               disabled (0),
               enabled (1)
               }
   MAX-ACCESS  read-write
   STATUS      current
   DESCRIPTION
      "Path: atm.editConf.pvcTable.ip.pim.bsrBorder

       Possibilities:
               disabled   (0)
               enabled   (1)"
   ::= {er1646v2ATMFwCfgEntry 53347840}

er1646v2ATMFwCfgIpPimTtlThreshold OBJECT-TYPE
   SYNTAX      Integer32
   MAX-ACCESS  read-write
   STATUS      current
   DESCRIPTION
      "Path: atm.editConf.pvcTable.ip.pim.ttlThreshold"
   ::= {er1646v2ATMFwCfgEntry 53348096}

er1646v2ATMFwCfgIpIMNetworkUnreachable OBJECT-TYPE
   SYNTAX      INTEGER
               {
               disabled (0),
               enabled (1)
               }
   MAX-ACCESS  read-write
   STATUS      current
   DESCRIPTION
      "Path: atm.editConf.pvcTable.ip.icmpMessages.networkUnreachable

       Possibilities:
               disabled   (0)
               enabled   (1)"
   ::= {er1646v2ATMFwCfgEntry 53412096}

er1646v2ATMFwCfgIpIMHostUnreachable OBJECT-TYPE
   SYNTAX      INTEGER
               {
               disabled (0),
               enabled (1)
               }
   MAX-ACCESS  read-write
   STATUS      current
   DESCRIPTION
      "Path: atm.editConf.pvcTable.ip.icmpMessages.hostUnreachable

       Possibilities:
               disabled   (0)
               enabled   (1)"
   ::= {er1646v2ATMFwCfgEntry 53412352}

er1646v2ATMFwCfgIpIMProtocolUnreachable OBJECT-TYPE
   SYNTAX      INTEGER
               {
               disabled (0),
               enabled (1)
               }
   MAX-ACCESS  read-write
   STATUS      current
   DESCRIPTION
      "Path: atm.editConf.pvcTable.ip.icmpMessages.protocolUnreachable

       Possibilities:
               disabled   (0)
               enabled   (1)"
   ::= {er1646v2ATMFwCfgEntry 53412608}

er1646v2ATMFwCfgIpIMPortUnreachable OBJECT-TYPE
   SYNTAX      INTEGER
               {
               disabled (0),
               enabled (1)
               }
   MAX-ACCESS  read-write
   STATUS      current
   DESCRIPTION
      "Path: atm.editConf.pvcTable.ip.icmpMessages.portUnreachable

       Possibilities:
               disabled   (0)
               enabled   (1)"
   ::= {er1646v2ATMFwCfgEntry 53412864}

er1646v2ATMFwCfgIpIMMtuExceeded OBJECT-TYPE
   SYNTAX      INTEGER
               {
               disabled (0),
               enabled (1)
               }
   MAX-ACCESS  read-write
   STATUS      current
   DESCRIPTION
      "Path: atm.editConf.pvcTable.ip.icmpMessages.mtuExceeded

       Possibilities:
               disabled   (0)
               enabled   (1)"
   ::= {er1646v2ATMFwCfgEntry 53413120}

er1646v2ATMFwCfgIpIMAdminProhibited OBJECT-TYPE
   SYNTAX      INTEGER
               {
               disabled (0),
               enabled (1)
               }
   MAX-ACCESS  read-write
   STATUS      current
   DESCRIPTION
      "Path: atm.editConf.pvcTable.ip.icmpMessages.adminProhibited

       Possibilities:
               disabled   (0)
               enabled   (1)"
   ::= {er1646v2ATMFwCfgEntry 53413376}

er1646v2ATMFwCfgIpIMTtlExceeded OBJECT-TYPE
   SYNTAX      INTEGER
               {
               disabled (0),
               enabled (1)
               }
   MAX-ACCESS  read-write
   STATUS      current
   DESCRIPTION
      "Path: atm.editConf.pvcTable.ip.icmpMessages.ttlExceeded

       Possibilities:
               disabled   (0)
               enabled   (1)"
   ::= {er1646v2ATMFwCfgEntry 53413632}

er1646v2ATMFwCfgIpIMRedirect OBJECT-TYPE
   SYNTAX      INTEGER
               {
               disabled (0),
               enabled (1)
               }
   MAX-ACCESS  read-write
   STATUS      current
   DESCRIPTION
      "Path: atm.editConf.pvcTable.ip.icmpMessages.redirect

       Possibilities:
               disabled   (0)
               enabled   (1)"
   ::= {er1646v2ATMFwCfgEntry 53413888}

er1646v2ATMFwCfgIpV6VrfRouter OBJECT-TYPE
   SYNTAX      DisplayString
   MAX-ACCESS  read-write
   STATUS      current
   DESCRIPTION
      "Path: atm.editConf.pvcTable.ipV6.vrfRouter"
   ::= {er1646v2ATMFwCfgEntry 704708608}

er1646v2ATMFwCfgIpV6AddrAutoConfigNrDupAddrDetects OBJECT-TYPE
   SYNTAX      Integer32
   MAX-ACCESS  read-write
   STATUS      current
   DESCRIPTION
      "Path: atm.editConf.pvcTable.ipV6.addrAutoConfig.nrDupAddrDetects"
   ::= {er1646v2ATMFwCfgEntry 704905472}

er1646v2ATMFwCfgIpV6AddrAutoConfigAcceptRa OBJECT-TYPE
   SYNTAX      INTEGER
               {
               disabled (0),
               enabled (1)
               }
   MAX-ACCESS  read-write
   STATUS      current
   DESCRIPTION
      "Path: atm.editConf.pvcTable.ipV6.addrAutoConfig.acceptRa

       Possibilities:
               disabled   (0)
               enabled   (1)"
   ::= {er1646v2ATMFwCfgEntry 704905728}

er1646v2ATMFwCfgIpV6AddrAutoConfigAcceptRaRdnss OBJECT-TYPE
   SYNTAX      INTEGER
               {
               disabled (0),
               enabled (1)
               }
   MAX-ACCESS  read-write
   STATUS      current
   DESCRIPTION
      "Path: atm.editConf.pvcTable.ipV6.addrAutoConfig.acceptRaRdnss

       Possibilities:
               disabled   (0)
               enabled   (1)"
   ::= {er1646v2ATMFwCfgEntry 704905984}

er1646v2ATMFwCfgIpV6AddrAutoConfigAcceptRaDnssl OBJECT-TYPE
   SYNTAX      INTEGER
               {
               disabled (0),
               enabled (1)
               }
   MAX-ACCESS  read-write
   STATUS      current
   DESCRIPTION
      "Path: atm.editConf.pvcTable.ipV6.addrAutoConfig.acceptRaDnssl

       Possibilities:
               disabled   (0)
               enabled   (1)"
   ::= {er1646v2ATMFwCfgEntry 704906240}

er1646v2ATMFwCfgIpV6DefaultRoute OBJECT-TYPE
   SYNTAX      INTEGER
               {
               disabled (0),
               enabled (1)
               }
   MAX-ACCESS  read-write
   STATUS      current
   DESCRIPTION
      "Path: atm.editConf.pvcTable.ipV6.defaultRoute

       Possibilities:
               disabled   (0)
               enabled   (1)"
   ::= {er1646v2ATMFwCfgEntry 704970752}

er1646v2ATMFwCfgIpV6RaSend OBJECT-TYPE
   SYNTAX      INTEGER
               {
               disabled (0),
               enabled (1)
               }
   MAX-ACCESS  read-write
   STATUS      current
   DESCRIPTION
      "Path: atm.editConf.pvcTable.ipV6.ra.send

       Possibilities:
               disabled   (0)
               enabled   (1)"
   ::= {er1646v2ATMFwCfgEntry 705036544}

er1646v2ATMFwCfgIpV6RaMinInterval OBJECT-TYPE
   SYNTAX      TimeTicks
   MAX-ACCESS  read-write
   STATUS      current
   DESCRIPTION
      "Path: atm.editConf.pvcTable.ipV6.ra.minInterval

       Time in centi-second."
   ::= {er1646v2ATMFwCfgEntry 705036800}

er1646v2ATMFwCfgIpV6RaMaxInterval OBJECT-TYPE
   SYNTAX      TimeTicks
   MAX-ACCESS  read-write
   STATUS      current
   DESCRIPTION
      "Path: atm.editConf.pvcTable.ipV6.ra.maxInterval

       Time in centi-second."
   ::= {er1646v2ATMFwCfgEntry 705037056}

er1646v2ATMFwCfgIpV6RaManagedFlag OBJECT-TYPE
   SYNTAX      INTEGER
               {
               disabled (0),
               enabled (1)
               }
   MAX-ACCESS  read-write
   STATUS      current
   DESCRIPTION
      "Path: atm.editConf.pvcTable.ipV6.ra.managedFlag

       Possibilities:
               disabled   (0)
               enabled   (1)"
   ::= {er1646v2ATMFwCfgEntry 705037312}

er1646v2ATMFwCfgIpV6RaOtherConfFlag OBJECT-TYPE
   SYNTAX      INTEGER
               {
               disabled (0),
               enabled (1)
               }
   MAX-ACCESS  read-write
   STATUS      current
   DESCRIPTION
      "Path: atm.editConf.pvcTable.ipV6.ra.otherConfFlag

       Possibilities:
               disabled   (0)
               enabled   (1)"
   ::= {er1646v2ATMFwCfgEntry 705037568}

er1646v2ATMFwCfgIpV6RaLinkMtu OBJECT-TYPE
   SYNTAX      Integer32
   MAX-ACCESS  read-write
   STATUS      current
   DESCRIPTION
      "Path: atm.editConf.pvcTable.ipV6.ra.linkMtu"
   ::= {er1646v2ATMFwCfgEntry 705037824}

er1646v2ATMFwCfgIpV6RaReachableTime OBJECT-TYPE
   SYNTAX      TimeTicks
   MAX-ACCESS  read-write
   STATUS      current
   DESCRIPTION
      "Path: atm.editConf.pvcTable.ipV6.ra.reachableTime

       Time in centi-second."
   ::= {er1646v2ATMFwCfgEntry 705038080}

er1646v2ATMFwCfgIpV6RaRetransmitTime OBJECT-TYPE
   SYNTAX      TimeTicks
   MAX-ACCESS  read-write
   STATUS      current
   DESCRIPTION
      "Path: atm.editConf.pvcTable.ipV6.ra.retransmitTime

       Time in centi-second."
   ::= {er1646v2ATMFwCfgEntry 705038336}

er1646v2ATMFwCfgIpV6RaHopLimit OBJECT-TYPE
   SYNTAX      Integer32
   MAX-ACCESS  read-write
   STATUS      current
   DESCRIPTION
      "Path: atm.editConf.pvcTable.ipV6.ra.hopLimit"
   ::= {er1646v2ATMFwCfgEntry 705038592}

er1646v2ATMFwCfgIpV6RaDefaultLifeTime OBJECT-TYPE
   SYNTAX      TimeTicks
   MAX-ACCESS  read-write
   STATUS      current
   DESCRIPTION
      "Path: atm.editConf.pvcTable.ipV6.ra.defaultLifeTime

       Time in centi-second."
   ::= {er1646v2ATMFwCfgEntry 705038848}

er1646v2ATMFwCfgIpV6RaDnsOptionsRdnssLifeTime OBJECT-TYPE
   SYNTAX      TimeTicks
   MAX-ACCESS  read-write
   STATUS      current
   DESCRIPTION
      "Path: atm.editConf.pvcTable.ipV6.ra.dnsOptions.rdnss.lifeTime

       Time in centi-second."
   ::= {er1646v2ATMFwCfgEntry 705039140}

er1646v2ATMFwCfgIpV6RaDnsOptionsRdnssImportServers OBJECT-TYPE
   SYNTAX      INTEGER
               {
               disabled (0),
               enabled (1)
               }
   MAX-ACCESS  read-write
   STATUS      current
   DESCRIPTION
      "Path: atm.editConf.pvcTable.ipV6.ra.dnsOptions.rdnss.importServers

       Possibilities:
               disabled   (0)
               enabled   (1)"
   ::= {er1646v2ATMFwCfgEntry 705039148}

er1646v2ATMFwCfgIpV6RaDnsOptionsDnsslLifeTime OBJECT-TYPE
   SYNTAX      TimeTicks
   MAX-ACCESS  read-write
   STATUS      current
   DESCRIPTION
      "Path: atm.editConf.pvcTable.ipV6.ra.dnsOptions.dnssl.lifeTime

       Time in centi-second."
   ::= {er1646v2ATMFwCfgEntry 705039172}

er1646v2ATMFwCfgIpV6RaDnsOptionsDnsslImportDomains OBJECT-TYPE
   SYNTAX      INTEGER
               {
               disabled (0),
               enabled (1)
               }
   MAX-ACCESS  read-write
   STATUS      current
   DESCRIPTION
      "Path: atm.editConf.pvcTable.ipV6.ra.dnsOptions.dnssl.importDomains

       Possibilities:
               disabled   (0)
               enabled   (1)"
   ::= {er1646v2ATMFwCfgEntry 705039180}

er1646v2ATMFwCfgIpV6RsSend OBJECT-TYPE
   SYNTAX      INTEGER
               {
               disabled (0),
               enabled (1)
               }
   MAX-ACCESS  read-write
   STATUS      current
   DESCRIPTION
      "Path: atm.editConf.pvcTable.ipV6.rs.send

       Possibilities:
               disabled   (0)
               enabled   (1)"
   ::= {er1646v2ATMFwCfgEntry 705954048}

er1646v2ATMFwCfgIpV6RsMaxRandomDelay OBJECT-TYPE
   SYNTAX      TimeTicks
   MAX-ACCESS  read-write
   STATUS      current
   DESCRIPTION
      "Path: atm.editConf.pvcTable.ipV6.rs.maxRandomDelay

       Time in centi-second."
   ::= {er1646v2ATMFwCfgEntry 705954304}

er1646v2ATMFwCfgIpV6RsInterval OBJECT-TYPE
   SYNTAX      TimeTicks
   MAX-ACCESS  read-write
   STATUS      current
   DESCRIPTION
      "Path: atm.editConf.pvcTable.ipV6.rs.interval

       Time in centi-second."
   ::= {er1646v2ATMFwCfgEntry 705954560}

er1646v2ATMFwCfgIpV6RsMaxSolicitations OBJECT-TYPE
   SYNTAX      Integer32
   MAX-ACCESS  read-write
   STATUS      current
   DESCRIPTION
      "Path: atm.editConf.pvcTable.ipV6.rs.maxSolicitations"
   ::= {er1646v2ATMFwCfgEntry 705954816}

er1646v2ATMFwCfgIpV6TrafficPolicyInbound OBJECT-TYPE
   SYNTAX      DisplayString
   MAX-ACCESS  read-write
   STATUS      current
   DESCRIPTION
      "Path: atm.editConf.pvcTable.ipV6.trafficPolicy.inbound"
   ::= {er1646v2ATMFwCfgEntry 705364224}

er1646v2ATMFwCfgIpV6TrafficPolicyOutbound OBJECT-TYPE
   SYNTAX      DisplayString
   MAX-ACCESS  read-write
   STATUS      current
   DESCRIPTION
      "Path: atm.editConf.pvcTable.ipV6.trafficPolicy.outbound"
   ::= {er1646v2ATMFwCfgEntry 705364480}

er1646v2ATMFwCfgIpV6FirewallZone OBJECT-TYPE
   SYNTAX      DisplayString
   MAX-ACCESS  read-write
   STATUS      current
   DESCRIPTION
      "Path: atm.editConf.pvcTable.ipV6.firewall.zone"
   ::= {er1646v2ATMFwCfgEntry 705429760}

er1646v2ATMFwCfgIpV6DhcpClientAddrAC OBJECT-TYPE
   SYNTAX      INTEGER
               {
               disabled (0),
               enabled (1)
               }
   MAX-ACCESS  read-write
   STATUS      current
   DESCRIPTION
      "Path: atm.editConf.pvcTable.ipV6.dhcp.client.addrAutoConfig

       Possibilities:
               disabled   (0)
               enabled   (1)"
   ::= {er1646v2ATMFwCfgEntry 705307648}

er1646v2ATMFwCfgIpV6DhcpClientPrDelMode OBJECT-TYPE
   SYNTAX      INTEGER
               {
               disabled (0),
               enabled (1)
               }
   MAX-ACCESS  read-write
   STATUS      current
   DESCRIPTION
      "Path: atm.editConf.pvcTable.ipV6.dhcp.client.pd.mode

       Possibilities:
               disabled   (0)
               enabled   (1)"
   ::= {er1646v2ATMFwCfgEntry 705308676}

er1646v2ATMFwCfgIpV6DhcpClientPrDelPool OBJECT-TYPE
   SYNTAX      DisplayString
   MAX-ACCESS  read-write
   STATUS      current
   DESCRIPTION
      "Path: atm.editConf.pvcTable.ipV6.dhcp.client.pd.pool"
   ::= {er1646v2ATMFwCfgEntry 705308680}

er1646v2ATMFwCfgIpV6DhcpClientPrDelPdExclOpt OBJECT-TYPE
   SYNTAX      INTEGER
               {
               disabled (0),
               enabled (1)
               }
   MAX-ACCESS  read-write
   STATUS      current
   DESCRIPTION
      "Path: atm.editConf.pvcTable.ipV6.dhcp.client.pd.pdExclOpt

       Possibilities:
               disabled   (0)
               enabled   (1)"
   ::= {er1646v2ATMFwCfgEntry 705308684}

er1646v2ATMFwCfgIpV6DhcpClientDnsServerPref OBJECT-TYPE
   SYNTAX      Integer32
   MAX-ACCESS  read-write
   STATUS      current
   DESCRIPTION
      "Path: atm.editConf.pvcTable.ipV6.dhcp.client.dns.serverPref"
   ::= {er1646v2ATMFwCfgEntry 705310724}

er1646v2ATMFwCfgIpV6DhcpClientRapidCommit OBJECT-TYPE
   SYNTAX      INTEGER
               {
               disabled (0),
               enabled (1)
               }
   MAX-ACCESS  read-write
   STATUS      current
   DESCRIPTION
      "Path: atm.editConf.pvcTable.ipV6.dhcp.client.rapidCommit

       Possibilities:
               disabled   (0)
               enabled   (1)"
   ::= {er1646v2ATMFwCfgEntry 705309696}

er1646v2ATMFwCfgIpV6DhcpClientTimersSolTimeOut OBJECT-TYPE
   SYNTAX      TimeTicks
   MAX-ACCESS  read-write
   STATUS      current
   DESCRIPTION
      "Path: atm.editConf.pvcTable.ipV6.dhcp.client.timers.solTimeOut

       Time in centi-second."
   ::= {er1646v2ATMFwCfgEntry 705311748}

er1646v2ATMFwCfgIpV6DhcpClientTimersSolMaxRt OBJECT-TYPE
   SYNTAX      TimeTicks
   MAX-ACCESS  read-write
   STATUS      current
   DESCRIPTION
      "Path: atm.editConf.pvcTable.ipV6.dhcp.client.timers.solMaxRt

       Time in centi-second."
   ::= {er1646v2ATMFwCfgEntry 705311752}

er1646v2ATMFwCfgIpV6DhcpClientTimersInfoRefresh OBJECT-TYPE
   SYNTAX      TimeTicks
   MAX-ACCESS  read-write
   STATUS      current
   DESCRIPTION
      "Path: atm.editConf.pvcTable.ipV6.dhcp.client.timers.infoRefresh

       Time in centi-second."
   ::= {er1646v2ATMFwCfgEntry 705311756}

er1646v2ATMFwCfgIpV6DhcpServerMode OBJECT-TYPE
   SYNTAX      INTEGER
               {
               disabled (0),
               enabled (1)
               }
   MAX-ACCESS  read-write
   STATUS      current
   DESCRIPTION
      "Path: atm.editConf.pvcTable.ipV6.dhcp.server.mode

       Possibilities:
               disabled   (0)
               enabled   (1)"
   ::= {er1646v2ATMFwCfgEntry 705315840}

er1646v2ATMFwCfgIpV6DhcpServerPreference OBJECT-TYPE
   SYNTAX      Integer32
   MAX-ACCESS  read-write
   STATUS      current
   DESCRIPTION
      "Path: atm.editConf.pvcTable.ipV6.dhcp.server.preference"
   ::= {er1646v2ATMFwCfgEntry 705316864}

er1646v2ATMFwCfgIpV6DhcpServerPool OBJECT-TYPE
   SYNTAX      DisplayString
   MAX-ACCESS  read-write
   STATUS      current
   DESCRIPTION
      "Path: atm.editConf.pvcTable.ipV6.dhcp.server.pool"
   ::= {er1646v2ATMFwCfgEntry 705317888}

er1646v2ATMFwCfgIpV6DhcpServerRapidCommit OBJECT-TYPE
   SYNTAX      INTEGER
               {
               disabled (0),
               enabled (1)
               }
   MAX-ACCESS  read-write
   STATUS      current
   DESCRIPTION
      "Path: atm.editConf.pvcTable.ipV6.dhcp.server.rapidCommit

       Possibilities:
               disabled   (0)
               enabled   (1)"
   ::= {er1646v2ATMFwCfgEntry 705318912}

er1646v2ATMFwCfgIpV6DhcpServerTimersInfoRefresh OBJECT-TYPE
   SYNTAX      TimeTicks
   MAX-ACCESS  read-write
   STATUS      current
   DESCRIPTION
      "Path: atm.editConf.pvcTable.ipV6.dhcp.server.timers.infoRefresh

       Time in centi-second."
   ::= {er1646v2ATMFwCfgEntry 705319940}

er1646v2ATMFwCfgIpV6DhcpRelayMode OBJECT-TYPE
   SYNTAX      INTEGER
               {
               disabled (0),
               enabled (1)
               }
   MAX-ACCESS  read-write
   STATUS      current
   DESCRIPTION
      "Path: atm.editConf.pvcTable.ipV6.dhcp.relay.mode

       Possibilities:
               disabled   (0)
               enabled   (1)"
   ::= {er1646v2ATMFwCfgEntry 705323040}

er1646v2ATMFwCfgIpV6SendRedirect OBJECT-TYPE
   SYNTAX      INTEGER
               {
               disabled (0),
               enabled (1)
               }
   MAX-ACCESS  read-write
   STATUS      current
   DESCRIPTION
      "Path: atm.editConf.pvcTable.ipV6.sendRedirect

       Possibilities:
               disabled   (0)
               enabled   (1)"
   ::= {er1646v2ATMFwCfgEntry 705101824}

er1646v2ATMFwCfgIpV6LinkMtu OBJECT-TYPE
   SYNTAX      Integer32
   MAX-ACCESS  read-write
   STATUS      current
   DESCRIPTION
      "Path: atm.editConf.pvcTable.ipV6.linkMtu"
   ::= {er1646v2ATMFwCfgEntry 705167360}

er1646v2ATMFwCfgIpV6InterfaceId OBJECT-TYPE
   SYNTAX      OCTET STRING
   MAX-ACCESS  read-write
   STATUS      current
   DESCRIPTION
      "Path: atm.editConf.pvcTable.ipV6.interfaceId"
   ::= {er1646v2ATMFwCfgEntry 705232896}

er1646v2ATMFwCfgIpV6MF OBJECT-TYPE
   SYNTAX      Integer32
   MAX-ACCESS  read-write
   STATUS      current
   DESCRIPTION
      "Path: atm.editConf.pvcTable.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2ATMFwCfgEntry 705757184}

er1646v2ATMFwCfgIpV6IcmpMessagesNoRoute OBJECT-TYPE
   SYNTAX      INTEGER
               {
               disabled (0),
               enabled (1)
               }
   MAX-ACCESS  read-write
   STATUS      current
   DESCRIPTION
      "Path: atm.editConf.pvcTable.ipV6.icmpMessages.noRoute

       Possibilities:
               disabled   (0)
               enabled   (1)"
   ::= {er1646v2ATMFwCfgEntry 705822976}

er1646v2ATMFwCfgIpV6IcmpMessagesBeyondScope OBJECT-TYPE
   SYNTAX      INTEGER
               {
               disabled (0),
               enabled (1)
               }
   MAX-ACCESS  read-write
   STATUS      current
   DESCRIPTION
      "Path: atm.editConf.pvcTable.ipV6.icmpMessages.beyondScope

       Possibilities:
               disabled   (0)
               enabled   (1)"
   ::= {er1646v2ATMFwCfgEntry 705823488}

er1646v2ATMFwCfgIpV6IcmpMessagesAddressUnreachable OBJECT-TYPE
   SYNTAX      INTEGER
               {
               disabled (0),
               enabled (1)
               }
   MAX-ACCESS  read-write
   STATUS      current
   DESCRIPTION
      "Path: atm.editConf.pvcTable.ipV6.icmpMessages.addressUnreachable

       Possibilities:
               disabled   (0)
               enabled   (1)"
   ::= {er1646v2ATMFwCfgEntry 705823744}

er1646v2ATMFwCfgIpV6IcmpMessagesPortUnreachable OBJECT-TYPE
   SYNTAX      INTEGER
               {
               disabled (0),
               enabled (1)
               }
   MAX-ACCESS  read-write
   STATUS      current
   DESCRIPTION
      "Path: atm.editConf.pvcTable.ipV6.icmpMessages.portUnreachable

       Possibilities:
               disabled   (0)
               enabled   (1)"
   ::= {er1646v2ATMFwCfgEntry 705824000}

er1646v2ATMFwCfgIpV6IcmpMessagesPacketTooBig OBJECT-TYPE
   SYNTAX      INTEGER
               {
               disabled (0),
               enabled (1)
               }
   MAX-ACCESS  read-write
   STATUS      current
   DESCRIPTION
      "Path: atm.editConf.pvcTable.ipV6.icmpMessages.packetTooBig

       Possibilities:
               disabled   (0)
               enabled   (1)"
   ::= {er1646v2ATMFwCfgEntry 705825280}

er1646v2ATMFwCfgIpV6IcmpMessagesHopLimitExceeded OBJECT-TYPE
   SYNTAX      INTEGER
               {
               disabled (0),
               enabled (1)
               }
   MAX-ACCESS  read-write
   STATUS      current
   DESCRIPTION
      "Path: atm.editConf.pvcTable.ipV6.icmpMessages.hopLimitExceeded

       Possibilities:
               disabled   (0)
               enabled   (1)"
   ::= {er1646v2ATMFwCfgEntry 705827840}

er1646v2ATMFwCfgIpV6IcmpMessagesFragTimeExceeded OBJECT-TYPE
   SYNTAX      INTEGER
               {
               disabled (0),
               enabled (1)
               }
   MAX-ACCESS  read-write
   STATUS      current
   DESCRIPTION
      "Path: atm.editConf.pvcTable.ipV6.icmpMessages.fragTimeExceeded

       Possibilities:
               disabled   (0)
               enabled   (1)"
   ::= {er1646v2ATMFwCfgEntry 705828096}

er1646v2ATMFwCfgIpV6IcmpMessagesHeaderFieldErr OBJECT-TYPE
   SYNTAX      INTEGER
               {
               disabled (0),
               enabled (1)
               }
   MAX-ACCESS  read-write
   STATUS      current
   DESCRIPTION
      "Path: atm.editConf.pvcTable.ipV6.icmpMessages.headerFieldErr

       Possibilities:
               disabled   (0)
               enabled   (1)"
   ::= {er1646v2ATMFwCfgEntry 705830400}

er1646v2ATMFwCfgIpV6IcmpMessagesOptionUnrecognized OBJECT-TYPE
   SYNTAX      INTEGER
               {
               disabled (0),
               enabled (1)
               }
   MAX-ACCESS  read-write
   STATUS      current
   DESCRIPTION
      "Path: atm.editConf.pvcTable.ipV6.icmpMessages.optionUnrecognized

       Possibilities:
               disabled   (0)
               enabled   (1)"
   ::= {er1646v2ATMFwCfgEntry 705830912}

er1646v2ATMFwCfgIpV6IcmpMessagesRedirect OBJECT-TYPE
   SYNTAX      INTEGER
               {
               disabled (0),
               enabled (1)
               }
   MAX-ACCESS  read-write
   STATUS      current
   DESCRIPTION
      "Path: atm.editConf.pvcTable.ipV6.icmpMessages.redirect

       Possibilities:
               disabled   (0)
               enabled   (1)"
   ::= {er1646v2ATMFwCfgEntry 705832960}

er1646v2ATMFwCfgBridgingAccList OBJECT-TYPE
   SYNTAX      DisplayString
   MAX-ACCESS  read-write
   STATUS      current
   DESCRIPTION
      "Path: atm.editConf.pvcTable.bridging.accessList"
   ::= {er1646v2ATMFwCfgEntry 453246976}

er1646v2ATMFwCfgBridgingInACL OBJECT-TYPE
   SYNTAX      DisplayString
   MAX-ACCESS  read-write
   STATUS      current
   DESCRIPTION
      "Path: atm.editConf.pvcTable.bridging.inAccessList"
   ::= {er1646v2ATMFwCfgEntry 456916992}

er1646v2ATMFwCfgBridgingTp OBJECT-TYPE
   SYNTAX      DisplayString
   MAX-ACCESS  read-write
   STATUS      current
   DESCRIPTION
      "Path: atm.editConf.pvcTable.bridging.trafficPolicy"
   ::= {er1646v2ATMFwCfgEntry 454295552}

er1646v2ATMFwCfgBridgingBrGrp OBJECT-TYPE
   SYNTAX      DisplayString
   MAX-ACCESS  read-write
   STATUS      current
   DESCRIPTION
      "Path: atm.editConf.pvcTable.bridging.bridgeGroup"
   ::= {er1646v2ATMFwCfgEntry 454819840}

er1646v2ATMFwCfgBridgingLimBC OBJECT-TYPE
   SYNTAX      INTEGER
               {
               disabled (0),
               enabled (1)
               }
   MAX-ACCESS  read-write
   STATUS      current
   DESCRIPTION
      "Path: atm.editConf.pvcTable.bridging.limitBroadcasts

       Possibilities:
               disabled   (0)
               enabled   (1)"
   ::= {er1646v2ATMFwCfgEntry 455081984}

er1646v2ATMFwCfgBridgingPrivateMode OBJECT-TYPE
   SYNTAX      INTEGER
               {
               disabled (0),
               enabled (1)
               }
   MAX-ACCESS  read-write
   STATUS      current
   DESCRIPTION
      "Path: atm.editConf.pvcTable.bridging.privateMode

       Possibilities:
               disabled   (0)
               enabled   (1)"
   ::= {er1646v2ATMFwCfgEntry 459538432}

er1646v2ATMFwCfgBridgingLearning OBJECT-TYPE
   SYNTAX      INTEGER
               {
               disabled (0),
               enabled (1)
               }
   MAX-ACCESS  read-write
   STATUS      current
   DESCRIPTION
      "Path: atm.editConf.pvcTable.bridging.learning

       Possibilities:
               disabled   (0)
               enabled   (1)"
   ::= {er1646v2ATMFwCfgEntry 456130560}

er1646v2ATMFwCfgBridgingMaxCacheSize OBJECT-TYPE
   SYNTAX      INTEGER
               {
               unlimited (0)
               }
   MAX-ACCESS  read-write
   STATUS      current
   DESCRIPTION
      "Path: atm.editConf.pvcTable.bridging.maxCacheSize

       Possibilities:
               unlimited   (0)"
   ::= {er1646v2ATMFwCfgEntry 456392704}

er1646v2ATMFwCfgBridgingRelearnDropOnRelearn OBJECT-TYPE
   SYNTAX      INTEGER
               {
               disabled (0),
               enabled (1)
               }
   MAX-ACCESS  read-write
   STATUS      current
   DESCRIPTION
      "Path: atm.editConf.pvcTable.bridging.relearn.dropOnRelearn

       Possibilities:
               disabled   (0)
               enabled   (1)"
   ::= {er1646v2ATMFwCfgEntry 456655872}

er1646v2ATMFwCfgBridgingRelearnShutdownThreshold OBJECT-TYPE
   SYNTAX      Integer32
   MAX-ACCESS  read-write
   STATUS      current
   DESCRIPTION
      "Path: atm.editConf.pvcTable.bridging.relearn.shutdownThreshold"
   ::= {er1646v2ATMFwCfgEntry 456656896}

er1646v2ATMFwCfgBridgingRelearnShutdownTime OBJECT-TYPE
   SYNTAX      TimeTicks
   MAX-ACCESS  read-write
   STATUS      current
   DESCRIPTION
      "Path: atm.editConf.pvcTable.bridging.relearn.shutdownTime

       Time in centi-second."
   ::= {er1646v2ATMFwCfgEntry 456657920}

er1646v2ATMFwCfgBridgingRelearnLoopDetection OBJECT-TYPE
   SYNTAX      INTEGER
               {
               disabled (0),
               passive (1),
               active (2)
               }
   MAX-ACCESS  read-write
   STATUS      current
   DESCRIPTION
      "Path: atm.editConf.pvcTable.bridging.relearn.loopDetection

       Possibilities:
               disabled   (0)
               passive   (1)
               active   (2)"
   ::= {er1646v2ATMFwCfgEntry 456658944}

er1646v2ATMFwCfgBridgingRelearnLoopDetectionInterval OBJECT-TYPE
   SYNTAX      TimeTicks
   MAX-ACCESS  read-write
   STATUS      current
   DESCRIPTION
      "Path: atm.editConf.pvcTable.bridging.relearn.loopDetectionInterval

       Time in centi-second."
   ::= {er1646v2ATMFwCfgEntry 456659968}

er1646v2ATMFwCfgBridgingVlanMemberShip OBJECT-TYPE
   SYNTAX      INTEGER
               {
               all (0),
               none (1),
               grouped (2)
               }
   MAX-ACCESS  read-write
   STATUS      current
   DESCRIPTION
      "Path: atm.editConf.pvcTable.bridging.vlanMemberShip

       Possibilities:
               all   (0)
               none   (1)
               grouped   (2)"
   ::= {er1646v2ATMFwCfgEntry 457965568}

er1646v2ATMFwCfgBridgingVlTUntaggedAction OBJECT-TYPE
   SYNTAX      INTEGER
               {
               discard (0),
               accept (1),
               tag (2)
               }
   MAX-ACCESS  read-write
   STATUS      current
   DESCRIPTION
      "Path: atm.editConf.pvcTable.bridging.vlanTagging.untagged.action

       Possibilities:
               discard   (0)
               accept   (1)
               tag   (2)"
   ::= {er1646v2ATMFwCfgEntry 459055104}

er1646v2ATMFwCfgBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.untagged.tagInfo.tpid

       Possibilities:
               dot1Q   (33024)
               dot1ad   (34984)
               0x9100   (37120)
               0x9200   (37376)
               0x9300   (37632)"
   ::= {er1646v2ATMFwCfgEntry 459059712}

er1646v2ATMFwCfgBridgingVlTUntaggedTagInfoVid OBJECT-TYPE
   SYNTAX      Integer32
   MAX-ACCESS  read-write
   STATUS      current
   DESCRIPTION
      "Path: atm.editConf.pvcTable.bridging.vlanTagging.untagged.tagInfo.vid"
   ::= {er1646v2ATMFwCfgEntry 459060224}

er1646v2ATMFwCfgBridgingVlTUnknownVlansAction OBJECT-TYPE
   SYNTAX      INTEGER
               {
               discard (0),
               accept (1),
               tag (2)
               }
   MAX-ACCESS  read-write
   STATUS      current
   DESCRIPTION
      "Path: atm.editConf.pvcTable.bridging.vlanTagging.unknownVlans.action

       Possibilities:
               discard   (0)
               accept   (1)
               tag   (2)"
   ::= {er1646v2ATMFwCfgEntry 459120640}

er1646v2ATMFwCfgBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.unknownVlans.tagInfo.tpid

       Possibilities:
               dot1Q   (33024)
               dot1ad   (34984)
               0x9100   (37120)
               0x9200   (37376)
               0x9300   (37632)"
   ::= {er1646v2ATMFwCfgEntry 459125248}

er1646v2ATMFwCfgBridgingVlTUnknownVlansTagInfoVid OBJECT-TYPE
   SYNTAX      Integer32
   MAX-ACCESS  read-write
   STATUS      current
   DESCRIPTION
      "Path: atm.editConf.pvcTable.bridging.vlanTagging.unknownVlans.tagInfo.vid"
   ::= {er1646v2ATMFwCfgEntry 459125760}

er1646v2ATMFwCfgBridgingDot1adType OBJECT-TYPE
   SYNTAX      INTEGER
               {
               slOPTg (0),
               cPort (4),
               sPort (1),
               nni (2)
               }
   MAX-ACCESS  read-write
   STATUS      current
   DESCRIPTION
      "Path: atm.editConf.pvcTable.bridging.dot1ad.type

       Possibilities:
               <OPT>   (0)
               cPort   (4)
               sPort   (1)
               nni   (2)"
   ::= {er1646v2ATMFwCfgEntry 460850176}

er1646v2ATMFwCfgBridgingPriority OBJECT-TYPE
   SYNTAX      Integer32
   MAX-ACCESS  read-write
   STATUS      current
   DESCRIPTION
      "Path: atm.editConf.pvcTable.bridging.priority"
   ::= {er1646v2ATMFwCfgEntry 453509120}

er1646v2ATMFwCfgBridgingPathCost OBJECT-TYPE
   SYNTAX      Integer32
   MAX-ACCESS  read-write
   STATUS      current
   DESCRIPTION
      "Path: atm.editConf.pvcTable.bridging.pathCost"
   ::= {er1646v2ATMFwCfgEntry 453771264}

er1646v2ATMFwCfgBridgingInternalPathCost OBJECT-TYPE
   SYNTAX      Integer32
   MAX-ACCESS  read-write
   STATUS      current
   DESCRIPTION
      "Path: atm.editConf.pvcTable.bridging.internalPathCost"
   ::= {er1646v2ATMFwCfgEntry 457703424}

er1646v2ATMFwCfgBridgingTCD OBJECT-TYPE
   SYNTAX      INTEGER
               {
               disabled (0),
               enabled (1)
               }
   MAX-ACCESS  read-write
   STATUS      current
   DESCRIPTION
      "Path: atm.editConf.pvcTable.bridging.topologyChangeDetection

       Possibilities:
               disabled   (0)
               enabled   (1)"
   ::= {er1646v2ATMFwCfgEntry 454033408}

er1646v2ATMFwCfgBridgingRestrictedRole OBJECT-TYPE
   SYNTAX      INTEGER
               {
               disabled (0),
               enabled (1)
               }
   MAX-ACCESS  read-write
   STATUS      current
   DESCRIPTION
      "Path: atm.editConf.pvcTable.bridging.restrictedRole

       Possibilities:
               disabled   (0)
               enabled   (1)"
   ::= {er1646v2ATMFwCfgEntry 458227712}

er1646v2ATMFwCfgBridgingAdminEdge OBJECT-TYPE
   SYNTAX      INTEGER
               {
               disabled (0),
               enabled (1)
               }
   MAX-ACCESS  read-write
   STATUS      current
   DESCRIPTION
      "Path: atm.editConf.pvcTable.bridging.adminEdge

       Possibilities:
               disabled   (0)
               enabled   (1)"
   ::= {er1646v2ATMFwCfgEntry 457179136}

er1646v2ATMFwCfgBridgingOamMacDeviceMac OBJECT-TYPE
   SYNTAX      DisplayString
   MAX-ACCESS  read-write
   STATUS      current
   DESCRIPTION
      "Path: atm.editConf.pvcTable.bridging.ethOam.macAddress.deviceMac"
   ::= {er1646v2ATMFwCfgEntry 458506496}

er1646v2ATMFwCfgBridgingOamMacUserMac OBJECT-TYPE
   SYNTAX      OCTET STRING
   MAX-ACCESS  read-write
   STATUS      current
   DESCRIPTION
      "Path: atm.editConf.pvcTable.bridging.ethOam.macAddress.userMac

       MAC address."
   ::= {er1646v2ATMFwCfgEntry 458506368}

er1646v2ATMFwCfgBridgingOamMacBridgeMac OBJECT-TYPE
   SYNTAX      DisplayString
   MAX-ACCESS  read-write
   STATUS      current
   DESCRIPTION
      "Path: atm.editConf.pvcTable.bridging.ethOam.macAddress.bridgeMac"
   ::= {er1646v2ATMFwCfgEntry 458506432}

er1646v2ATMFwCfgBridgingMgmtInline OBJECT-TYPE
   SYNTAX      INTEGER
               {
               disabled (0),
               enabled (1)
               }
   MAX-ACCESS  read-write
   STATUS      current
   DESCRIPTION
      "Path: atm.editConf.pvcTable.bridging.mgmtInline

       Possibilities:
               disabled   (0)
               enabled   (1)"
   ::= {er1646v2ATMFwCfgEntry 458752000}

er1646v2ATMFwCfgBridgingL2ptMode OBJECT-TYPE
   SYNTAX      INTEGER
               {
               disabled (0),
               enabled (1)
               }
   MAX-ACCESS  read-write
   STATUS      current
   DESCRIPTION
      "Path: atm.editConf.pvcTable.bridging.l2ProtTunnel.mode

       Possibilities:
               disabled   (0)
               enabled   (1)"
   ::= {er1646v2ATMFwCfgEntry 459292672}

er1646v2ATMFwCfgBridgingL2ptProtocols OBJECT-TYPE
   SYNTAX      Integer32
   MAX-ACCESS  read-write
   STATUS      current
   DESCRIPTION
      "Path: atm.editConf.pvcTable.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2ATMFwCfgEntry 459309056}

er1646v2ATMFwCfgBridgingL2ptDestMac OBJECT-TYPE
   SYNTAX      OCTET STRING
   MAX-ACCESS  read-write
   STATUS      current
   DESCRIPTION
      "Path: atm.editConf.pvcTable.bridging.l2ProtTunnel.destinationMac

       MAC address."
   ::= {er1646v2ATMFwCfgEntry 459325440}

er1646v2ATMFwCfgBridgingL2ptCos OBJECT-TYPE
   SYNTAX      INTEGER
               {
               unchanged (255)
               }
   MAX-ACCESS  read-write
   STATUS      current
   DESCRIPTION
      "Path: atm.editConf.pvcTable.bridging.l2ProtTunnel.cos

       Possibilities:
               unchanged   (255)"
   ::= {er1646v2ATMFwCfgEntry 459341824}

er1646v2ATMFwCfgBridgingL2ptDropThrStp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.stp

       unit name = packets/sec

       Possibilities:
               unlimited   (0)"
   ::= {er1646v2ATMFwCfgEntry 459358272}

er1646v2ATMFwCfgBridgingL2ptDropThrLldp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.lldp

       unit name = packets/sec

       Possibilities:
               unlimited   (0)"
   ::= {er1646v2ATMFwCfgEntry 459358336}

er1646v2ATMFwCfgBridgingL2ptDropThrOam OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.oam

       unit name = packets/sec

       Possibilities:
               unlimited   (0)"
   ::= {er1646v2ATMFwCfgEntry 459358400}

er1646v2ATMFwCfgBridgingL2ptDropThrCdp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.cdp

       unit name = packets/sec

       Possibilities:
               unlimited   (0)"
   ::= {er1646v2ATMFwCfgEntry 459358464}

er1646v2ATMFwCfgBridgingL2ptDropThrVtp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.vtp

       unit name = packets/sec

       Possibilities:
               unlimited   (0)"
   ::= {er1646v2ATMFwCfgEntry 459358528}

er1646v2ATMFwCfgBridgingL2ptDropThrLacp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.lacp

       unit name = packets/sec

       Possibilities:
               unlimited   (0)"
   ::= {er1646v2ATMFwCfgEntry 459358592}

er1646v2ATMFwCfgBridgingL2ptDropThrEfmOam OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.efmOam

       unit name = packets/sec

       Possibilities:
               unlimited   (0)"
   ::= {er1646v2ATMFwCfgEntry 459358656}

er1646v2ATMFwCfgBridgingL2ptDropThrPvst OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.pvst

       unit name = packets/sec

       Possibilities:
               unlimited   (0)"
   ::= {er1646v2ATMFwCfgEntry 459358720}

er1646v2ATMFwCfgBridgingL2ptDropThrMmrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.mmrp

       unit name = packets/sec

       Possibilities:
               unlimited   (0)"
   ::= {er1646v2ATMFwCfgEntry 459358784}

er1646v2ATMFwCfgBridgingL2ptDropThrMvrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.mvrp

       unit name = packets/sec

       Possibilities:
               unlimited   (0)"
   ::= {er1646v2ATMFwCfgEntry 459358848}

er1646v2ATMFwCfgBridgingL2ptDropThrGvrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.gvrp

       unit name = packets/sec

       Possibilities:
               unlimited   (0)"
   ::= {er1646v2ATMFwCfgEntry 459358912}

er1646v2ATMFwCfgBridgingL2ptDropThrGmrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.gmrp

       unit name = packets/sec

       Possibilities:
               unlimited   (0)"
   ::= {er1646v2ATMFwCfgEntry 459358976}

er1646v2ATMFwCfgBridgingL2ptDropThrDtp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.dtp

       unit name = packets/sec

       Possibilities:
               unlimited   (0)"
   ::= {er1646v2ATMFwCfgEntry 459359040}

er1646v2ATMFwCfgBridgingL2ptDropThrPagp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.pagp

       unit name = packets/sec

       Possibilities:
               unlimited   (0)"
   ::= {er1646v2ATMFwCfgEntry 459359104}

er1646v2ATMFwCfgBridgingL2ptDropThrUdld OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.udld

       unit name = packets/sec

       Possibilities:
               unlimited   (0)"
   ::= {er1646v2ATMFwCfgEntry 459359168}

er1646v2ATMFwCfgVirtEthernetVirtualEthernet OBJECT-TYPE
   SYNTAX      DisplayString
   MAX-ACCESS  read-write
   STATUS      current
   DESCRIPTION
      "Path: atm.editConf.pvcTable.virtEthernet.virtualEthernet"
   ::= {er1646v2ATMFwCfgEntry 151060480}

er1646v2ATMFwCfgAtmVpi OBJECT-TYPE
   SYNTAX      Integer32
   MAX-ACCESS  read-write
   STATUS      current
   DESCRIPTION
      "Path: atm.editConf.pvcTable.atm.vpi"
   ::= {er1646v2ATMFwCfgEntry 285278208}

er1646v2ATMFwCfgAtmVci OBJECT-TYPE
   SYNTAX      Integer32
   MAX-ACCESS  read-write
   STATUS      current
   DESCRIPTION
      "Path: atm.editConf.pvcTable.atm.vci"
   ::= {er1646v2ATMFwCfgEntry 285343744}

er1646v2ATMFwCfgAtmHighLayProt OBJECT-TYPE
   SYNTAX      INTEGER
               {
               rfc2684 (7),
               ppp (2),
               pppOverEthernet (11)
               }
   MAX-ACCESS  read-write
   STATUS      current
   DESCRIPTION
      "Path: atm.editConf.pvcTable.atm.higherLayerProtocol

       Possibilities:
               rfc2684   (7)
               ppp   (2)
               pppOverEthernet   (11)"
   ::= {er1646v2ATMFwCfgEntry 285409280}

er1646v2ATMFwCfgAtmMultiProt OBJECT-TYPE
   SYNTAX      INTEGER
               {
               llcEncapsulation (0),
               vcMultiplexing (1)
               }
   MAX-ACCESS  read-write
   STATUS      current
   DESCRIPTION
      "Path: atm.editConf.pvcTable.atm.multiProtocolMech

       Possibilities:
               llcEncapsulation   (0)
               vcMultiplexing   (1)"
   ::= {er1646v2ATMFwCfgEntry 285474816}

er1646v2ATMFwCfgAtmServCat OBJECT-TYPE
   SYNTAX      INTEGER
               {
               cbr (1),
               vbrmrt (2),
               vbrmnrt (3),
               ubr (4)
               }
   MAX-ACCESS  read-write
   STATUS      current
   DESCRIPTION
      "Path: atm.editConf.pvcTable.atm.serviceCategory

       Possibilities:
               cbr   (1)
               vbr-rt   (2)
               vbr-nrt   (3)
               ubr   (4)"
   ::= {er1646v2ATMFwCfgEntry 285999104}

er1646v2ATMFwCfgAtmPeakCellRate OBJECT-TYPE
   SYNTAX      INTEGER
               {
               auto (0)
               }
   UNITS       "bps"
   MAX-ACCESS  read-write
   STATUS      current
   DESCRIPTION
      "Path: atm.editConf.pvcTable.atm.peakCellRate

       unit name = bps

       Possibilities:
               auto   (0)"
   ::= {er1646v2ATMFwCfgEntry 285540352}

er1646v2ATMFwCfgAtmSustCellRate OBJECT-TYPE
   SYNTAX      INTEGER
               {
               auto (0)
               }
   UNITS       "bps"
   MAX-ACCESS  read-write
   STATUS      current
   DESCRIPTION
      "Path: atm.editConf.pvcTable.atm.sustCellRate

       unit name = bps

       Possibilities:
               auto   (0)"
   ::= {er1646v2ATMFwCfgEntry 285868032}

er1646v2ATMFwCfgAtmMaxBurstSize OBJECT-TYPE
   SYNTAX      Integer32
   UNITS       "cellTimes"
   MAX-ACCESS  read-write
   STATUS      current
   DESCRIPTION
      "Path: atm.editConf.pvcTable.atm.maxBurstSize

       unit name = cellTimes"
   ::= {er1646v2ATMFwCfgEntry 285933568}

er1646v2ATMFwCfgAtmInArpTimeOut OBJECT-TYPE
   SYNTAX      TimeTicks
   MAX-ACCESS  read-write
   STATUS      current
   DESCRIPTION
      "Path: atm.editConf.pvcTable.atm.inArpTimeOut

       Time in centi-second."
   ::= {er1646v2ATMFwCfgEntry 285605888}

er1646v2ATMFwCfgAtmF5LbOper OBJECT-TYPE
   SYNTAX      INTEGER
               {
               disabled (0),
               enabled (1)
               }
   MAX-ACCESS  read-write
   STATUS      current
   DESCRIPTION
      "Path: atm.editConf.pvcTable.atm.oamF5Loopback.operation

       Possibilities:
               disabled   (0)
               enabled   (1)"
   ::= {er1646v2ATMFwCfgEntry 285671680}

er1646v2ATMFwCfgAtmF5LbInterval OBJECT-TYPE
   SYNTAX      TimeTicks
   MAX-ACCESS  read-write
   STATUS      current
   DESCRIPTION
      "Path: atm.editConf.pvcTable.atm.oamF5Loopback.interval

       Time in centi-second."
   ::= {er1646v2ATMFwCfgEntry 285671936}

er1646v2ATMFwCfgAtmF5LbFailsPerm OBJECT-TYPE
   SYNTAX      Integer32
   MAX-ACCESS  read-write
   STATUS      current
   DESCRIPTION
      "Path: atm.editConf.pvcTable.atm.oamF5Loopback.failsPermitted"
   ::= {er1646v2ATMFwCfgEntry 285672448}

er1646v2ATMFwCfgAtmF5LbTar OBJECT-TYPE
   SYNTAX      INTEGER
               {
               endToEnd (0),
               segment (1),
               both (2)
               }
   MAX-ACCESS  read-write
   STATUS      current
   DESCRIPTION
      "Path: atm.editConf.pvcTable.atm.oamF5Loopback.target

       Possibilities:
               endToEnd   (0)
               segment   (1)
               both   (2)"
   ::= {er1646v2ATMFwCfgEntry 285672704}

er1646v2ATMFwCfgAtmF5ccDir OBJECT-TYPE
   SYNTAX      INTEGER
               {
               sink (1),
               source (2),
               both (3)
               }
   MAX-ACCESS  read-write
   STATUS      current
   DESCRIPTION
      "Path: atm.editConf.pvcTable.atm.oamF5CC.direction

       Possibilities:
               sink   (1)
               source   (2)
               both   (3)"
   ::= {er1646v2ATMFwCfgEntry 285737216}

er1646v2ATMFwCfgAtmF5ccTar OBJECT-TYPE
   SYNTAX      INTEGER
               {
               endToEnd (0),
               segment (1),
               both (2)
               }
   MAX-ACCESS  read-write
   STATUS      current
   DESCRIPTION
      "Path: atm.editConf.pvcTable.atm.oamF5CC.target

       Possibilities:
               endToEnd   (0)
               segment   (1)
               both   (2)"
   ::= {er1646v2ATMFwCfgEntry 285737472}

er1646v2ATMFwCfgAtmF5ccTxMode OBJECT-TYPE
   SYNTAX      INTEGER
               {
               continuously (0),
               onIdle (1)
               }
   MAX-ACCESS  read-write
   STATUS      current
   DESCRIPTION
      "Path: atm.editConf.pvcTable.atm.oamF5CC.tx.mode

       Possibilities:
               continuously   (0)
               onIdle   (1)"
   ::= {er1646v2ATMFwCfgEntry 285737729}

er1646v2ATMFwCfgAtmF5ccTxTxPer OBJECT-TYPE
   SYNTAX      TimeTicks
   MAX-ACCESS  read-write
   STATUS      current
   DESCRIPTION
      "Path: atm.editConf.pvcTable.atm.oamF5CC.tx.interval

       Time in centi-second."
   ::= {er1646v2ATMFwCfgEntry 285737730}

er1646v2ATMFwCfgAtmF5ccRxRcvTim OBJECT-TYPE
   SYNTAX      TimeTicks
   MAX-ACCESS  read-write
   STATUS      current
   DESCRIPTION
      "Path: atm.editConf.pvcTable.atm.oamF5CC.rx.timeOut

       Time in centi-second."
   ::= {er1646v2ATMFwCfgEntry 285738497}

er1646v2ATMFwCfgAtmF5ccActProc OBJECT-TYPE
   SYNTAX      INTEGER
               {
               passive (0),
               activated (1),
               deactivated (2),
               initActivation (3)
               }
   MAX-ACCESS  read-write
   STATUS      current
   DESCRIPTION
      "Path: atm.editConf.pvcTable.atm.oamF5CC.actDeact.initProcedure

       Possibilities:
               passive   (0)
               activated   (1)
               deactivated   (2)
               initActivation   (3)"
   ::= {er1646v2ATMFwCfgEntry 285737985}

er1646v2ATMFwCfgAtmF5ccActTim OBJECT-TYPE
   SYNTAX      TimeTicks
   MAX-ACCESS  read-write
   STATUS      current
   DESCRIPTION
      "Path: atm.editConf.pvcTable.atm.oamF5CC.actDeact.retryInterval

       Time in centi-second."
   ::= {er1646v2ATMFwCfgEntry 285737986}

er1646v2ATMFwCfgAtmF5ccActCnt OBJECT-TYPE
   SYNTAX      Integer32
   MAX-ACCESS  read-write
   STATUS      current
   DESCRIPTION
      "Path: atm.editConf.pvcTable.atm.oamF5CC.actDeact.retryCount"
   ::= {er1646v2ATMFwCfgEntry 285737987}

er1646v2ATMFwCfgAtmF5pmDir OBJECT-TYPE
   SYNTAX      INTEGER
               {
               sink (1),
               source (2),
               both (3)
               }
   MAX-ACCESS  read-write
   STATUS      current
   DESCRIPTION
      "Path: atm.editConf.pvcTable.atm.oamF5PM.direction

       Possibilities:
               sink   (1)
               source   (2)
               both   (3)"
   ::= {er1646v2ATMFwCfgEntry 285802752}

er1646v2ATMFwCfgAtmF5pmTar OBJECT-TYPE
   SYNTAX      INTEGER
               {
               endToEnd (0),
               segment (1)
               }
   MAX-ACCESS  read-write
   STATUS      current
   DESCRIPTION
      "Path: atm.editConf.pvcTable.atm.oamF5PM.target

       Possibilities:
               endToEnd   (0)
               segment   (1)"
   ::= {er1646v2ATMFwCfgEntry 285803008}

er1646v2ATMFwCfgAtmF5pmType OBJECT-TYPE
   SYNTAX      INTEGER
               {
               fpm (0),
               fpmWithBr (1)
               }
   MAX-ACCESS  read-write
   STATUS      current
   DESCRIPTION
      "Path: atm.editConf.pvcTable.atm.oamF5PM.type

       Possibilities:
               fpm   (0)
               fpmWithBr   (1)"
   ::= {er1646v2ATMFwCfgEntry 285803264}

er1646v2ATMFwCfgAtmF5pmPolicy OBJECT-TYPE
   SYNTAX      INTEGER
               {
               inband (0),
               outband (1)
               }
   MAX-ACCESS  read-write
   STATUS      current
   DESCRIPTION
      "Path: atm.editConf.pvcTable.atm.oamF5PM.policy

       Possibilities:
               inband   (0)
               outband   (1)"
   ::= {er1646v2ATMFwCfgEntry 285803520}

er1646v2ATMFwCfgAtmF5pmBsizeamb OBJECT-TYPE
   SYNTAX      INTEGER
               {
               s128 (0),
               s256 (1),
               s512 (2),
               s1024 (3),
               s2048 (4),
               s4096 (5),
               s8192 (6),
               s16384 (7),
               s32768 (8)
               }
   MAX-ACCESS  read-write
   STATUS      current
   DESCRIPTION
      "Path: atm.editConf.pvcTable.atm.oamF5PM.blockSizeAB

       Possibilities:
               128   (0)
               256   (1)
               512   (2)
               1024   (3)
               2048   (4)
               4096   (5)
               8192   (6)
               16384   (7)
               32768   (8)"
   ::= {er1646v2ATMFwCfgEntry 285803776}

er1646v2ATMFwCfgAtmF5pmBsizebma OBJECT-TYPE
   SYNTAX      INTEGER
               {
               s128 (0),
               s256 (1),
               s512 (2),
               s1024 (3),
               s2048 (4),
               s4096 (5),
               s8192 (6),
               s16384 (7),
               s32768 (8)
               }
   MAX-ACCESS  read-write
   STATUS      current
   DESCRIPTION
      "Path: atm.editConf.pvcTable.atm.oamF5PM.blockSizeBA

       Possibilities:
               128   (0)
               256   (1)
               512   (2)
               1024   (3)
               2048   (4)
               4096   (5)
               8192   (6)
               16384   (7)
               32768   (8)"
   ::= {er1646v2ATMFwCfgEntry 285804032}

er1646v2ATMFwCfgAtmF5pmActProc OBJECT-TYPE
   SYNTAX      INTEGER
               {
               passive (0),
               activated (1),
               deactivated (2),
               initActivation (3)
               }
   MAX-ACCESS  read-write
   STATUS      current
   DESCRIPTION
      "Path: atm.editConf.pvcTable.atm.oamF5PM.actDeact.initProcedure

       Possibilities:
               passive   (0)
               activated   (1)
               deactivated   (2)
               initActivation   (3)"
   ::= {er1646v2ATMFwCfgEntry 285804289}

er1646v2ATMFwCfgAtmF5pmActTim OBJECT-TYPE
   SYNTAX      TimeTicks
   MAX-ACCESS  read-write
   STATUS      current
   DESCRIPTION
      "Path: atm.editConf.pvcTable.atm.oamF5PM.actDeact.retryInterval

       Time in centi-second."
   ::= {er1646v2ATMFwCfgEntry 285804290}

er1646v2ATMFwCfgAtmF5pmActCnt OBJECT-TYPE
   SYNTAX      Integer32
   MAX-ACCESS  read-write
   STATUS      current
   DESCRIPTION
      "Path: atm.editConf.pvcTable.atm.oamF5PM.actDeact.retryCount"
   ::= {er1646v2ATMFwCfgEntry 285804291}

er1646v2ATMFwCfgAtmCpt OBJECT-TYPE
   SYNTAX      INTEGER
               {
               no (0),
               yes (1)
               }
   MAX-ACCESS  read-write
   STATUS      current
   DESCRIPTION
      "Path: atm.editConf.pvcTable.atm.segmentEndPoint

       Possibilities:
               no   (0)
               yes   (1)"
   ::= {er1646v2ATMFwCfgEntry 286195712}

er1646v2ATMFwCfgPppLnkMOperation OBJECT-TYPE
   SYNTAX      INTEGER
               {
               disabled (0),
               enabled (1)
               }
   MAX-ACCESS  read-write
   STATUS      current
   DESCRIPTION
      "Path: atm.editConf.pvcTable.ppp.linkMonitoring.operation

       Possibilities:
               disabled   (0)
               enabled   (1)"
   ::= {er1646v2ATMFwCfgEntry 201392384}

er1646v2ATMFwCfgPppLnkMInterval OBJECT-TYPE
   SYNTAX      TimeTicks
   MAX-ACCESS  read-write
   STATUS      current
   DESCRIPTION
      "Path: atm.editConf.pvcTable.ppp.linkMonitoring.interval

       Time in centi-second."
   ::= {er1646v2ATMFwCfgEntry 201392640}

er1646v2ATMFwCfgPppLnkMRepTimeOut OBJECT-TYPE
   SYNTAX      TimeTicks
   MAX-ACCESS  read-write
   STATUS      current
   DESCRIPTION
      "Path: atm.editConf.pvcTable.ppp.linkMonitoring.replyTimeOut

       Time in centi-second."
   ::= {er1646v2ATMFwCfgEntry 201392896}

er1646v2ATMFwCfgPppLnkMFailsPrmt OBJECT-TYPE
   SYNTAX      Integer32
   MAX-ACCESS  read-write
   STATUS      current
   DESCRIPTION
      "Path: atm.editConf.pvcTable.ppp.linkMonitoring.failsPermitted"
   ::= {er1646v2ATMFwCfgEntry 201393152}

er1646v2ATMFwCfgPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: atm.editConf.pvcTable.ppp.authentication

       Possibilities:
               disabled   (0)
               chap   (1)
               pap   (2)
               chapOrPap   (3)
               msChap   (4)
               msChapV2   (5)"
   ::= {er1646v2ATMFwCfgEntry 201457664}

er1646v2ATMFwCfgPppAuthenPeriod OBJECT-TYPE
   SYNTAX      TimeTicks
   MAX-ACCESS  read-write
   STATUS      current
   DESCRIPTION
      "Path: atm.editConf.pvcTable.ppp.authenPeriod

       Time in centi-second."
   ::= {er1646v2ATMFwCfgEntry 201523200}

er1646v2ATMFwCfgPppCompression OBJECT-TYPE
   SYNTAX      INTEGER
               {
               disabled (0),
               predictor1 (1)
               }
   MAX-ACCESS  read-write
   STATUS      current
   DESCRIPTION
      "Path: atm.editConf.pvcTable.ppp.compression

       Possibilities:
               disabled   (0)
               predictor1   (1)"
   ::= {er1646v2ATMFwCfgEntry 201588736}

er1646v2ATMFwCfgPppSessionName OBJECT-TYPE
   SYNTAX      DisplayString
   MAX-ACCESS  read-write
   STATUS      current
   DESCRIPTION
      "Path: atm.editConf.pvcTable.ppp.sessionName"
   ::= {er1646v2ATMFwCfgEntry 201654272}

er1646v2ATMFwCfgPppSessionSecret OBJECT-TYPE
   SYNTAX      DisplayString
   MAX-ACCESS  read-write
   STATUS      current
   DESCRIPTION
      "Path: atm.editConf.pvcTable.ppp.sessionSecret"
   ::= {er1646v2ATMFwCfgEntry 201719808}

er1646v2ATMFwCfgPppEncModeSessionSecret OBJECT-TYPE
   SYNTAX      INTEGER
               {
               none (1),
               encrypt (2),
               encType1 (3),
               invalid (128)
               }
   MAX-ACCESS  read-write
   STATUS      current
   DESCRIPTION
      "Path: atm.editConf.pvcTable.ppp.encModeSessionSecret

       Possibilities:
               none   (1)
               encrypt   (2)
               encType1   (3)
               invalid   (128)"
   ::= {er1646v2ATMFwCfgEntry 201850880}

er1646v2ATMFwCfgPppEncSessionSecret OBJECT-TYPE
   SYNTAX      DisplayString
   MAX-ACCESS  read-write
   STATUS      current
   DESCRIPTION
      "Path: atm.editConf.pvcTable.ppp.encSessionSecret"
   ::= {er1646v2ATMFwCfgEntry 201916416}

er1646v2ATMFwCfgPppServiceName OBJECT-TYPE
   SYNTAX      DisplayString
   MAX-ACCESS  read-write
   STATUS      current
   DESCRIPTION
      "Path: atm.editConf.pvcTable.ppp.serviceName"
   ::= {er1646v2ATMFwCfgEntry 201785344}

er1646v2ATMFwCfgFrComLmiMode OBJECT-TYPE
   SYNTAX      INTEGER
               {
               noLmi (3),
               user (2),
               network (1),
               nni (4),
               auto (0)
               }
   MAX-ACCESS  read-write
   STATUS      current
   DESCRIPTION
      "Path: atm.editConf.pvcTable.frameRelay.common.lmi.mode

       Possibilities:
               noLmi   (3)
               user   (2)
               network   (1)
               nni   (4)
               auto   (0)"
   ::= {er1646v2ATMFwCfgEntry 688918560}

er1646v2ATMFwCfgFrComLmiType OBJECT-TYPE
   SYNTAX      INTEGER
               {
               lmiRev1 (1),
               ansiT1m617md (2),
               q933mAnnexmA (3),
               frf1m2 (4)
               }
   MAX-ACCESS  read-write
   STATUS      current
   DESCRIPTION
      "Path: atm.editConf.pvcTable.frameRelay.common.lmi.type

       Possibilities:
               lmiRev1   (1)
               ansiT1-617-d   (2)
               q933-Annex-A   (3)
               frf1-2   (4)"
   ::= {er1646v2ATMFwCfgEntry 688918544}

er1646v2ATMFwCfgFrComLmiPollInt OBJECT-TYPE
   SYNTAX      TimeTicks
   MAX-ACCESS  read-write
   STATUS      current
   DESCRIPTION
      "Path: atm.editConf.pvcTable.frameRelay.common.lmi.pollingInterval

       Time in centi-second."
   ::= {er1646v2ATMFwCfgEntry 688918576}

er1646v2ATMFwCfgFrComLmiErrThres OBJECT-TYPE
   SYNTAX      Integer32
   MAX-ACCESS  read-write
   STATUS      current
   DESCRIPTION
      "Path: atm.editConf.pvcTable.frameRelay.common.lmi.errorThreshold"
   ::= {er1646v2ATMFwCfgEntry 688918592}

er1646v2ATMFwCfgFrComLmiMonEvt OBJECT-TYPE
   SYNTAX      Integer32
   MAX-ACCESS  read-write
   STATUS      current
   DESCRIPTION
      "Path: atm.editConf.pvcTable.frameRelay.common.lmi.monitoredEvents"
   ::= {er1646v2ATMFwCfgEntry 688918608}

er1646v2ATMFwCfgFrComLmiExpPollInt OBJECT-TYPE
   SYNTAX      TimeTicks
   MAX-ACCESS  read-write
   STATUS      current
   DESCRIPTION
      "Path: atm.editConf.pvcTable.frameRelay.common.lmi.expectedPollInterval

       Time in centi-second."
   ::= {er1646v2ATMFwCfgEntry 688918624}

er1646v2ATMFwCfgFrComLmiFullEnqInt OBJECT-TYPE
   SYNTAX      Integer32
   MAX-ACCESS  read-write
   STATUS      current
   DESCRIPTION
      "Path: atm.editConf.pvcTable.frameRelay.common.lmi.fullEnquiryInterval"
   ::= {er1646v2ATMFwCfgEntry 688918640}

er1646v2ATMFwCfgFrComFragIMode OBJECT-TYPE
   SYNTAX      INTEGER
               {
               disabled (0),
               enabled (1)
               }
   MAX-ACCESS  read-write
   STATUS      current
   DESCRIPTION
      "Path: atm.editConf.pvcTable.frameRelay.common.fragmentation.interfaceFormat

       Possibilities:
               disabled   (0)
               enabled   (1)"
   ::= {er1646v2ATMFwCfgEntry 688922640}

er1646v2ATMFwCfgFrComMLD OBJECT-TYPE
   SYNTAX      INTEGER
               {
               routing (0),
               bridging (1),
               routingAndBridging (2)
               }
   MAX-ACCESS  read-write
   STATUS      current
   DESCRIPTION
      "Path: atm.editConf.pvcTable.frameRelay.common.modeLearnedDlci

       Possibilities:
               routing   (0)
               bridging   (1)
               routingAndBridging   (2)"
   ::= {er1646v2ATMFwCfgEntry 688926720}

er1646v2ATMFwCfgInbBwCir OBJECT-TYPE
   SYNTAX      Integer32
   MAX-ACCESS  read-write
   STATUS      current
   DESCRIPTION
      "Path: atm.editConf.pvcTable.inboundBandwidth.cir"
   ::= {er1646v2ATMFwCfgEntry 117506048}

er1646v2ATMFwCfgInbBwTc OBJECT-TYPE
   SYNTAX      INTEGER
               {
               auto (0)
               }
   MAX-ACCESS  read-write
   STATUS      current
   DESCRIPTION
      "Path: atm.editConf.pvcTable.inboundBandwidth.tc

       Possibilities:
               auto   (0)"
   ::= {er1646v2ATMFwCfgEntry 117833728}

er1646v2ATMFwCfgInbBwCorrType OBJECT-TYPE
   SYNTAX      INTEGER
               {
               noCorrection (0),
               predefined (1),
               manual (2)
               }
   MAX-ACCESS  read-write
   STATUS      current
   DESCRIPTION
      "Path: atm.editConf.pvcTable.inboundBandwidth.correction.type

       Possibilities:
               noCorrection   (0)
               predefined   (1)
               manual   (2)"
   ::= {er1646v2ATMFwCfgEntry 117579776}

er1646v2ATMFwCfgInbBwCorrPredefEncapsFrameRelay OBJECT-TYPE
   SYNTAX      DisplayString
   MAX-ACCESS  read-write
   STATUS      current
   DESCRIPTION
      "Path: atm.editConf.pvcTable.inboundBandwidth.correction.predefined.encapsulation.frameRelay"
   ::= {er1646v2ATMFwCfgEntry 117589056}

er1646v2ATMFwCfgInbBwCorrPredefEncapsPpp OBJECT-TYPE
   SYNTAX      DisplayString
   MAX-ACCESS  read-write
   STATUS      current
   DESCRIPTION
      "Path: atm.editConf.pvcTable.inboundBandwidth.correction.predefined.encapsulation.ppp"
   ::= {er1646v2ATMFwCfgEntry 117589120}

er1646v2ATMFwCfgInbBwCorrPredefEncapsAtmHl OBJECT-TYPE
   SYNTAX      INTEGER
               {
               rfc2684 (0),
               ppp (1),
               pppOverEthernet (2)
               }
   MAX-ACCESS  read-write
   STATUS      current
   DESCRIPTION
      "Path: atm.editConf.pvcTable.inboundBandwidth.correction.predefined.encapsulation.atm.higherLayer

       Possibilities:
               rfc2684   (0)
               ppp   (1)
               pppOverEthernet   (2)"
   ::= {er1646v2ATMFwCfgEntry 117589192}

er1646v2ATMFwCfgInbBwCorrPredefEncapsAtmMp OBJECT-TYPE
   SYNTAX      INTEGER
               {
               llcEncapsulation (0),
               vcMultiplexing (1)
               }
   MAX-ACCESS  read-write
   STATUS      current
   DESCRIPTION
      "Path: atm.editConf.pvcTable.inboundBandwidth.correction.predefined.encapsulation.atm.multiProtocol

       Possibilities:
               llcEncapsulation   (0)
               vcMultiplexing   (1)"
   ::= {er1646v2ATMFwCfgEntry 117589200}

er1646v2ATMFwCfgInbBwCorrPredefEncapsHdlc OBJECT-TYPE
   SYNTAX      DisplayString
   MAX-ACCESS  read-write
   STATUS      current
   DESCRIPTION
      "Path: atm.editConf.pvcTable.inboundBandwidth.correction.predefined.encapsulation.hdlc"
   ::= {er1646v2ATMFwCfgEntry 117589248}

er1646v2ATMFwCfgInbBwCorrPredefEncapsEfmFs OBJECT-TYPE
   SYNTAX      Integer32
   MAX-ACCESS  read-write
   STATUS      current
   DESCRIPTION
      "Path: atm.editConf.pvcTable.inboundBandwidth.correction.predefined.encapsulation.efm.fragmentSize"
   ::= {er1646v2ATMFwCfgEntry 117589320}

er1646v2ATMFwCfgInbBwCorrPredefEncapsEfmIb OBJECT-TYPE
   SYNTAX      Integer32
   MAX-ACCESS  read-write
   STATUS      current
   DESCRIPTION
      "Path: atm.editConf.pvcTable.inboundBandwidth.correction.predefined.encapsulation.efm.idleBytes"
   ::= {er1646v2ATMFwCfgEntry 117589328}

er1646v2ATMFwCfgInbBwCorrPredefMode OBJECT-TYPE
   SYNTAX      INTEGER
               {
               routing (0),
               bridging (1)
               }
   MAX-ACCESS  read-write
   STATUS      current
   DESCRIPTION
      "Path: atm.editConf.pvcTable.inboundBandwidth.correction.predefined.mode

       Possibilities:
               routing   (0)
               bridging   (1)"
   ::= {er1646v2ATMFwCfgEntry 117590016}

er1646v2ATMFwCfgInbBwCorrManualOverhead OBJECT-TYPE
   SYNTAX      Integer32
   MAX-ACCESS  read-write
   STATUS      current
   DESCRIPTION
      "Path: atm.editConf.pvcTable.inboundBandwidth.correction.manual.overhead"
   ::= {er1646v2ATMFwCfgEntry 117596192}

er1646v2ATMFwCfgInbBwCorrManualFrameData OBJECT-TYPE
   SYNTAX      Counter32
   MAX-ACCESS  read-write
   STATUS      current
   DESCRIPTION
      "Path: atm.editConf.pvcTable.inboundBandwidth.correction.manual.frameData

       32 bit unsigned wrappable counter."
   ::= {er1646v2ATMFwCfgEntry 117596224}

er1646v2ATMFwCfgInbBwCorrManualFrameHeader OBJECT-TYPE
   SYNTAX      Counter32
   MAX-ACCESS  read-write
   STATUS      current
   DESCRIPTION
      "Path: atm.editConf.pvcTable.inboundBandwidth.correction.manual.frameHeader

       32 bit unsigned wrappable counter."
   ::= {er1646v2ATMFwCfgEntry 117596256}

er1646v2ATMFwCfgInbBwMaxFifoQLen OBJECT-TYPE
   SYNTAX      Integer32
   MAX-ACCESS  read-write
   STATUS      current
   DESCRIPTION
      "Path: atm.editConf.pvcTable.inboundBandwidth.maxFifoQLen"
   ::= {er1646v2ATMFwCfgEntry 117637120}

er1646v2ATMFwCfgInbBwPriorityPolicy OBJECT-TYPE
   SYNTAX      DisplayString
   MAX-ACCESS  read-write
   STATUS      current
   DESCRIPTION
      "Path: atm.editConf.pvcTable.inboundBandwidth.priorityPolicy"
   ::= {er1646v2ATMFwCfgEntry 117702656}

er1646v2ATMFwCfgIpH OBJECT-TYPE
   SYNTAX      SEQUENCE OF Er1646v2ATMFwCfgIpHEntry
   MAX-ACCESS  not-accessible
   STATUS      current
   DESCRIPTION
      ""
   ::= {er1646v2ATMFwCfg 51314688}

er1646v2ATMFwCfgIpHEntry OBJECT-TYPE
   SYNTAX      Er1646v2ATMFwCfgIpHEntry
   MAX-ACCESS  not-accessible
   STATUS      current
   DESCRIPTION
      ""
   INDEX      { er1646v2ATMFwCfgIpHGlobalIx,
                er1646v2ATMFwCfgTableIx,
                er1646v2ATMFwCfgIpHTableIx }
   ::= {er1646v2ATMFwCfgIpH 1}

Er1646v2ATMFwCfgIpHEntry ::=
   SEQUENCE
      {
      er1646v2ATMFwCfgIpHActions
         VariableLengthTableActions,
      er1646v2ATMFwCfgIpHGlobalIx
         GlobalIndex,
      er1646v2ATMFwCfgIpHTableIx
         TableIndex,
      er1646v2ATMFwCfgIpHAddress
         IpAddress,
      er1646v2ATMFwCfgIpHDhcpRelayOptionSubscriberId
         DisplayString
      }

er1646v2ATMFwCfgIpHActions OBJECT-TYPE
   SYNTAX      VariableLengthTableActions
   MAX-ACCESS  read-write
   STATUS      current
   DESCRIPTION
      "By way of this field, some manipulations
       on this table may be performed."
   ::= {er1646v2ATMFwCfgIpHEntry 2}

er1646v2ATMFwCfgIpHGlobalIx OBJECT-TYPE
   SYNTAX      GlobalIndex
   MAX-ACCESS  not-accessible
   STATUS      current
   DESCRIPTION
      "The value of the tlsCntTreeGlobalIndex of the MANAGED OBJECT."
   ::= {er1646v2ATMFwCfgIpHEntry 10}

er1646v2ATMFwCfgIpHTableIx OBJECT-TYPE
   SYNTAX      TableIndex
   MAX-ACCESS  not-accessible
   STATUS      current
   DESCRIPTION
      ""
   ::= {er1646v2ATMFwCfgIpHEntry 11}

er1646v2ATMFwCfgIpHAddress OBJECT-TYPE
   SYNTAX      IpAddress
   MAX-ACCESS  read-write
   STATUS      current
   DESCRIPTION
      "Path: atm.editConf.pvcTable.ip.helpers.address"
   ::= {er1646v2ATMFwCfgIpHEntry 16777216}

er1646v2ATMFwCfgIpHDhcpRelayOptionSubscriberId OBJECT-TYPE
   SYNTAX      DisplayString
   MAX-ACCESS  read-write
   STATUS      current
   DESCRIPTION
      "Path: atm.editConf.pvcTable.ip.helpers.dhcpRelayOption.subscriberId"
   ::= {er1646v2ATMFwCfgIpHEntry 33947648}

er1646v2ATMFwCfgIpV6Addresses OBJECT-TYPE
   SYNTAX      SEQUENCE OF Er1646v2ATMFwCfgIpV6AddressesEntry
   MAX-ACCESS  not-accessible
   STATUS      current
   DESCRIPTION
      ""
   ::= {er1646v2ATMFwCfg 704839680}

er1646v2ATMFwCfgIpV6AddressesEntry OBJECT-TYPE
   SYNTAX      Er1646v2ATMFwCfgIpV6AddressesEntry
   MAX-ACCESS  not-accessible
   STATUS      current
   DESCRIPTION
      ""
   INDEX      { er1646v2ATMFwCfgIpV6AddressesGlobalIx,
                er1646v2ATMFwCfgTableIx,
                er1646v2ATMFwCfgIpV6AddressesTableIx }
   ::= {er1646v2ATMFwCfgIpV6Addresses 1}

Er1646v2ATMFwCfgIpV6AddressesEntry ::=
   SEQUENCE
      {
      er1646v2ATMFwCfgIpV6AddressesActions
         VariableLengthTableActions,
      er1646v2ATMFwCfgIpV6AddressesGlobalIx
         GlobalIndex,
      er1646v2ATMFwCfgIpV6AddressesTableIx
         TableIndex,
      er1646v2ATMFwCfgIpV6AddressesType
         INTEGER,
      er1646v2ATMFwCfgIpV6AddressesAddress
         Ipv6Address,
      er1646v2ATMFwCfgIpV6AddressesPrefixLength
         Integer32,
      er1646v2ATMFwCfgIpV6AddressesGeneralPrefix
         DisplayString,
      er1646v2ATMFwCfgIpV6AddressesRaSend
         INTEGER,
      er1646v2ATMFwCfgIpV6AddressesRaOnLinkFlag
         INTEGER,
      er1646v2ATMFwCfgIpV6AddressesRaAutoFlag
         INTEGER,
      er1646v2ATMFwCfgIpV6AddressesRaValidLifeTime
         TimeTicks,
      er1646v2ATMFwCfgIpV6AddressesRaValidLTMode
         INTEGER,
      er1646v2ATMFwCfgIpV6AddressesRaPrefLifeTime
         TimeTicks,
      er1646v2ATMFwCfgIpV6AddressesRaPrefLTMode
         INTEGER
      }

er1646v2ATMFwCfgIpV6AddressesActions OBJECT-TYPE
   SYNTAX      VariableLengthTableActions
   MAX-ACCESS  read-write
   STATUS      current
   DESCRIPTION
      "By way of this field, some manipulations
       on this table may be performed."
   ::= {er1646v2ATMFwCfgIpV6AddressesEntry 2}

er1646v2ATMFwCfgIpV6AddressesGlobalIx OBJECT-TYPE
   SYNTAX      GlobalIndex
   MAX-ACCESS  not-accessible
   STATUS      current
   DESCRIPTION
      "The value of the tlsCntTreeGlobalIndex of the MANAGED OBJECT."
   ::= {er1646v2ATMFwCfgIpV6AddressesEntry 10}

er1646v2ATMFwCfgIpV6AddressesTableIx OBJECT-TYPE
   SYNTAX      TableIndex
   MAX-ACCESS  not-accessible
   STATUS      current
   DESCRIPTION
      ""
   ::= {er1646v2ATMFwCfgIpV6AddressesEntry 11}

er1646v2ATMFwCfgIpV6AddressesType OBJECT-TYPE
   SYNTAX      INTEGER
               {
               unicast (0),
               eui64 (1),
               anycast (2),
               linkLocal (3),
               generalPrefix (4)
               }
   MAX-ACCESS  read-write
   STATUS      current
   DESCRIPTION
      "Path: atm.editConf.pvcTable.ipV6.addresses.type

       Possibilities:
               unicast   (0)
               eui64   (1)
               anycast   (2)
               linkLocal   (3)
               generalPrefix   (4)"
   ::= {er1646v2ATMFwCfgIpV6AddressesEntry 50331648}

er1646v2ATMFwCfgIpV6AddressesAddress OBJECT-TYPE
   SYNTAX      Ipv6Address
   MAX-ACCESS  read-write
   STATUS      current
   DESCRIPTION
      "Path: atm.editConf.pvcTable.ipV6.addresses.address

       ipv6 address"
   ::= {er1646v2ATMFwCfgIpV6AddressesEntry 16777216}

er1646v2ATMFwCfgIpV6AddressesPrefixLength OBJECT-TYPE
   SYNTAX      Integer32
   MAX-ACCESS  read-write
   STATUS      current
   DESCRIPTION
      "Path: atm.editConf.pvcTable.ipV6.addresses.prefixLength"
   ::= {er1646v2ATMFwCfgIpV6AddressesEntry 33554432}

er1646v2ATMFwCfgIpV6AddressesGeneralPrefix OBJECT-TYPE
   SYNTAX      DisplayString
   MAX-ACCESS  read-write
   STATUS      current
   DESCRIPTION
      "Path: atm.editConf.pvcTable.ipV6.addresses.generalPrefix"
   ::= {er1646v2ATMFwCfgIpV6AddressesEntry 83886080}

er1646v2ATMFwCfgIpV6AddressesRaSend OBJECT-TYPE
   SYNTAX      INTEGER
               {
               disabled (0),
               enabled (1)
               }
   MAX-ACCESS  read-write
   STATUS      current
   DESCRIPTION
      "Path: atm.editConf.pvcTable.ipV6.addresses.ra.send

       Possibilities:
               disabled   (0)
               enabled   (1)"
   ::= {er1646v2ATMFwCfgIpV6AddressesEntry 67174400}

er1646v2ATMFwCfgIpV6AddressesRaOnLinkFlag OBJECT-TYPE
   SYNTAX      INTEGER
               {
               disabled (0),
               enabled (1)
               }
   MAX-ACCESS  read-write
   STATUS      current
   DESCRIPTION
      "Path: atm.editConf.pvcTable.ipV6.addresses.ra.onLinkFlag

       Possibilities:
               disabled   (0)
               enabled   (1)"
   ::= {er1646v2ATMFwCfgIpV6AddressesEntry 67371008}

er1646v2ATMFwCfgIpV6AddressesRaAutoFlag OBJECT-TYPE
   SYNTAX      INTEGER
               {
               disabled (0),
               enabled (1)
               }
   MAX-ACCESS  read-write
   STATUS      current
   DESCRIPTION
      "Path: atm.editConf.pvcTable.ipV6.addresses.ra.autonomousFlag

       Possibilities:
               disabled   (0)
               enabled   (1)"
   ::= {er1646v2ATMFwCfgIpV6AddressesEntry 67567616}

er1646v2ATMFwCfgIpV6AddressesRaValidLifeTime OBJECT-TYPE
   SYNTAX      TimeTicks
   MAX-ACCESS  read-write
   STATUS      current
   DESCRIPTION
      "Path: atm.editConf.pvcTable.ipV6.addresses.ra.validLifeTime

       Time in centi-second."
   ::= {er1646v2ATMFwCfgIpV6AddressesEntry 67239936}

er1646v2ATMFwCfgIpV6AddressesRaValidLTMode OBJECT-TYPE
   SYNTAX      INTEGER
               {
               fixed (0),
               infinite (2)
               }
   MAX-ACCESS  read-write
   STATUS      current
   DESCRIPTION
      "Path: atm.editConf.pvcTable.ipV6.addresses.ra.validLifeTimeMode

       Possibilities:
               fixed   (0)
               infinite   (2)"
   ::= {er1646v2ATMFwCfgIpV6AddressesEntry 67305472}

er1646v2ATMFwCfgIpV6AddressesRaPrefLifeTime OBJECT-TYPE
   SYNTAX      TimeTicks
   MAX-ACCESS  read-write
   STATUS      current
   DESCRIPTION
      "Path: atm.editConf.pvcTable.ipV6.addresses.ra.prefLifeTime

       Time in centi-second."
   ::= {er1646v2ATMFwCfgIpV6AddressesEntry 67436544}

er1646v2ATMFwCfgIpV6AddressesRaPrefLTMode OBJECT-TYPE
   SYNTAX      INTEGER
               {
               fixed (0),
               infinite (2)
               }
   MAX-ACCESS  read-write
   STATUS      current
   DESCRIPTION
      "Path: atm.editConf.pvcTable.ipV6.addresses.ra.prefLifeTimeMode

       Possibilities:
               fixed   (0)
               infinite   (2)"
   ::= {er1646v2ATMFwCfgIpV6AddressesEntry 67502080}

er1646v2ATMFwCfgIpV6RaDnsOptionsRdnssServers OBJECT-TYPE
   SYNTAX      SEQUENCE OF Er1646v2ATMFwCfgIpV6RaDnsOptionsRdnssServersEntry
   MAX-ACCESS  not-accessible
   STATUS      current
   DESCRIPTION
      ""
   ::= {er1646v2ATMFwCfg 705039144}

er1646v2ATMFwCfgIpV6RaDnsOptionsRdnssServersEntry OBJECT-TYPE
   SYNTAX      Er1646v2ATMFwCfgIpV6RaDnsOptionsRdnssServersEntry
   MAX-ACCESS  not-accessible
   STATUS      current
   DESCRIPTION
      ""
   INDEX      { er1646v2ATMFwCfgIpV6RaDnsOptionsRdnssServersGlobalIx,
                er1646v2ATMFwCfgTableIx,
                er1646v2ATMFwCfgIpV6RaDnsOptionsRdnssServersTableIx }
   ::= {er1646v2ATMFwCfgIpV6RaDnsOptionsRdnssServers 1}

Er1646v2ATMFwCfgIpV6RaDnsOptionsRdnssServersEntry ::=
   SEQUENCE
      {
      er1646v2ATMFwCfgIpV6RaDnsOptionsRdnssServersActions
         VariableLengthTableActions,
      er1646v2ATMFwCfgIpV6RaDnsOptionsRdnssServersGlobalIx
         GlobalIndex,
      er1646v2ATMFwCfgIpV6RaDnsOptionsRdnssServersTableIx
         TableIndex,
      er1646v2ATMFwCfgIpV6RaDnsOptionsRdnssServersAddress
         Ipv6Address
      }

er1646v2ATMFwCfgIpV6RaDnsOptionsRdnssServersActions OBJECT-TYPE
   SYNTAX      VariableLengthTableActions
   MAX-ACCESS  read-write
   STATUS      current
   DESCRIPTION
      "By way of this field, some manipulations
       on this table may be performed."
   ::= {er1646v2ATMFwCfgIpV6RaDnsOptionsRdnssServersEntry 2}

er1646v2ATMFwCfgIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2ATMFwCfgIpV6RaDnsOptionsRdnssServersEntry 10}

er1646v2ATMFwCfgIpV6RaDnsOptionsRdnssServersTableIx OBJECT-TYPE
   SYNTAX      TableIndex
   MAX-ACCESS  not-accessible
   STATUS      current
   DESCRIPTION
      ""
   ::= {er1646v2ATMFwCfgIpV6RaDnsOptionsRdnssServersEntry 11}

er1646v2ATMFwCfgIpV6RaDnsOptionsRdnssServersAddress OBJECT-TYPE
   SYNTAX      Ipv6Address
   MAX-ACCESS  read-write
   STATUS      current
   DESCRIPTION
      "Path: atm.editConf.pvcTable.ipV6.ra.dnsOptions.rdnss.servers.address

       ipv6 address"
   ::= {er1646v2ATMFwCfgIpV6RaDnsOptionsRdnssServersEntry 16777216}

er1646v2ATMFwCfgIpV6RaDnsOptionsDnsslDomains OBJECT-TYPE
   SYNTAX      SEQUENCE OF Er1646v2ATMFwCfgIpV6RaDnsOptionsDnsslDomainsEntry
   MAX-ACCESS  not-accessible
   STATUS      current
   DESCRIPTION
      ""
   ::= {er1646v2ATMFwCfg 705039176}

er1646v2ATMFwCfgIpV6RaDnsOptionsDnsslDomainsEntry OBJECT-TYPE
   SYNTAX      Er1646v2ATMFwCfgIpV6RaDnsOptionsDnsslDomainsEntry
   MAX-ACCESS  not-accessible
   STATUS      current
   DESCRIPTION
      ""
   INDEX      { er1646v2ATMFwCfgIpV6RaDnsOptionsDnsslDomainsGlobalIx,
                er1646v2ATMFwCfgTableIx,
                er1646v2ATMFwCfgIpV6RaDnsOptionsDnsslDomainsTableIx }
   ::= {er1646v2ATMFwCfgIpV6RaDnsOptionsDnsslDomains 1}

Er1646v2ATMFwCfgIpV6RaDnsOptionsDnsslDomainsEntry ::=
   SEQUENCE
      {
      er1646v2ATMFwCfgIpV6RaDnsOptionsDnsslDomainsActions
         VariableLengthTableActions,
      er1646v2ATMFwCfgIpV6RaDnsOptionsDnsslDomainsGlobalIx
         GlobalIndex,
      er1646v2ATMFwCfgIpV6RaDnsOptionsDnsslDomainsTableIx
         TableIndex,
      er1646v2ATMFwCfgIpV6RaDnsOptionsDnsslDomainsName
         DisplayString
      }

er1646v2ATMFwCfgIpV6RaDnsOptionsDnsslDomainsActions OBJECT-TYPE
   SYNTAX      VariableLengthTableActions
   MAX-ACCESS  read-write
   STATUS      current
   DESCRIPTION
      "By way of this field, some manipulations
       on this table may be performed."
   ::= {er1646v2ATMFwCfgIpV6RaDnsOptionsDnsslDomainsEntry 2}

er1646v2ATMFwCfgIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2ATMFwCfgIpV6RaDnsOptionsDnsslDomainsEntry 10}

er1646v2ATMFwCfgIpV6RaDnsOptionsDnsslDomainsTableIx OBJECT-TYPE
   SYNTAX      TableIndex
   MAX-ACCESS  not-accessible
   STATUS      current
   DESCRIPTION
      ""
   ::= {er1646v2ATMFwCfgIpV6RaDnsOptionsDnsslDomainsEntry 11}

er1646v2ATMFwCfgIpV6RaDnsOptionsDnsslDomainsName OBJECT-TYPE
   SYNTAX      DisplayString
   MAX-ACCESS  read-write
   STATUS      current
   DESCRIPTION
      "Path: atm.editConf.pvcTable.ipV6.ra.dnsOptions.dnssl.domains.name"
   ::= {er1646v2ATMFwCfgIpV6RaDnsOptionsDnsslDomainsEntry 16777216}

er1646v2ATMFwCfgIpV6DhcpClientUserClassOpt OBJECT-TYPE
   SYNTAX      SEQUENCE OF Er1646v2ATMFwCfgIpV6DhcpClientUserClassOptEntry
   MAX-ACCESS  not-accessible
   STATUS      current
   DESCRIPTION
      ""
   ::= {er1646v2ATMFwCfg 705312768}

er1646v2ATMFwCfgIpV6DhcpClientUserClassOptEntry OBJECT-TYPE
   SYNTAX      Er1646v2ATMFwCfgIpV6DhcpClientUserClassOptEntry
   MAX-ACCESS  not-accessible
   STATUS      current
   DESCRIPTION
      ""
   INDEX      { er1646v2ATMFwCfgIpV6DhcpClientUserClassOptGlobalIx,
                er1646v2ATMFwCfgTableIx,
                er1646v2ATMFwCfgIpV6DhcpClientUserClassOptTableIx }
   ::= {er1646v2ATMFwCfgIpV6DhcpClientUserClassOpt 1}

Er1646v2ATMFwCfgIpV6DhcpClientUserClassOptEntry ::=
   SEQUENCE
      {
      er1646v2ATMFwCfgIpV6DhcpClientUserClassOptActions
         VariableLengthTableActions,
      er1646v2ATMFwCfgIpV6DhcpClientUserClassOptGlobalIx
         GlobalIndex,
      er1646v2ATMFwCfgIpV6DhcpClientUserClassOptTableIx
         TableIndex,
      er1646v2ATMFwCfgIpV6DhcpClientUserClassOptValueAscii
         DisplayString,
      er1646v2ATMFwCfgIpV6DhcpClientUserClassOptValueDecimal
         Integer32,
      er1646v2ATMFwCfgIpV6DhcpClientUserClassOptValueHexData
         OCTET STRING
      }

er1646v2ATMFwCfgIpV6DhcpClientUserClassOptActions OBJECT-TYPE
   SYNTAX      VariableLengthTableActions
   MAX-ACCESS  read-write
   STATUS      current
   DESCRIPTION
      "By way of this field, some manipulations
       on this table may be performed."
   ::= {er1646v2ATMFwCfgIpV6DhcpClientUserClassOptEntry 2}

er1646v2ATMFwCfgIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2ATMFwCfgIpV6DhcpClientUserClassOptEntry 10}

er1646v2ATMFwCfgIpV6DhcpClientUserClassOptTableIx OBJECT-TYPE
   SYNTAX      TableIndex
   MAX-ACCESS  not-accessible
   STATUS      current
   DESCRIPTION
      ""
   ::= {er1646v2ATMFwCfgIpV6DhcpClientUserClassOptEntry 11}

er1646v2ATMFwCfgIpV6DhcpClientUserClassOptValueAscii OBJECT-TYPE
   SYNTAX      DisplayString
   MAX-ACCESS  read-write
   STATUS      current
   DESCRIPTION
      "Path: atm.editConf.pvcTable.ipV6.dhcp.client.userClassOpt.value.ascii"
   ::= {er1646v2ATMFwCfgIpV6DhcpClientUserClassOptEntry 16842752}

er1646v2ATMFwCfgIpV6DhcpClientUserClassOptValueDecimal OBJECT-TYPE
   SYNTAX      Integer32
   MAX-ACCESS  read-write
   STATUS      current
   DESCRIPTION
      "Path: atm.editConf.pvcTable.ipV6.dhcp.client.userClassOpt.value.decimal"
   ::= {er1646v2ATMFwCfgIpV6DhcpClientUserClassOptEntry 16908288}

er1646v2ATMFwCfgIpV6DhcpClientUserClassOptValueHexData OBJECT-TYPE
   SYNTAX      OCTET STRING
   MAX-ACCESS  read-write
   STATUS      current
   DESCRIPTION
      "Path: atm.editConf.pvcTable.ipV6.dhcp.client.userClassOpt.value.hexData"
   ::= {er1646v2ATMFwCfgIpV6DhcpClientUserClassOptEntry 16973824}

er1646v2ATMFwCfgIpV6DhcpClientVendorCl OBJECT-TYPE
   SYNTAX      SEQUENCE OF Er1646v2ATMFwCfgIpV6DhcpClientVendorClEntry
   MAX-ACCESS  not-accessible
   STATUS      current
   DESCRIPTION
      ""
   ::= {er1646v2ATMFwCfg 705313792}

er1646v2ATMFwCfgIpV6DhcpClientVendorClEntry OBJECT-TYPE
   SYNTAX      Er1646v2ATMFwCfgIpV6DhcpClientVendorClEntry
   MAX-ACCESS  not-accessible
   STATUS      current
   DESCRIPTION
      ""
   INDEX      { er1646v2ATMFwCfgIpV6DhcpClientVendorClGlobalIx,
                er1646v2ATMFwCfgTableIx,
                er1646v2ATMFwCfgIpV6DhcpClientVendorClTableIx }
   ::= {er1646v2ATMFwCfgIpV6DhcpClientVendorCl 1}

Er1646v2ATMFwCfgIpV6DhcpClientVendorClEntry ::=
   SEQUENCE
      {
      er1646v2ATMFwCfgIpV6DhcpClientVendorClActions
         VariableLengthTableActions,
      er1646v2ATMFwCfgIpV6DhcpClientVendorClGlobalIx
         GlobalIndex,
      er1646v2ATMFwCfgIpV6DhcpClientVendorClTableIx
         TableIndex,
      er1646v2ATMFwCfgIpV6DhcpClientVendorClValueAscii
         DisplayString,
      er1646v2ATMFwCfgIpV6DhcpClientVendorClValueDecimal
         Integer32,
      er1646v2ATMFwCfgIpV6DhcpClientVendorClValueHexData
         OCTET STRING
      }

er1646v2ATMFwCfgIpV6DhcpClientVendorClActions OBJECT-TYPE
   SYNTAX      VariableLengthTableActions
   MAX-ACCESS  read-write
   STATUS      current
   DESCRIPTION
      "By way of this field, some manipulations
       on this table may be performed."
   ::= {er1646v2ATMFwCfgIpV6DhcpClientVendorClEntry 2}

er1646v2ATMFwCfgIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2ATMFwCfgIpV6DhcpClientVendorClEntry 10}

er1646v2ATMFwCfgIpV6DhcpClientVendorClTableIx OBJECT-TYPE
   SYNTAX      TableIndex
   MAX-ACCESS  not-accessible
   STATUS      current
   DESCRIPTION
      ""
   ::= {er1646v2ATMFwCfgIpV6DhcpClientVendorClEntry 11}

er1646v2ATMFwCfgIpV6DhcpClientVendorClValueAscii OBJECT-TYPE
   SYNTAX      DisplayString
   MAX-ACCESS  read-write
   STATUS      current
   DESCRIPTION
      "Path: atm.editConf.pvcTable.ipV6.dhcp.client.vendorClassOpt.value.ascii"
   ::= {er1646v2ATMFwCfgIpV6DhcpClientVendorClEntry 16842752}

er1646v2ATMFwCfgIpV6DhcpClientVendorClValueDecimal OBJECT-TYPE
   SYNTAX      Integer32
   MAX-ACCESS  read-write
   STATUS      current
   DESCRIPTION
      "Path: atm.editConf.pvcTable.ipV6.dhcp.client.vendorClassOpt.value.decimal"
   ::= {er1646v2ATMFwCfgIpV6DhcpClientVendorClEntry 16908288}

er1646v2ATMFwCfgIpV6DhcpClientVendorClValueHexData OBJECT-TYPE
   SYNTAX      OCTET STRING
   MAX-ACCESS  read-write
   STATUS      current
   DESCRIPTION
      "Path: atm.editConf.pvcTable.ipV6.dhcp.client.vendorClassOpt.value.hexData"
   ::= {er1646v2ATMFwCfgIpV6DhcpClientVendorClEntry 16973824}

er1646v2ATMFwCfgIpV6DhcpRelayDestinations OBJECT-TYPE
   SYNTAX      SEQUENCE OF Er1646v2ATMFwCfgIpV6DhcpRelayDestinationsEntry
   MAX-ACCESS  not-accessible
   STATUS      current
   DESCRIPTION
      ""
   ::= {er1646v2ATMFwCfg 705323072}

er1646v2ATMFwCfgIpV6DhcpRelayDestinationsEntry OBJECT-TYPE
   SYNTAX      Er1646v2ATMFwCfgIpV6DhcpRelayDestinationsEntry
   MAX-ACCESS  not-accessible
   STATUS      current
   DESCRIPTION
      ""
   INDEX      { er1646v2ATMFwCfgIpV6DhcpRelayDestinationsGlobalIx,
                er1646v2ATMFwCfgTableIx,
                er1646v2ATMFwCfgIpV6DhcpRelayDestinationsTableIx }
   ::= {er1646v2ATMFwCfgIpV6DhcpRelayDestinations 1}

Er1646v2ATMFwCfgIpV6DhcpRelayDestinationsEntry ::=
   SEQUENCE
      {
      er1646v2ATMFwCfgIpV6DhcpRelayDestinationsActions
         VariableLengthTableActions,
      er1646v2ATMFwCfgIpV6DhcpRelayDestinationsGlobalIx
         GlobalIndex,
      er1646v2ATMFwCfgIpV6DhcpRelayDestinationsTableIx
         TableIndex,
      er1646v2ATMFwCfgIpV6DhcpRelayDestinationsAddress
         Ipv6Address,
      er1646v2ATMFwCfgIpV6DhcpRelayDestinationsInterface
         DisplayString
      }

er1646v2ATMFwCfgIpV6DhcpRelayDestinationsActions OBJECT-TYPE
   SYNTAX      VariableLengthTableActions
   MAX-ACCESS  read-write
   STATUS      current
   DESCRIPTION
      "By way of this field, some manipulations
       on this table may be performed."
   ::= {er1646v2ATMFwCfgIpV6DhcpRelayDestinationsEntry 2}

er1646v2ATMFwCfgIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2ATMFwCfgIpV6DhcpRelayDestinationsEntry 10}

er1646v2ATMFwCfgIpV6DhcpRelayDestinationsTableIx OBJECT-TYPE
   SYNTAX      TableIndex
   MAX-ACCESS  not-accessible
   STATUS      current
   DESCRIPTION
      ""
   ::= {er1646v2ATMFwCfgIpV6DhcpRelayDestinationsEntry 11}

er1646v2ATMFwCfgIpV6DhcpRelayDestinationsAddress OBJECT-TYPE
   SYNTAX      Ipv6Address
   MAX-ACCESS  read-write
   STATUS      current
   DESCRIPTION
      "Path: atm.editConf.pvcTable.ipV6.dhcp.relay.destinations.address

       ipv6 address"
   ::= {er1646v2ATMFwCfgIpV6DhcpRelayDestinationsEntry 16777216}

er1646v2ATMFwCfgIpV6DhcpRelayDestinationsInterface OBJECT-TYPE
   SYNTAX      DisplayString
   MAX-ACCESS  read-write
   STATUS      current
   DESCRIPTION
      "Path: atm.editConf.pvcTable.ipV6.dhcp.relay.destinations.interface"
   ::= {er1646v2ATMFwCfgIpV6DhcpRelayDestinationsEntry 33554432}

er1646v2ATMFwCfgBridgingVlTVlans OBJECT-TYPE
   SYNTAX      SEQUENCE OF Er1646v2ATMFwCfgBridgingVlTVlansEntry
   MAX-ACCESS  not-accessible
   STATUS      current
   DESCRIPTION
      ""
   ::= {er1646v2ATMFwCfg 459079680}

er1646v2ATMFwCfgBridgingVlTVlansEntry OBJECT-TYPE
   SYNTAX      Er1646v2ATMFwCfgBridgingVlTVlansEntry
   MAX-ACCESS  not-accessible
   STATUS      current
   DESCRIPTION
      ""
   INDEX      { er1646v2ATMFwCfgBridgingVlTVlansGlobalIx,
                er1646v2ATMFwCfgTableIx,
                er1646v2ATMFwCfgBridgingVlTVlansTableIx }
   ::= {er1646v2ATMFwCfgBridgingVlTVlans 1}

Er1646v2ATMFwCfgBridgingVlTVlansEntry ::=
   SEQUENCE
      {
      er1646v2ATMFwCfgBridgingVlTVlansActions
         VariableLengthTableActions,
      er1646v2ATMFwCfgBridgingVlTVlansGlobalIx
         GlobalIndex,
      er1646v2ATMFwCfgBridgingVlTVlansTableIx
         TableIndex,
      er1646v2ATMFwCfgBridgingVlTVlansVid
         Integer32,
      er1646v2ATMFwCfgBridgingVlTVlansEndVid
         Integer32,
      er1646v2ATMFwCfgBridgingVlTVlansAction
         INTEGER,
      er1646v2ATMFwCfgBridgingVlTVlansTagInfoTpid
         INTEGER,
      er1646v2ATMFwCfgBridgingVlTVlansTagInfoVid
         Integer32
      }

er1646v2ATMFwCfgBridgingVlTVlansActions OBJECT-TYPE
   SYNTAX      VariableLengthTableActions
   MAX-ACCESS  read-write
   STATUS      current
   DESCRIPTION
      "By way of this field, some manipulations
       on this table may be performed."
   ::= {er1646v2ATMFwCfgBridgingVlTVlansEntry 2}

er1646v2ATMFwCfgBridgingVlTVlansGlobalIx OBJECT-TYPE
   SYNTAX      GlobalIndex
   MAX-ACCESS  not-accessible
   STATUS      current
   DESCRIPTION
      "The value of the tlsCntTreeGlobalIndex of the MANAGED OBJECT."
   ::= {er1646v2ATMFwCfgBridgingVlTVlansEntry 10}

er1646v2ATMFwCfgBridgingVlTVlansTableIx OBJECT-TYPE
   SYNTAX      TableIndex
   MAX-ACCESS  not-accessible
   STATUS      current
   DESCRIPTION
      ""
   ::= {er1646v2ATMFwCfgBridgingVlTVlansEntry 11}

er1646v2ATMFwCfgBridgingVlTVlansVid OBJECT-TYPE
   SYNTAX      Integer32
   MAX-ACCESS  read-write
   STATUS      current
   DESCRIPTION
      "Path: atm.editConf.pvcTable.bridging.vlanTagging.vlans.vid"
   ::= {er1646v2ATMFwCfgBridgingVlTVlansEntry 536870912}

er1646v2ATMFwCfgBridgingVlTVlansEndVid OBJECT-TYPE
   SYNTAX      Integer32
   MAX-ACCESS  read-write
   STATUS      current
   DESCRIPTION
      "Path: atm.editConf.pvcTable.bridging.vlanTagging.vlans.endVid"
   ::= {er1646v2ATMFwCfgBridgingVlTVlansEntry 2147483648}

er1646v2ATMFwCfgBridgingVlTVlansAction OBJECT-TYPE
   SYNTAX      INTEGER
               {
               discard (0),
               accept (1),
               tag (2)
               }
   MAX-ACCESS  read-write
   STATUS      current
   DESCRIPTION
      "Path: atm.editConf.pvcTable.bridging.vlanTagging.vlans.action

       Possibilities:
               discard   (0)
               accept   (1)
               tag   (2)"
   ::= {er1646v2ATMFwCfgBridgingVlTVlansEntry 1073741824}

er1646v2ATMFwCfgBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.vlans.tagInfo.tpid

       Possibilities:
               dot1Q   (33024)
               dot1ad   (34984)
               0x9100   (37120)
               0x9200   (37376)
               0x9300   (37632)"
   ::= {er1646v2ATMFwCfgBridgingVlTVlansEntry 1677721600}

er1646v2ATMFwCfgBridgingVlTVlansTagInfoVid OBJECT-TYPE
   SYNTAX      Integer32
   MAX-ACCESS  read-write
   STATUS      current
   DESCRIPTION
      "Path: atm.editConf.pvcTable.bridging.vlanTagging.vlans.tagInfo.vid"
   ::= {er1646v2ATMFwCfgBridgingVlTVlansEntry 1744830464}

er1646v2ATMFwCfgFrDlci OBJECT-TYPE
   SYNTAX      SEQUENCE OF Er1646v2ATMFwCfgFrDlciEntry
   MAX-ACCESS  not-accessible
   STATUS      current
   DESCRIPTION
      ""
   ::= {er1646v2ATMFwCfg 689963008}

er1646v2ATMFwCfgFrDlciEntry OBJECT-TYPE
   SYNTAX      Er1646v2ATMFwCfgFrDlciEntry
   MAX-ACCESS  not-accessible
   STATUS      current
   DESCRIPTION
      ""
   INDEX      { er1646v2ATMFwCfgFrDlciGlobalIx,
                er1646v2ATMFwCfgTableIx,
                er1646v2ATMFwCfgFrDlciTableIx }
   ::= {er1646v2ATMFwCfgFrDlci 1}

Er1646v2ATMFwCfgFrDlciEntry ::=
   SEQUENCE
      {
      er1646v2ATMFwCfgFrDlciActions
         VariableLengthTableActions,
      er1646v2ATMFwCfgFrDlciGlobalIx
         GlobalIndex,
      er1646v2ATMFwCfgFrDlciTableIx
         TableIndex,
      er1646v2ATMFwCfgFrDlciName
         DisplayString,
      er1646v2ATMFwCfgFrDlciAdminStatus
         INTEGER,
      er1646v2ATMFwCfgFrDlciMode
         INTEGER,
      er1646v2ATMFwCfgFrDlciIpVrfRouter
         DisplayString,
      er1646v2ATMFwCfgFrDlciIpAdr
         IpAddress,
      er1646v2ATMFwCfgFrDlciIpNetm
         IpAddress,
      er1646v2ATMFwCfgFrDlciIpSNetName
         INTEGER,
      er1646v2ATMFwCfgFrDlciIpSNetCust
         DisplayString,
      er1646v2ATMFwCfgFrDlciIpRem
         IpAddress,
      er1646v2ATMFwCfgFrDlciIpMtu
         Integer32,
      er1646v2ATMFwCfgFrDlciIpMssAdjust
         INTEGER,
      er1646v2ATMFwCfgFrDlciIpRipMetric
         Integer32,
      er1646v2ATMFwCfgFrDlciIpRipMetricOut
         Integer32,
      er1646v2ATMFwCfgFrDlciIpRipMode
         INTEGER,
      er1646v2ATMFwCfgFrDlciIpRipTxVer
         INTEGER,
      er1646v2ATMFwCfgFrDlciIpRipRxVer
         INTEGER,
      er1646v2ATMFwCfgFrDlciIpRipSplitH
         INTEGER,
      er1646v2ATMFwCfgFrDlciIpRipAuth
         INTEGER,
      er1646v2ATMFwCfgFrDlciIpRipFilter
         DisplayString,
      er1646v2ATMFwCfgFrDlciIpRipFilterIn
         DisplayString,
      er1646v2ATMFwCfgFrDlciIpRipClearNextHop
         INTEGER,
      er1646v2ATMFwCfgFrDlciIpAccPol
         DisplayString,
      er1646v2ATMFwCfgFrDlciIpAB
         DisplayString,
      er1646v2ATMFwCfgFrDlciIpMA
         INTEGER,
      er1646v2ATMFwCfgFrDlciIpMF
         Integer32,
      er1646v2ATMFwCfgFrDlciIpDB
         INTEGER,
      er1646v2ATMFwCfgFrDlciIpIR
         INTEGER,
      er1646v2ATMFwCfgFrDlciIpIgmp
         INTEGER,
      er1646v2ATMFwCfgFrDlciIpNN
         DisplayString,
      er1646v2ATMFwCfgFrDlciIpPimMode
         INTEGER,
      er1646v2ATMFwCfgFrDlciIpPimDrPriority
         Counter32,
      er1646v2ATMFwCfgFrDlciIpPimHelloTime
         TimeTicks,
      er1646v2ATMFwCfgFrDlciIpPimPropagationDelay
         TimeTicks,
      er1646v2ATMFwCfgFrDlciIpPimOverrideInterval
         TimeTicks,
      er1646v2ATMFwCfgFrDlciIpPimBsrBorder
         INTEGER,
      er1646v2ATMFwCfgFrDlciIpPimTtlThreshold
         Integer32,
      er1646v2ATMFwCfgFrDlciIpIMNetworkUnreachable
         INTEGER,
      er1646v2ATMFwCfgFrDlciIpIMHostUnreachable
         INTEGER,
      er1646v2ATMFwCfgFrDlciIpIMProtocolUnreachable
         INTEGER,
      er1646v2ATMFwCfgFrDlciIpIMPortUnreachable
         INTEGER,
      er1646v2ATMFwCfgFrDlciIpIMMtuExceeded
         INTEGER,
      er1646v2ATMFwCfgFrDlciIpIMAdminProhibited
         INTEGER,
      er1646v2ATMFwCfgFrDlciIpIMTtlExceeded
         INTEGER,
      er1646v2ATMFwCfgFrDlciIpIMRedirect
         INTEGER,
      er1646v2ATMFwCfgFrDlciBridgingAccList
         DisplayString,
      er1646v2ATMFwCfgFrDlciBridgingInACL
         DisplayString,
      er1646v2ATMFwCfgFrDlciBridgingTp
         DisplayString,
      er1646v2ATMFwCfgFrDlciBridgingBrGrp
         DisplayString,
      er1646v2ATMFwCfgFrDlciBridgingLimBC
         INTEGER,
      er1646v2ATMFwCfgFrDlciBridgingPrivateMode
         INTEGER,
      er1646v2ATMFwCfgFrDlciBridgingLearning
         INTEGER,
      er1646v2ATMFwCfgFrDlciBridgingMaxCacheSize
         INTEGER,
      er1646v2ATMFwCfgFrDlciBridgingRelearnDropOnRelearn
         INTEGER,
      er1646v2ATMFwCfgFrDlciBridgingRelearnShutdownThreshold
         Integer32,
      er1646v2ATMFwCfgFrDlciBridgingRelearnShutdownTime
         TimeTicks,
      er1646v2ATMFwCfgFrDlciBridgingRelearnLoopDetection
         INTEGER,
      er1646v2ATMFwCfgFrDlciBridgingRelearnLoopDetectionInterval
         TimeTicks,
      er1646v2ATMFwCfgFrDlciBridgingVlanMemberShip
         INTEGER,
      er1646v2ATMFwCfgFrDlciBridgingVlTUntaggedAction
         INTEGER,
      er1646v2ATMFwCfgFrDlciBridgingVlTUntaggedTagInfoTpid
         INTEGER,
      er1646v2ATMFwCfgFrDlciBridgingVlTUntaggedTagInfoVid
         Integer32,
      er1646v2ATMFwCfgFrDlciBridgingVlTUnknownVlansAction
         INTEGER,
      er1646v2ATMFwCfgFrDlciBridgingVlTUnknownVlansTagInfoTpid
         INTEGER,
      er1646v2ATMFwCfgFrDlciBridgingVlTUnknownVlansTagInfoVid
         Integer32,
      er1646v2ATMFwCfgFrDlciBridgingDot1adType
         INTEGER,
      er1646v2ATMFwCfgFrDlciBridgingPriority
         Integer32,
      er1646v2ATMFwCfgFrDlciBridgingPathCost
         Integer32,
      er1646v2ATMFwCfgFrDlciBridgingInternalPathCost
         Integer32,
      er1646v2ATMFwCfgFrDlciBridgingTCD
         INTEGER,
      er1646v2ATMFwCfgFrDlciBridgingRestrictedRole
         INTEGER,
      er1646v2ATMFwCfgFrDlciBridgingAdminEdge
         INTEGER,
      er1646v2ATMFwCfgFrDlciBridgingOamMacDeviceMac
         DisplayString,
      er1646v2ATMFwCfgFrDlciBridgingOamMacUserMac
         OCTET STRING,
      er1646v2ATMFwCfgFrDlciBridgingOamMacBridgeMac
         DisplayString,
      er1646v2ATMFwCfgFrDlciBridgingMgmtInline
         INTEGER,
      er1646v2ATMFwCfgFrDlciBridgingL2ptMode
         INTEGER,
      er1646v2ATMFwCfgFrDlciBridgingL2ptProtocols
         Integer32,
      er1646v2ATMFwCfgFrDlciBridgingL2ptDestMac
         OCTET STRING,
      er1646v2ATMFwCfgFrDlciBridgingL2ptCos
         INTEGER,
      er1646v2ATMFwCfgFrDlciBridgingL2ptDropThrStp
         INTEGER,
      er1646v2ATMFwCfgFrDlciBridgingL2ptDropThrLldp
         INTEGER,
      er1646v2ATMFwCfgFrDlciBridgingL2ptDropThrOam
         INTEGER,
      er1646v2ATMFwCfgFrDlciBridgingL2ptDropThrCdp
         INTEGER,
      er1646v2ATMFwCfgFrDlciBridgingL2ptDropThrVtp
         INTEGER,
      er1646v2ATMFwCfgFrDlciBridgingL2ptDropThrLacp
         INTEGER,
      er1646v2ATMFwCfgFrDlciBridgingL2ptDropThrEfmOam
         INTEGER,
      er1646v2ATMFwCfgFrDlciBridgingL2ptDropThrPvst
         INTEGER,
      er1646v2ATMFwCfgFrDlciBridgingL2ptDropThrMmrp
         INTEGER,
      er1646v2ATMFwCfgFrDlciBridgingL2ptDropThrMvrp
         INTEGER,
      er1646v2ATMFwCfgFrDlciBridgingL2ptDropThrGvrp
         INTEGER,
      er1646v2ATMFwCfgFrDlciBridgingL2ptDropThrGmrp
         INTEGER,
      er1646v2ATMFwCfgFrDlciBridgingL2ptDropThrDtp
         INTEGER,
      er1646v2ATMFwCfgFrDlciBridgingL2ptDropThrPagp
         INTEGER,
      er1646v2ATMFwCfgFrDlciBridgingL2ptDropThrUdld
         INTEGER,
      er1646v2ATMFwCfgFrDlciFrDlci
         Integer32,
      er1646v2ATMFwCfgFrDlciFrCir
         Integer32,
      er1646v2ATMFwCfgFrDlciFrOverhead
         Integer32,
      er1646v2ATMFwCfgFrDlciFrTc
         Integer32,
      er1646v2ATMFwCfgFrDlciFrSlidingWindow
         INTEGER,
      er1646v2ATMFwCfgFrDlciFrDeBitSet
         INTEGER,
      er1646v2ATMFwCfgFrDlciFrDefaultQueue
         INTEGER,
      er1646v2ATMFwCfgFrDlciFrRxCir
         Integer32,
      er1646v2ATMFwCfgFrDlciFrRxExcess
         INTEGER,
      er1646v2ATMFwCfgFrDlciFrFragEMode
         INTEGER
      }

er1646v2ATMFwCfgFrDlciActions OBJECT-TYPE
   SYNTAX      VariableLengthTableActions
   MAX-ACCESS  read-write
   STATUS      current
   DESCRIPTION
      "By way of this field, some manipulations
       on this table may be performed."
   ::= {er1646v2ATMFwCfgFrDlciEntry 2}

er1646v2ATMFwCfgFrDlciGlobalIx OBJECT-TYPE
   SYNTAX      GlobalIndex
   MAX-ACCESS  not-accessible
   STATUS      current
   DESCRIPTION
      "The value of the tlsCntTreeGlobalIndex of the MANAGED OBJECT."
   ::= {er1646v2ATMFwCfgFrDlciEntry 10}

er1646v2ATMFwCfgFrDlciTableIx OBJECT-TYPE
   SYNTAX      TableIndex
   MAX-ACCESS  not-accessible
   STATUS      current
   DESCRIPTION
      ""
   ::= {er1646v2ATMFwCfgFrDlciEntry 11}

er1646v2ATMFwCfgFrDlciName OBJECT-TYPE
   SYNTAX      DisplayString
   MAX-ACCESS  read-write
   STATUS      current
   DESCRIPTION
      "Path: atm.editConf.pvcTable.frameRelay.dlciTable.name"
   ::= {er1646v2ATMFwCfgFrDlciEntry 16777216}

er1646v2ATMFwCfgFrDlciAdminStatus OBJECT-TYPE
   SYNTAX      INTEGER
               {
               up (1),
               down (2)
               }
   MAX-ACCESS  read-write
   STATUS      current
   DESCRIPTION
      "Path: atm.editConf.pvcTable.frameRelay.dlciTable.adminStatus

       Possibilities:
               up   (1)
               down   (2)"
   ::= {er1646v2ATMFwCfgFrDlciEntry 33554432}

er1646v2ATMFwCfgFrDlciMode OBJECT-TYPE
   SYNTAX      INTEGER
               {
               routing (1),
               bridging (2),
               routingAndBridging (3)
               }
   MAX-ACCESS  read-write
   STATUS      current
   DESCRIPTION
      "Path: atm.editConf.pvcTable.frameRelay.dlciTable.mode

       Possibilities:
               routing   (1)
               bridging   (2)
               routingAndBridging   (3)"
   ::= {er1646v2ATMFwCfgFrDlciEntry 67108864}

er1646v2ATMFwCfgFrDlciIpVrfRouter OBJECT-TYPE
   SYNTAX      DisplayString
   MAX-ACCESS  read-write
   STATUS      current
   DESCRIPTION
      "Path: atm.editConf.pvcTable.frameRelay.dlciTable.ip.vrfRouter"
   ::= {er1646v2ATMFwCfgFrDlciEntry 53215232}

er1646v2ATMFwCfgFrDlciIpAdr OBJECT-TYPE
   SYNTAX      IpAddress
   MAX-ACCESS  read-write
   STATUS      current
   DESCRIPTION
      "Path: atm.editConf.pvcTable.frameRelay.dlciTable.ip.address"
   ::= {er1646v2ATMFwCfgFrDlciEntry 58261504}

er1646v2ATMFwCfgFrDlciIpNetm OBJECT-TYPE
   SYNTAX      IpAddress
   MAX-ACCESS  read-write
   STATUS      current
   DESCRIPTION
      "Path: atm.editConf.pvcTable.frameRelay.dlciTable.ip.netMask"
   ::= {er1646v2ATMFwCfgFrDlciEntry 58392576}

er1646v2ATMFwCfgFrDlciIpSNetName OBJECT-TYPE
   SYNTAX      INTEGER
               {
               slOPTg (0),
               corp (2),
               dmz (3),
               internet (1)
               }
   MAX-ACCESS  read-write
   STATUS      current
   DESCRIPTION
      "Path: atm.editConf.pvcTable.frameRelay.dlciTable.ip.sNet.name

       Possibilities:
               <OPT>   (0)
               corp   (2)
               dmz   (3)
               internet   (1)"
   ::= {er1646v2ATMFwCfgFrDlciEntry 53674240}

er1646v2ATMFwCfgFrDlciIpSNetCust OBJECT-TYPE
   SYNTAX      DisplayString
   MAX-ACCESS  read-write
   STATUS      current
   DESCRIPTION
      "Path: atm.editConf.pvcTable.frameRelay.dlciTable.ip.sNet.custom"
   ::= {er1646v2ATMFwCfgFrDlciEntry 53674496}

er1646v2ATMFwCfgFrDlciIpRem OBJECT-TYPE
   SYNTAX      IpAddress
   MAX-ACCESS  read-write
   STATUS      current
   DESCRIPTION
      "Path: atm.editConf.pvcTable.frameRelay.dlciTable.ip.remote"
   ::= {er1646v2ATMFwCfgFrDlciEntry 58458112}

er1646v2ATMFwCfgFrDlciIpMtu OBJECT-TYPE
   SYNTAX      Integer32
   MAX-ACCESS  read-write
   STATUS      current
   DESCRIPTION
      "Path: atm.editConf.pvcTable.frameRelay.dlciTable.ip.mtu"
   ::= {er1646v2ATMFwCfgFrDlciEntry 52953088}

er1646v2ATMFwCfgFrDlciIpMssAdjust OBJECT-TYPE
   SYNTAX      INTEGER
               {
               disabled (0),
               auto (65536)
               }
   MAX-ACCESS  read-write
   STATUS      current
   DESCRIPTION
      "Path: atm.editConf.pvcTable.frameRelay.dlciTable.ip.mssAdjust

       Possibilities:
               disabled   (0)
               auto   (65536)"
   ::= {er1646v2ATMFwCfgFrDlciEntry 53280768}

er1646v2ATMFwCfgFrDlciIpRipMetric OBJECT-TYPE
   SYNTAX      Integer32
   MAX-ACCESS  read-write
   STATUS      current
   DESCRIPTION
      "Path: atm.editConf.pvcTable.frameRelay.dlciTable.ip.rip.metric"
   ::= {er1646v2ATMFwCfgFrDlciEntry 51712768}

er1646v2ATMFwCfgFrDlciIpRipMetricOut OBJECT-TYPE
   SYNTAX      Integer32
   MAX-ACCESS  read-write
   STATUS      current
   DESCRIPTION
      "Path: atm.editConf.pvcTable.frameRelay.dlciTable.ip.rip.metricOut"
   ::= {er1646v2ATMFwCfgFrDlciEntry 51713024}

er1646v2ATMFwCfgFrDlciIpRipMode OBJECT-TYPE
   SYNTAX      INTEGER
               {
               disabled (0),
               passive (1),
               active (2)
               }
   MAX-ACCESS  read-write
   STATUS      current
   DESCRIPTION
      "Path: atm.editConf.pvcTable.frameRelay.dlciTable.ip.rip.mode

       Possibilities:
               disabled   (0)
               passive   (1)
               active   (2)"
   ::= {er1646v2ATMFwCfgFrDlciEntry 51713280}

er1646v2ATMFwCfgFrDlciIpRipTxVer OBJECT-TYPE
   SYNTAX      INTEGER
               {
               rip1 (0),
               rip2 (1),
               rip1mcompatible (2)
               }
   MAX-ACCESS  read-write
   STATUS      current
   DESCRIPTION
      "Path: atm.editConf.pvcTable.frameRelay.dlciTable.ip.rip.txVersion

       Possibilities:
               rip1   (0)
               rip2   (1)
               rip1-compatible   (2)"
   ::= {er1646v2ATMFwCfgFrDlciEntry 51716864}

er1646v2ATMFwCfgFrDlciIpRipRxVer OBJECT-TYPE
   SYNTAX      INTEGER
               {
               rip1only (0),
               rip2only (1),
               rip12 (2)
               }
   MAX-ACCESS  read-write
   STATUS      current
   DESCRIPTION
      "Path: atm.editConf.pvcTable.frameRelay.dlciTable.ip.rip.rxVersion

       Possibilities:
               rip1only   (0)
               rip2only   (1)
               rip1&2   (2)"
   ::= {er1646v2ATMFwCfgFrDlciEntry 51717120}

er1646v2ATMFwCfgFrDlciIpRipSplitH OBJECT-TYPE
   SYNTAX      INTEGER
               {
               disabled (0),
               enabled (1),
               poisonedReverse (2)
               }
   MAX-ACCESS  read-write
   STATUS      current
   DESCRIPTION
      "Path: atm.editConf.pvcTable.frameRelay.dlciTable.ip.rip.splitHorizon

       Possibilities:
               disabled   (0)
               enabled   (1)
               poisonedReverse   (2)"
   ::= {er1646v2ATMFwCfgFrDlciEntry 51713792}

er1646v2ATMFwCfgFrDlciIpRipAuth OBJECT-TYPE
   SYNTAX      INTEGER
               {
               disabled (0),
               texts (1),
               md5 (2)
               }
   MAX-ACCESS  read-write
   STATUS      current
   DESCRIPTION
      "Path: atm.editConf.pvcTable.frameRelay.dlciTable.ip.rip.authentication

       Possibilities:
               disabled   (0)
               text    (1)
               md5   (2)"
   ::= {er1646v2ATMFwCfgFrDlciEntry 51712512}

er1646v2ATMFwCfgFrDlciIpRipFilter OBJECT-TYPE
   SYNTAX      DisplayString
   MAX-ACCESS  read-write
   STATUS      current
   DESCRIPTION
      "Path: atm.editConf.pvcTable.frameRelay.dlciTable.ip.rip.filter"
   ::= {er1646v2ATMFwCfgFrDlciEntry 51716096}

er1646v2ATMFwCfgFrDlciIpRipFilterIn OBJECT-TYPE
   SYNTAX      DisplayString
   MAX-ACCESS  read-write
   STATUS      current
   DESCRIPTION
      "Path: atm.editConf.pvcTable.frameRelay.dlciTable.ip.rip.filterIn"
   ::= {er1646v2ATMFwCfgFrDlciEntry 51716352}

er1646v2ATMFwCfgFrDlciIpRipClearNextHop OBJECT-TYPE
   SYNTAX      INTEGER
               {
               disabled (0),
               enabled (1)
               }
   MAX-ACCESS  read-write
   STATUS      current
   DESCRIPTION
      "Path: atm.editConf.pvcTable.frameRelay.dlciTable.ip.rip.clearNextHop

       Possibilities:
               disabled   (0)
               enabled   (1)"
   ::= {er1646v2ATMFwCfgFrDlciEntry 51708416}

er1646v2ATMFwCfgFrDlciIpAccPol OBJECT-TYPE
   SYNTAX      DisplayString
   MAX-ACCESS  read-write
   STATUS      current
   DESCRIPTION
      "Path: atm.editConf.pvcTable.frameRelay.dlciTable.ip.accessPolicy"
   ::= {er1646v2ATMFwCfgFrDlciEntry 53084160}

er1646v2ATMFwCfgFrDlciIpAB OBJECT-TYPE
   SYNTAX      DisplayString
   MAX-ACCESS  read-write
   STATUS      current
   DESCRIPTION
      "Path: atm.editConf.pvcTable.frameRelay.dlciTable.ip.trafficPolicy"
   ::= {er1646v2ATMFwCfgFrDlciEntry 51249152}

er1646v2ATMFwCfgFrDlciIpMA OBJECT-TYPE
   SYNTAX      INTEGER
               {
               disabled (0),
               enabled (1)
               }
   MAX-ACCESS  read-write
   STATUS      current
   DESCRIPTION
      "Path: atm.editConf.pvcTable.frameRelay.dlciTable.ip.mgmtAccess

       Possibilities:
               disabled   (0)
               enabled   (1)"
   ::= {er1646v2ATMFwCfgFrDlciEntry 51380224}

er1646v2ATMFwCfgFrDlciIpMF OBJECT-TYPE
   SYNTAX      Integer32
   MAX-ACCESS  read-write
   STATUS      current
   DESCRIPTION
      "Path: atm.editConf.pvcTable.frameRelay.dlciTable.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2ATMFwCfgFrDlciEntry 51445760}

er1646v2ATMFwCfgFrDlciIpDB OBJECT-TYPE
   SYNTAX      INTEGER
               {
               disabled (0),
               enabled (1)
               }
   MAX-ACCESS  read-write
   STATUS      current
   DESCRIPTION
      "Path: atm.editConf.pvcTable.frameRelay.dlciTable.ip.directedBroadcasts

       Possibilities:
               disabled   (0)
               enabled   (1)"
   ::= {er1646v2ATMFwCfgFrDlciEntry 51773440}

er1646v2ATMFwCfgFrDlciIpIR OBJECT-TYPE
   SYNTAX      INTEGER
               {
               disabled (0),
               enabled (1)
               }
   MAX-ACCESS  read-write
   STATUS      current
   DESCRIPTION
      "Path: atm.editConf.pvcTable.frameRelay.dlciTable.ip.icmpRedirects

       Possibilities:
               disabled   (0)
               enabled   (1)"
   ::= {er1646v2ATMFwCfgFrDlciEntry 52035584}

er1646v2ATMFwCfgFrDlciIpIgmp OBJECT-TYPE
   SYNTAX      INTEGER
               {
               disabled (0),
               proxy (1),
               router (2),
               v3Router (5)
               }
   MAX-ACCESS  read-write
   STATUS      current
   DESCRIPTION
      "Path: atm.editConf.pvcTable.frameRelay.dlciTable.ip.igmp

       Possibilities:
               disabled   (0)
               proxy   (1)
               router   (2)
               v3Router   (5)"
   ::= {er1646v2ATMFwCfgFrDlciEntry 52428800}

er1646v2ATMFwCfgFrDlciIpNN OBJECT-TYPE
   SYNTAX      DisplayString
   MAX-ACCESS  read-write
   STATUS      current
   DESCRIPTION
      "Path: atm.editConf.pvcTable.frameRelay.dlciTable.ip.nat"
   ::= {er1646v2ATMFwCfgFrDlciEntry 52101120}

er1646v2ATMFwCfgFrDlciIpPimMode OBJECT-TYPE
   SYNTAX      INTEGER
               {
               disabled (0),
               sparse (1),
               passive (2)
               }
   MAX-ACCESS  read-write
   STATUS      current
   DESCRIPTION
      "Path: atm.editConf.pvcTable.frameRelay.dlciTable.ip.pim.mode

       Possibilities:
               disabled   (0)
               sparse   (1)
               passive   (2)"
   ::= {er1646v2ATMFwCfgFrDlciEntry 53346560}

er1646v2ATMFwCfgFrDlciIpPimDrPriority OBJECT-TYPE
   SYNTAX      Counter32
   MAX-ACCESS  read-write
   STATUS      current
   DESCRIPTION
      "Path: atm.editConf.pvcTable.frameRelay.dlciTable.ip.pim.drPriority

       32 bit unsigned wrappable counter."
   ::= {er1646v2ATMFwCfgFrDlciEntry 53346816}

er1646v2ATMFwCfgFrDlciIpPimHelloTime OBJECT-TYPE
   SYNTAX      TimeTicks
   MAX-ACCESS  read-write
   STATUS      current
   DESCRIPTION
      "Path: atm.editConf.pvcTable.frameRelay.dlciTable.ip.pim.helloTime

       Time in centi-second."
   ::= {er1646v2ATMFwCfgFrDlciEntry 53347072}

er1646v2ATMFwCfgFrDlciIpPimPropagationDelay OBJECT-TYPE
   SYNTAX      TimeTicks
   MAX-ACCESS  read-write
   STATUS      current
   DESCRIPTION
      "Path: atm.editConf.pvcTable.frameRelay.dlciTable.ip.pim.propagationDelay

       Time in centi-second."
   ::= {er1646v2ATMFwCfgFrDlciEntry 53347328}

er1646v2ATMFwCfgFrDlciIpPimOverrideInterval OBJECT-TYPE
   SYNTAX      TimeTicks
   MAX-ACCESS  read-write
   STATUS      current
   DESCRIPTION
      "Path: atm.editConf.pvcTable.frameRelay.dlciTable.ip.pim.overrideInterval

       Time in centi-second."
   ::= {er1646v2ATMFwCfgFrDlciEntry 53347584}

er1646v2ATMFwCfgFrDlciIpPimBsrBorder OBJECT-TYPE
   SYNTAX      INTEGER
               {
               disabled (0),
               enabled (1)
               }
   MAX-ACCESS  read-write
   STATUS      current
   DESCRIPTION
      "Path: atm.editConf.pvcTable.frameRelay.dlciTable.ip.pim.bsrBorder

       Possibilities:
               disabled   (0)
               enabled   (1)"
   ::= {er1646v2ATMFwCfgFrDlciEntry 53347840}

er1646v2ATMFwCfgFrDlciIpPimTtlThreshold OBJECT-TYPE
   SYNTAX      Integer32
   MAX-ACCESS  read-write
   STATUS      current
   DESCRIPTION
      "Path: atm.editConf.pvcTable.frameRelay.dlciTable.ip.pim.ttlThreshold"
   ::= {er1646v2ATMFwCfgFrDlciEntry 53348096}

er1646v2ATMFwCfgFrDlciIpIMNetworkUnreachable OBJECT-TYPE
   SYNTAX      INTEGER
               {
               disabled (0),
               enabled (1)
               }
   MAX-ACCESS  read-write
   STATUS      current
   DESCRIPTION
      "Path: atm.editConf.pvcTable.frameRelay.dlciTable.ip.icmpMessages.networkUnreachable

       Possibilities:
               disabled   (0)
               enabled   (1)"
   ::= {er1646v2ATMFwCfgFrDlciEntry 53412096}

er1646v2ATMFwCfgFrDlciIpIMHostUnreachable OBJECT-TYPE
   SYNTAX      INTEGER
               {
               disabled (0),
               enabled (1)
               }
   MAX-ACCESS  read-write
   STATUS      current
   DESCRIPTION
      "Path: atm.editConf.pvcTable.frameRelay.dlciTable.ip.icmpMessages.hostUnreachable

       Possibilities:
               disabled   (0)
               enabled   (1)"
   ::= {er1646v2ATMFwCfgFrDlciEntry 53412352}

er1646v2ATMFwCfgFrDlciIpIMProtocolUnreachable OBJECT-TYPE
   SYNTAX      INTEGER
               {
               disabled (0),
               enabled (1)
               }
   MAX-ACCESS  read-write
   STATUS      current
   DESCRIPTION
      "Path: atm.editConf.pvcTable.frameRelay.dlciTable.ip.icmpMessages.protocolUnreachable

       Possibilities:
               disabled   (0)
               enabled   (1)"
   ::= {er1646v2ATMFwCfgFrDlciEntry 53412608}

er1646v2ATMFwCfgFrDlciIpIMPortUnreachable OBJECT-TYPE
   SYNTAX      INTEGER
               {
               disabled (0),
               enabled (1)
               }
   MAX-ACCESS  read-write
   STATUS      current
   DESCRIPTION
      "Path: atm.editConf.pvcTable.frameRelay.dlciTable.ip.icmpMessages.portUnreachable

       Possibilities:
               disabled   (0)
               enabled   (1)"
   ::= {er1646v2ATMFwCfgFrDlciEntry 53412864}

er1646v2ATMFwCfgFrDlciIpIMMtuExceeded OBJECT-TYPE
   SYNTAX      INTEGER
               {
               disabled (0),
               enabled (1)
               }
   MAX-ACCESS  read-write
   STATUS      current
   DESCRIPTION
      "Path: atm.editConf.pvcTable.frameRelay.dlciTable.ip.icmpMessages.mtuExceeded

       Possibilities:
               disabled   (0)
               enabled   (1)"
   ::= {er1646v2ATMFwCfgFrDlciEntry 53413120}

er1646v2ATMFwCfgFrDlciIpIMAdminProhibited OBJECT-TYPE
   SYNTAX      INTEGER
               {
               disabled (0),
               enabled (1)
               }
   MAX-ACCESS  read-write
   STATUS      current
   DESCRIPTION
      "Path: atm.editConf.pvcTable.frameRelay.dlciTable.ip.icmpMessages.adminProhibited

       Possibilities:
               disabled   (0)
               enabled   (1)"
   ::= {er1646v2ATMFwCfgFrDlciEntry 53413376}

er1646v2ATMFwCfgFrDlciIpIMTtlExceeded OBJECT-TYPE
   SYNTAX      INTEGER
               {
               disabled (0),
               enabled (1)
               }
   MAX-ACCESS  read-write
   STATUS      current
   DESCRIPTION
      "Path: atm.editConf.pvcTable.frameRelay.dlciTable.ip.icmpMessages.ttlExceeded

       Possibilities:
               disabled   (0)
               enabled   (1)"
   ::= {er1646v2ATMFwCfgFrDlciEntry 53413632}

er1646v2ATMFwCfgFrDlciIpIMRedirect OBJECT-TYPE
   SYNTAX      INTEGER
               {
               disabled (0),
               enabled (1)
               }
   MAX-ACCESS  read-write
   STATUS      current
   DESCRIPTION
      "Path: atm.editConf.pvcTable.frameRelay.dlciTable.ip.icmpMessages.redirect

       Possibilities:
               disabled   (0)
               enabled   (1)"
   ::= {er1646v2ATMFwCfgFrDlciEntry 53413888}

er1646v2ATMFwCfgFrDlciBridgingAccList OBJECT-TYPE
   SYNTAX      DisplayString
   MAX-ACCESS  read-write
   STATUS      current
   DESCRIPTION
      "Path: atm.editConf.pvcTable.frameRelay.dlciTable.bridging.accessList"
   ::= {er1646v2ATMFwCfgFrDlciEntry 453246976}

er1646v2ATMFwCfgFrDlciBridgingInACL OBJECT-TYPE
   SYNTAX      DisplayString
   MAX-ACCESS  read-write
   STATUS      current
   DESCRIPTION
      "Path: atm.editConf.pvcTable.frameRelay.dlciTable.bridging.inAccessList"
   ::= {er1646v2ATMFwCfgFrDlciEntry 456916992}

er1646v2ATMFwCfgFrDlciBridgingTp OBJECT-TYPE
   SYNTAX      DisplayString
   MAX-ACCESS  read-write
   STATUS      current
   DESCRIPTION
      "Path: atm.editConf.pvcTable.frameRelay.dlciTable.bridging.trafficPolicy"
   ::= {er1646v2ATMFwCfgFrDlciEntry 454295552}

er1646v2ATMFwCfgFrDlciBridgingBrGrp OBJECT-TYPE
   SYNTAX      DisplayString
   MAX-ACCESS  read-write
   STATUS      current
   DESCRIPTION
      "Path: atm.editConf.pvcTable.frameRelay.dlciTable.bridging.bridgeGroup"
   ::= {er1646v2ATMFwCfgFrDlciEntry 454819840}

er1646v2ATMFwCfgFrDlciBridgingLimBC OBJECT-TYPE
   SYNTAX      INTEGER
               {
               disabled (0),
               enabled (1)
               }
   MAX-ACCESS  read-write
   STATUS      current
   DESCRIPTION
      "Path: atm.editConf.pvcTable.frameRelay.dlciTable.bridging.limitBroadcasts

       Possibilities:
               disabled   (0)
               enabled   (1)"
   ::= {er1646v2ATMFwCfgFrDlciEntry 455081984}

er1646v2ATMFwCfgFrDlciBridgingPrivateMode OBJECT-TYPE
   SYNTAX      INTEGER
               {
               disabled (0),
               enabled (1)
               }
   MAX-ACCESS  read-write
   STATUS      current
   DESCRIPTION
      "Path: atm.editConf.pvcTable.frameRelay.dlciTable.bridging.privateMode

       Possibilities:
               disabled   (0)
               enabled   (1)"
   ::= {er1646v2ATMFwCfgFrDlciEntry 459538432}

er1646v2ATMFwCfgFrDlciBridgingLearning OBJECT-TYPE
   SYNTAX      INTEGER
               {
               disabled (0),
               enabled (1)
               }
   MAX-ACCESS  read-write
   STATUS      current
   DESCRIPTION
      "Path: atm.editConf.pvcTable.frameRelay.dlciTable.bridging.learning

       Possibilities:
               disabled   (0)
               enabled   (1)"
   ::= {er1646v2ATMFwCfgFrDlciEntry 456130560}

er1646v2ATMFwCfgFrDlciBridgingMaxCacheSize OBJECT-TYPE
   SYNTAX      INTEGER
               {
               unlimited (0)
               }
   MAX-ACCESS  read-write
   STATUS      current
   DESCRIPTION
      "Path: atm.editConf.pvcTable.frameRelay.dlciTable.bridging.maxCacheSize

       Possibilities:
               unlimited   (0)"
   ::= {er1646v2ATMFwCfgFrDlciEntry 456392704}

er1646v2ATMFwCfgFrDlciBridgingRelearnDropOnRelearn OBJECT-TYPE
   SYNTAX      INTEGER
               {
               disabled (0),
               enabled (1)
               }
   MAX-ACCESS  read-write
   STATUS      current
   DESCRIPTION
      "Path: atm.editConf.pvcTable.frameRelay.dlciTable.bridging.relearn.dropOnRelearn

       Possibilities:
               disabled   (0)
               enabled   (1)"
   ::= {er1646v2ATMFwCfgFrDlciEntry 456655872}

er1646v2ATMFwCfgFrDlciBridgingRelearnShutdownThreshold OBJECT-TYPE
   SYNTAX      Integer32
   MAX-ACCESS  read-write
   STATUS      current
   DESCRIPTION
      "Path: atm.editConf.pvcTable.frameRelay.dlciTable.bridging.relearn.shutdownThreshold"
   ::= {er1646v2ATMFwCfgFrDlciEntry 456656896}

er1646v2ATMFwCfgFrDlciBridgingRelearnShutdownTime OBJECT-TYPE
   SYNTAX      TimeTicks
   MAX-ACCESS  read-write
   STATUS      current
   DESCRIPTION
      "Path: atm.editConf.pvcTable.frameRelay.dlciTable.bridging.relearn.shutdownTime

       Time in centi-second."
   ::= {er1646v2ATMFwCfgFrDlciEntry 456657920}

er1646v2ATMFwCfgFrDlciBridgingRelearnLoopDetection OBJECT-TYPE
   SYNTAX      INTEGER
               {
               disabled (0),
               passive (1),
               active (2)
               }
   MAX-ACCESS  read-write
   STATUS      current
   DESCRIPTION
      "Path: atm.editConf.pvcTable.frameRelay.dlciTable.bridging.relearn.loopDetection

       Possibilities:
               disabled   (0)
               passive   (1)
               active   (2)"
   ::= {er1646v2ATMFwCfgFrDlciEntry 456658944}

er1646v2ATMFwCfgFrDlciBridgingRelearnLoopDetectionInterval OBJECT-TYPE
   SYNTAX      TimeTicks
   MAX-ACCESS  read-write
   STATUS      current
   DESCRIPTION
      "Path: atm.editConf.pvcTable.frameRelay.dlciTable.bridging.relearn.loopDetectionInterval

       Time in centi-second."
   ::= {er1646v2ATMFwCfgFrDlciEntry 456659968}

er1646v2ATMFwCfgFrDlciBridgingVlanMemberShip OBJECT-TYPE
   SYNTAX      INTEGER
               {
               all (0),
               none (1),
               grouped (2)
               }
   MAX-ACCESS  read-write
   STATUS      current
   DESCRIPTION
      "Path: atm.editConf.pvcTable.frameRelay.dlciTable.bridging.vlanMemberShip

       Possibilities:
               all   (0)
               none   (1)
               grouped   (2)"
   ::= {er1646v2ATMFwCfgFrDlciEntry 457965568}

er1646v2ATMFwCfgFrDlciBridgingVlTUntaggedAction OBJECT-TYPE
   SYNTAX      INTEGER
               {
               discard (0),
               accept (1),
               tag (2)
               }
   MAX-ACCESS  read-write
   STATUS      current
   DESCRIPTION
      "Path: atm.editConf.pvcTable.frameRelay.dlciTable.bridging.vlanTagging.untagged.action

       Possibilities:
               discard   (0)
               accept   (1)
               tag   (2)"
   ::= {er1646v2ATMFwCfgFrDlciEntry 459055104}

er1646v2ATMFwCfgFrDlciBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.frameRelay.dlciTable.bridging.vlanTagging.untagged.tagInfo.tpid

       Possibilities:
               dot1Q   (33024)
               dot1ad   (34984)
               0x9100   (37120)
               0x9200   (37376)
               0x9300   (37632)"
   ::= {er1646v2ATMFwCfgFrDlciEntry 459059712}

er1646v2ATMFwCfgFrDlciBridgingVlTUntaggedTagInfoVid OBJECT-TYPE
   SYNTAX      Integer32
   MAX-ACCESS  read-write
   STATUS      current
   DESCRIPTION
      "Path: atm.editConf.pvcTable.frameRelay.dlciTable.bridging.vlanTagging.untagged.tagInfo.vid"
   ::= {er1646v2ATMFwCfgFrDlciEntry 459060224}

er1646v2ATMFwCfgFrDlciBridgingVlTUnknownVlansAction OBJECT-TYPE
   SYNTAX      INTEGER
               {
               discard (0),
               accept (1),
               tag (2)
               }
   MAX-ACCESS  read-write
   STATUS      current
   DESCRIPTION
      "Path: atm.editConf.pvcTable.frameRelay.dlciTable.bridging.vlanTagging.unknownVlans.action

       Possibilities:
               discard   (0)
               accept   (1)
               tag   (2)"
   ::= {er1646v2ATMFwCfgFrDlciEntry 459120640}

er1646v2ATMFwCfgFrDlciBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.frameRelay.dlciTable.bridging.vlanTagging.unknownVlans.tagInfo.tpid

       Possibilities:
               dot1Q   (33024)
               dot1ad   (34984)
               0x9100   (37120)
               0x9200   (37376)
               0x9300   (37632)"
   ::= {er1646v2ATMFwCfgFrDlciEntry 459125248}

er1646v2ATMFwCfgFrDlciBridgingVlTUnknownVlansTagInfoVid OBJECT-TYPE
   SYNTAX      Integer32
   MAX-ACCESS  read-write
   STATUS      current
   DESCRIPTION
      "Path: atm.editConf.pvcTable.frameRelay.dlciTable.bridging.vlanTagging.unknownVlans.tagInfo.vid"
   ::= {er1646v2ATMFwCfgFrDlciEntry 459125760}

er1646v2ATMFwCfgFrDlciBridgingDot1adType OBJECT-TYPE
   SYNTAX      INTEGER
               {
               slOPTg (0),
               cPort (4),
               sPort (1),
               nni (2)
               }
   MAX-ACCESS  read-write
   STATUS      current
   DESCRIPTION
      "Path: atm.editConf.pvcTable.frameRelay.dlciTable.bridging.dot1ad.type

       Possibilities:
               <OPT>   (0)
               cPort   (4)
               sPort   (1)
               nni   (2)"
   ::= {er1646v2ATMFwCfgFrDlciEntry 460850176}

er1646v2ATMFwCfgFrDlciBridgingPriority OBJECT-TYPE
   SYNTAX      Integer32
   MAX-ACCESS  read-write
   STATUS      current
   DESCRIPTION
      "Path: atm.editConf.pvcTable.frameRelay.dlciTable.bridging.priority"
   ::= {er1646v2ATMFwCfgFrDlciEntry 453509120}

er1646v2ATMFwCfgFrDlciBridgingPathCost OBJECT-TYPE
   SYNTAX      Integer32
   MAX-ACCESS  read-write
   STATUS      current
   DESCRIPTION
      "Path: atm.editConf.pvcTable.frameRelay.dlciTable.bridging.pathCost"
   ::= {er1646v2ATMFwCfgFrDlciEntry 453771264}

er1646v2ATMFwCfgFrDlciBridgingInternalPathCost OBJECT-TYPE
   SYNTAX      Integer32
   MAX-ACCESS  read-write
   STATUS      current
   DESCRIPTION
      "Path: atm.editConf.pvcTable.frameRelay.dlciTable.bridging.internalPathCost"
   ::= {er1646v2ATMFwCfgFrDlciEntry 457703424}

er1646v2ATMFwCfgFrDlciBridgingTCD OBJECT-TYPE
   SYNTAX      INTEGER
               {
               disabled (0),
               enabled (1)
               }
   MAX-ACCESS  read-write
   STATUS      current
   DESCRIPTION
      "Path: atm.editConf.pvcTable.frameRelay.dlciTable.bridging.topologyChangeDetection

       Possibilities:
               disabled   (0)
               enabled   (1)"
   ::= {er1646v2ATMFwCfgFrDlciEntry 454033408}

er1646v2ATMFwCfgFrDlciBridgingRestrictedRole OBJECT-TYPE
   SYNTAX      INTEGER
               {
               disabled (0),
               enabled (1)
               }
   MAX-ACCESS  read-write
   STATUS      current
   DESCRIPTION
      "Path: atm.editConf.pvcTable.frameRelay.dlciTable.bridging.restrictedRole

       Possibilities:
               disabled   (0)
               enabled   (1)"
   ::= {er1646v2ATMFwCfgFrDlciEntry 458227712}

er1646v2ATMFwCfgFrDlciBridgingAdminEdge OBJECT-TYPE
   SYNTAX      INTEGER
               {
               disabled (0),
               enabled (1)
               }
   MAX-ACCESS  read-write
   STATUS      current
   DESCRIPTION
      "Path: atm.editConf.pvcTable.frameRelay.dlciTable.bridging.adminEdge

       Possibilities:
               disabled   (0)
               enabled   (1)"
   ::= {er1646v2ATMFwCfgFrDlciEntry 457179136}

er1646v2ATMFwCfgFrDlciBridgingOamMacDeviceMac OBJECT-TYPE
   SYNTAX      DisplayString
   MAX-ACCESS  read-write
   STATUS      current
   DESCRIPTION
      "Path: atm.editConf.pvcTable.frameRelay.dlciTable.bridging.ethOam.macAddress.deviceMac"
   ::= {er1646v2ATMFwCfgFrDlciEntry 458506496}

er1646v2ATMFwCfgFrDlciBridgingOamMacUserMac OBJECT-TYPE
   SYNTAX      OCTET STRING
   MAX-ACCESS  read-write
   STATUS      current
   DESCRIPTION
      "Path: atm.editConf.pvcTable.frameRelay.dlciTable.bridging.ethOam.macAddress.userMac

       MAC address."
   ::= {er1646v2ATMFwCfgFrDlciEntry 458506368}

er1646v2ATMFwCfgFrDlciBridgingOamMacBridgeMac OBJECT-TYPE
   SYNTAX      DisplayString
   MAX-ACCESS  read-write
   STATUS      current
   DESCRIPTION
      "Path: atm.editConf.pvcTable.frameRelay.dlciTable.bridging.ethOam.macAddress.bridgeMac"
   ::= {er1646v2ATMFwCfgFrDlciEntry 458506432}

er1646v2ATMFwCfgFrDlciBridgingMgmtInline OBJECT-TYPE
   SYNTAX      INTEGER
               {
               disabled (0),
               enabled (1)
               }
   MAX-ACCESS  read-write
   STATUS      current
   DESCRIPTION
      "Path: atm.editConf.pvcTable.frameRelay.dlciTable.bridging.mgmtInline

       Possibilities:
               disabled   (0)
               enabled   (1)"
   ::= {er1646v2ATMFwCfgFrDlciEntry 458752000}

er1646v2ATMFwCfgFrDlciBridgingL2ptMode OBJECT-TYPE
   SYNTAX      INTEGER
               {
               disabled (0),
               enabled (1)
               }
   MAX-ACCESS  read-write
   STATUS      current
   DESCRIPTION
      "Path: atm.editConf.pvcTable.frameRelay.dlciTable.bridging.l2ProtTunnel.mode

       Possibilities:
               disabled   (0)
               enabled   (1)"
   ::= {er1646v2ATMFwCfgFrDlciEntry 459292672}

er1646v2ATMFwCfgFrDlciBridgingL2ptProtocols OBJECT-TYPE
   SYNTAX      Integer32
   MAX-ACCESS  read-write
   STATUS      current
   DESCRIPTION
      "Path: atm.editConf.pvcTable.frameRelay.dlciTable.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2ATMFwCfgFrDlciEntry 459309056}

er1646v2ATMFwCfgFrDlciBridgingL2ptDestMac OBJECT-TYPE
   SYNTAX      OCTET STRING
   MAX-ACCESS  read-write
   STATUS      current
   DESCRIPTION
      "Path: atm.editConf.pvcTable.frameRelay.dlciTable.bridging.l2ProtTunnel.destinationMac

       MAC address."
   ::= {er1646v2ATMFwCfgFrDlciEntry 459325440}

er1646v2ATMFwCfgFrDlciBridgingL2ptCos OBJECT-TYPE
   SYNTAX      INTEGER
               {
               unchanged (255)
               }
   MAX-ACCESS  read-write
   STATUS      current
   DESCRIPTION
      "Path: atm.editConf.pvcTable.frameRelay.dlciTable.bridging.l2ProtTunnel.cos

       Possibilities:
               unchanged   (255)"
   ::= {er1646v2ATMFwCfgFrDlciEntry 459341824}

er1646v2ATMFwCfgFrDlciBridgingL2ptDropThrStp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.stp

       unit name = packets/sec

       Possibilities:
               unlimited   (0)"
   ::= {er1646v2ATMFwCfgFrDlciEntry 459358272}

er1646v2ATMFwCfgFrDlciBridgingL2ptDropThrLldp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.lldp

       unit name = packets/sec

       Possibilities:
               unlimited   (0)"
   ::= {er1646v2ATMFwCfgFrDlciEntry 459358336}

er1646v2ATMFwCfgFrDlciBridgingL2ptDropThrOam OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.oam

       unit name = packets/sec

       Possibilities:
               unlimited   (0)"
   ::= {er1646v2ATMFwCfgFrDlciEntry 459358400}

er1646v2ATMFwCfgFrDlciBridgingL2ptDropThrCdp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.cdp

       unit name = packets/sec

       Possibilities:
               unlimited   (0)"
   ::= {er1646v2ATMFwCfgFrDlciEntry 459358464}

er1646v2ATMFwCfgFrDlciBridgingL2ptDropThrVtp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.vtp

       unit name = packets/sec

       Possibilities:
               unlimited   (0)"
   ::= {er1646v2ATMFwCfgFrDlciEntry 459358528}

er1646v2ATMFwCfgFrDlciBridgingL2ptDropThrLacp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.lacp

       unit name = packets/sec

       Possibilities:
               unlimited   (0)"
   ::= {er1646v2ATMFwCfgFrDlciEntry 459358592}

er1646v2ATMFwCfgFrDlciBridgingL2ptDropThrEfmOam OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.efmOam

       unit name = packets/sec

       Possibilities:
               unlimited   (0)"
   ::= {er1646v2ATMFwCfgFrDlciEntry 459358656}

er1646v2ATMFwCfgFrDlciBridgingL2ptDropThrPvst OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.pvst

       unit name = packets/sec

       Possibilities:
               unlimited   (0)"
   ::= {er1646v2ATMFwCfgFrDlciEntry 459358720}

er1646v2ATMFwCfgFrDlciBridgingL2ptDropThrMmrp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.mmrp

       unit name = packets/sec

       Possibilities:
               unlimited   (0)"
   ::= {er1646v2ATMFwCfgFrDlciEntry 459358784}

er1646v2ATMFwCfgFrDlciBridgingL2ptDropThrMvrp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.mvrp

       unit name = packets/sec

       Possibilities:
               unlimited   (0)"
   ::= {er1646v2ATMFwCfgFrDlciEntry 459358848}

er1646v2ATMFwCfgFrDlciBridgingL2ptDropThrGvrp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.gvrp

       unit name = packets/sec

       Possibilities:
               unlimited   (0)"
   ::= {er1646v2ATMFwCfgFrDlciEntry 459358912}

er1646v2ATMFwCfgFrDlciBridgingL2ptDropThrGmrp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.gmrp

       unit name = packets/sec

       Possibilities:
               unlimited   (0)"
   ::= {er1646v2ATMFwCfgFrDlciEntry 459358976}

er1646v2ATMFwCfgFrDlciBridgingL2ptDropThrDtp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.dtp

       unit name = packets/sec

       Possibilities:
               unlimited   (0)"
   ::= {er1646v2ATMFwCfgFrDlciEntry 459359040}

er1646v2ATMFwCfgFrDlciBridgingL2ptDropThrPagp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.pagp

       unit name = packets/sec

       Possibilities:
               unlimited   (0)"
   ::= {er1646v2ATMFwCfgFrDlciEntry 459359104}

er1646v2ATMFwCfgFrDlciBridgingL2ptDropThrUdld OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.udld

       unit name = packets/sec

       Possibilities:
               unlimited   (0)"
   ::= {er1646v2ATMFwCfgFrDlciEntry 459359168}

er1646v2ATMFwCfgFrDlciFrDlci OBJECT-TYPE
   SYNTAX      Integer32
   MAX-ACCESS  read-write
   STATUS      current
   DESCRIPTION
      "Path: atm.editConf.pvcTable.frameRelay.dlciTable.frameRelay.dlci"
   ::= {er1646v2ATMFwCfgFrDlciEntry 218169344}

er1646v2ATMFwCfgFrDlciFrCir OBJECT-TYPE
   SYNTAX      Integer32
   MAX-ACCESS  read-write
   STATUS      current
   DESCRIPTION
      "Path: atm.editConf.pvcTable.frameRelay.dlciTable.frameRelay.cir"
   ::= {er1646v2ATMFwCfgFrDlciEntry 218234880}

er1646v2ATMFwCfgFrDlciFrOverhead OBJECT-TYPE
   SYNTAX      Integer32
   MAX-ACCESS  read-write
   STATUS      current
   DESCRIPTION
      "Path: atm.editConf.pvcTable.frameRelay.dlciTable.frameRelay.overhead"
   ::= {er1646v2ATMFwCfgFrDlciEntry 218890240}

er1646v2ATMFwCfgFrDlciFrTc OBJECT-TYPE
   SYNTAX      Integer32
   MAX-ACCESS  read-write
   STATUS      current
   DESCRIPTION
      "Path: atm.editConf.pvcTable.frameRelay.dlciTable.frameRelay.tc"
   ::= {er1646v2ATMFwCfgFrDlciEntry 218759168}

er1646v2ATMFwCfgFrDlciFrSlidingWindow OBJECT-TYPE
   SYNTAX      INTEGER
               {
               disabled (0),
               enabled (1)
               }
   MAX-ACCESS  read-write
   STATUS      current
   DESCRIPTION
      "Path: atm.editConf.pvcTable.frameRelay.dlciTable.frameRelay.slidingWindow

       Possibilities:
               disabled   (0)
               enabled   (1)"
   ::= {er1646v2ATMFwCfgFrDlciEntry 218824704}

er1646v2ATMFwCfgFrDlciFrDeBitSet OBJECT-TYPE
   SYNTAX      INTEGER
               {
               disabled (0),
               enabled (1)
               }
   MAX-ACCESS  read-write
   STATUS      current
   DESCRIPTION
      "Path: atm.editConf.pvcTable.frameRelay.dlciTable.frameRelay.deBitSet

       Possibilities:
               disabled   (0)
               enabled   (1)"
   ::= {er1646v2ATMFwCfgFrDlciEntry 218431488}

er1646v2ATMFwCfgFrDlciFrDefaultQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: atm.editConf.pvcTable.frameRelay.dlciTable.frameRelay.defaultQueue

       Possibilities:
               queue1   (0)
               queue2   (1)
               queue3   (2)
               queue4   (3)
               queue5   (4)
               lowDelayQueue   (5)
               lowDelay2Queue   (6)
               systemQueue   (7)"
   ::= {er1646v2ATMFwCfgFrDlciEntry 218628096}

er1646v2ATMFwCfgFrDlciFrRxCir OBJECT-TYPE
   SYNTAX      Integer32
   MAX-ACCESS  read-write
   STATUS      current
   DESCRIPTION
      "Path: atm.editConf.pvcTable.frameRelay.dlciTable.frameRelay.rxCir"
   ::= {er1646v2ATMFwCfgFrDlciEntry 218497024}

er1646v2ATMFwCfgFrDlciFrRxExcess OBJECT-TYPE
   SYNTAX      INTEGER
               {
               discard (0),
               setDeBit (1),
               ignore (2)
               }
   MAX-ACCESS  read-write
   STATUS      current
   DESCRIPTION
      "Path: atm.editConf.pvcTable.frameRelay.dlciTable.frameRelay.rxExcess

       Possibilities:
               discard   (0)
               setDeBit   (1)
               ignore   (2)"
   ::= {er1646v2ATMFwCfgFrDlciEntry 218562560}

er1646v2ATMFwCfgFrDlciFrFragEMode OBJECT-TYPE
   SYNTAX      INTEGER
               {
               disabled (0),
               enabled (1)
               }
   MAX-ACCESS  read-write
   STATUS      current
   DESCRIPTION
      "Path: atm.editConf.pvcTable.frameRelay.dlciTable.frameRelay.fragmentation.endToEndFormat

       Possibilities:
               disabled   (0)
               enabled   (1)"
   ::= {er1646v2ATMFwCfgFrDlciEntry 218366208}

er1646v2ATMFwCfgFrDlciIpH OBJECT-TYPE
   SYNTAX      SEQUENCE OF Er1646v2ATMFwCfgFrDlciIpHEntry
   MAX-ACCESS  not-accessible
   STATUS      current
   DESCRIPTION
      ""
   ::= {er1646v2ATMFwCfg 689975536}

er1646v2ATMFwCfgFrDlciIpHEntry OBJECT-TYPE
   SYNTAX      Er1646v2ATMFwCfgFrDlciIpHEntry
   MAX-ACCESS  not-accessible
   STATUS      current
   DESCRIPTION
      ""
   INDEX      { er1646v2ATMFwCfgFrDlciIpHGlobalIx,
                er1646v2ATMFwCfgTableIx,
                er1646v2ATMFwCfgFrDlciTableIx,
                er1646v2ATMFwCfgFrDlciIpHTableIx }
   ::= {er1646v2ATMFwCfgFrDlciIpH 1}

Er1646v2ATMFwCfgFrDlciIpHEntry ::=
   SEQUENCE
      {
      er1646v2ATMFwCfgFrDlciIpHActions
         VariableLengthTableActions,
      er1646v2ATMFwCfgFrDlciIpHGlobalIx
         GlobalIndex,
      er1646v2ATMFwCfgFrDlciIpHTableIx
         TableIndex,
      er1646v2ATMFwCfgFrDlciIpHAddress
         IpAddress,
      er1646v2ATMFwCfgFrDlciIpHDhcpRelayOptionSubscriberId
         DisplayString
      }

er1646v2ATMFwCfgFrDlciIpHActions OBJECT-TYPE
   SYNTAX      VariableLengthTableActions
   MAX-ACCESS  read-write
   STATUS      current
   DESCRIPTION
      "By way of this field, some manipulations
       on this table may be performed."
   ::= {er1646v2ATMFwCfgFrDlciIpHEntry 2}

er1646v2ATMFwCfgFrDlciIpHGlobalIx OBJECT-TYPE
   SYNTAX      GlobalIndex
   MAX-ACCESS  not-accessible
   STATUS      current
   DESCRIPTION
      "The value of the tlsCntTreeGlobalIndex of the MANAGED OBJECT."
   ::= {er1646v2ATMFwCfgFrDlciIpHEntry 10}

er1646v2ATMFwCfgFrDlciIpHTableIx OBJECT-TYPE
   SYNTAX      TableIndex
   MAX-ACCESS  not-accessible
   STATUS      current
   DESCRIPTION
      ""
   ::= {er1646v2ATMFwCfgFrDlciIpHEntry 11}

er1646v2ATMFwCfgFrDlciIpHAddress OBJECT-TYPE
   SYNTAX      IpAddress
   MAX-ACCESS  read-write
   STATUS      current
   DESCRIPTION
      "Path: atm.editConf.pvcTable.frameRelay.dlciTable.ip.helpers.address"
   ::= {er1646v2ATMFwCfgFrDlciIpHEntry 16777216}

er1646v2ATMFwCfgFrDlciIpHDhcpRelayOptionSubscriberId OBJECT-TYPE
   SYNTAX      DisplayString
   MAX-ACCESS  read-write
   STATUS      current
   DESCRIPTION
      "Path: atm.editConf.pvcTable.frameRelay.dlciTable.ip.helpers.dhcpRelayOption.subscriberId"
   ::= {er1646v2ATMFwCfgFrDlciIpHEntry 33947648}

er1646v2ATMFwCfgFrDlciBridgingVlTVlans OBJECT-TYPE
   SYNTAX      SEQUENCE OF Er1646v2ATMFwCfgFrDlciBridgingVlTVlansEntry
   MAX-ACCESS  not-accessible
   STATUS      current
   DESCRIPTION
      ""
   ::= {er1646v2ATMFwCfg 690075088}

er1646v2ATMFwCfgFrDlciBridgingVlTVlansEntry OBJECT-TYPE
   SYNTAX      Er1646v2ATMFwCfgFrDlciBridgingVlTVlansEntry
   MAX-ACCESS  not-accessible
   STATUS      current
   DESCRIPTION
      ""
   INDEX      { er1646v2ATMFwCfgFrDlciBridgingVlTVlansGlobalIx,
                er1646v2ATMFwCfgTableIx,
                er1646v2ATMFwCfgFrDlciTableIx,
                er1646v2ATMFwCfgFrDlciBridgingVlTVlansTableIx }
   ::= {er1646v2ATMFwCfgFrDlciBridgingVlTVlans 1}

Er1646v2ATMFwCfgFrDlciBridgingVlTVlansEntry ::=
   SEQUENCE
      {
      er1646v2ATMFwCfgFrDlciBridgingVlTVlansActions
         VariableLengthTableActions,
      er1646v2ATMFwCfgFrDlciBridgingVlTVlansGlobalIx
         GlobalIndex,
      er1646v2ATMFwCfgFrDlciBridgingVlTVlansTableIx
         TableIndex,
      er1646v2ATMFwCfgFrDlciBridgingVlTVlansVid
         Integer32,
      er1646v2ATMFwCfgFrDlciBridgingVlTVlansEndVid
         Integer32,
      er1646v2ATMFwCfgFrDlciBridgingVlTVlansAction
         INTEGER,
      er1646v2ATMFwCfgFrDlciBridgingVlTVlansTagInfoTpid
         INTEGER,
      er1646v2ATMFwCfgFrDlciBridgingVlTVlansTagInfoVid
         Integer32
      }

er1646v2ATMFwCfgFrDlciBridgingVlTVlansActions OBJECT-TYPE
   SYNTAX      VariableLengthTableActions
   MAX-ACCESS  read-write
   STATUS      current
   DESCRIPTION
      "By way of this field, some manipulations
       on this table may be performed."
   ::= {er1646v2ATMFwCfgFrDlciBridgingVlTVlansEntry 2}

er1646v2ATMFwCfgFrDlciBridgingVlTVlansGlobalIx OBJECT-TYPE
   SYNTAX      GlobalIndex
   MAX-ACCESS  not-accessible
   STATUS      current
   DESCRIPTION
      "The value of the tlsCntTreeGlobalIndex of the MANAGED OBJECT."
   ::= {er1646v2ATMFwCfgFrDlciBridgingVlTVlansEntry 10}

er1646v2ATMFwCfgFrDlciBridgingVlTVlansTableIx OBJECT-TYPE
   SYNTAX      TableIndex
   MAX-ACCESS  not-accessible
   STATUS      current
   DESCRIPTION
      ""
   ::= {er1646v2ATMFwCfgFrDlciBridgingVlTVlansEntry 11}

er1646v2ATMFwCfgFrDlciBridgingVlTVlansVid OBJECT-TYPE
   SYNTAX      Integer32
   MAX-ACCESS  read-write
   STATUS      current
   DESCRIPTION
      "Path: atm.editConf.pvcTable.frameRelay.dlciTable.bridging.vlanTagging.vlans.vid"
   ::= {er1646v2ATMFwCfgFrDlciBridgingVlTVlansEntry 536870912}

er1646v2ATMFwCfgFrDlciBridgingVlTVlansEndVid OBJECT-TYPE
   SYNTAX      Integer32
   MAX-ACCESS  read-write
   STATUS      current
   DESCRIPTION
      "Path: atm.editConf.pvcTable.frameRelay.dlciTable.bridging.vlanTagging.vlans.endVid"
   ::= {er1646v2ATMFwCfgFrDlciBridgingVlTVlansEntry 2147483648}

er1646v2ATMFwCfgFrDlciBridgingVlTVlansAction OBJECT-TYPE
   SYNTAX      INTEGER
               {
               discard (0),
               accept (1),
               tag (2)
               }
   MAX-ACCESS  read-write
   STATUS      current
   DESCRIPTION
      "Path: atm.editConf.pvcTable.frameRelay.dlciTable.bridging.vlanTagging.vlans.action

       Possibilities:
               discard   (0)
               accept   (1)
               tag   (2)"
   ::= {er1646v2ATMFwCfgFrDlciBridgingVlTVlansEntry 1073741824}

er1646v2ATMFwCfgFrDlciBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.frameRelay.dlciTable.bridging.vlanTagging.vlans.tagInfo.tpid

       Possibilities:
               dot1Q   (33024)
               dot1ad   (34984)
               0x9100   (37120)
               0x9200   (37376)
               0x9300   (37632)"
   ::= {er1646v2ATMFwCfgFrDlciBridgingVlTVlansEntry 1677721600}

er1646v2ATMFwCfgFrDlciBridgingVlTVlansTagInfoVid OBJECT-TYPE
   SYNTAX      Integer32
   MAX-ACCESS  read-write
   STATUS      current
   DESCRIPTION
      "Path: atm.editConf.pvcTable.frameRelay.dlciTable.bridging.vlanTagging.vlans.tagInfo.vid"
   ::= {er1646v2ATMFwCfgFrDlciBridgingVlTVlansEntry 1744830464}



sr1646v2ATMFw OBJECT IDENTIFIER ::= {r1646v2ATMFw 14}


sr1646v2ATMFwAtmSync OBJECT IDENTIFIER ::= {sr1646v2ATMFw 91}

sr1646v2ATMFwAtmSyncTable OBJECT-TYPE
   SYNTAX      SEQUENCE OF Sr1646v2ATMFwAtmSyncEntry
   MAX-ACCESS  not-accessible
   STATUS      current
   DESCRIPTION
      ""
   ::= {sr1646v2ATMFwAtmSync 1}

sr1646v2ATMFwAtmSyncEntry OBJECT-TYPE
   SYNTAX      Sr1646v2ATMFwAtmSyncEntry
   MAX-ACCESS  not-accessible
   STATUS      current
   DESCRIPTION
      ""
   INDEX      { sr1646v2ATMFwAtmSyncGlobalIx }
   ::= {sr1646v2ATMFwAtmSyncTable 1}

Sr1646v2ATMFwAtmSyncEntry ::=
   SEQUENCE
      {
      sr1646v2ATMFwAtmSyncGlobalIx
         GlobalIndex,
      sr1646v2ATMFwAtmSyncValue
         INTEGER
      }

sr1646v2ATMFwAtmSyncGlobalIx OBJECT-TYPE
   SYNTAX      GlobalIndex
   MAX-ACCESS  not-accessible
   STATUS      current
   DESCRIPTION
      "The value of the tlsCntTreeGlobalIndex of the MANAGED OBJECT."
   ::= {sr1646v2ATMFwAtmSyncEntry 10}

sr1646v2ATMFwAtmSyncValue OBJECT-TYPE
   SYNTAX      INTEGER
               {
               notSynced (0),
               synced (1)
               }
   MAX-ACCESS  read-only
   STATUS      current
   DESCRIPTION
      "Path: atm.status.atmSync

       Possibilities:
               notSynced   (0)
               synced   (1)"
   ::= {sr1646v2ATMFwAtmSyncEntry 2147483648}


sr1646v2ATMFwVp OBJECT IDENTIFIER ::= {sr1646v2ATMFw 93}

sr1646v2ATMFwVpSSCTable OBJECT-TYPE
   SYNTAX      SEQUENCE OF Sr1646v2ATMFwVpEntry
   MAX-ACCESS  not-accessible
   STATUS      current
   DESCRIPTION
      ""
   ::= {sr1646v2ATMFwVp 1}

sr1646v2ATMFwVpEntry OBJECT-TYPE
   SYNTAX      Sr1646v2ATMFwVpEntry
   MAX-ACCESS  not-accessible
   STATUS      current
   DESCRIPTION
      ""
   INDEX      { sr1646v2ATMFwVpGlobalIx,
                sr1646v2ATMFwVpTableIx }
   ::= {sr1646v2ATMFwVpSSCTable 1}

Sr1646v2ATMFwVpEntry ::=
   SEQUENCE
      {
      sr1646v2ATMFwVpGlobalIx
         GlobalIndex,
      sr1646v2ATMFwVpTableIx
         TableIndex,
      sr1646v2ATMFwVpVpi
         Integer32,
      sr1646v2ATMFwVpIfOperStatus
         INTEGER,
      sr1646v2ATMFwVpOamF4SegOamLB
         INTEGER,
      sr1646v2ATMFwVpOamF4SegOamCC
         INTEGER,
      sr1646v2ATMFwVpOamF4SegOamPMStatus
         INTEGER,
      sr1646v2ATMFwVpOamF4SegOamPMBlockSizeAB
         INTEGER,
      sr1646v2ATMFwVpOamF4SegOamPMBlockSizeBA
         INTEGER,
      sr1646v2ATMFwVpOamF4SegAis
         INTEGER,
      sr1646v2ATMFwVpOamF4SegRdi
         INTEGER,
      sr1646v2ATMFwVpOamF4EteOamLB
         INTEGER,
      sr1646v2ATMFwVpOamF4EteOamCC
         INTEGER,
      sr1646v2ATMFwVpOamF4EteOamPMStatus
         INTEGER,
      sr1646v2ATMFwVpOamF4EteOamPMBlockSizeAB
         INTEGER,
      sr1646v2ATMFwVpOamF4EteOamPMBlockSizeBA
         INTEGER,
      sr1646v2ATMFwVpOamF4EteAis
         INTEGER,
      sr1646v2ATMFwVpOamF4EteRdi
         INTEGER,
      sr1646v2ATMFwVpOamF4SegEP
         INTEGER,
      sr1646v2ATMFwVpOamF4CnxEP
         INTEGER
      }

sr1646v2ATMFwVpGlobalIx OBJECT-TYPE
   SYNTAX      GlobalIndex
   MAX-ACCESS  not-accessible
   STATUS      current
   DESCRIPTION
      "The value of the tlsCntTreeGlobalIndex of the MANAGED OBJECT."
   ::= {sr1646v2ATMFwVpEntry 10}

sr1646v2ATMFwVpTableIx OBJECT-TYPE
   SYNTAX      TableIndex
   MAX-ACCESS  not-accessible
   STATUS      current
   DESCRIPTION
      ""
   ::= {sr1646v2ATMFwVpEntry 11}

sr1646v2ATMFwVpVpi OBJECT-TYPE
   SYNTAX      Integer32
   MAX-ACCESS  read-only
   STATUS      current
   DESCRIPTION
      "Path: atm.status.vp.vpi"
   ::= {sr1646v2ATMFwVpEntry 16777216}

sr1646v2ATMFwVpIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: atm.status.vp.ifOperStatus

       Possibilities:
               up   (1)
               down   (2)
               testing   (3)
               unknown   (4)
               dormant   (5)
               notPresent   (6)
               lowerLayerDown   (7)"
   ::= {sr1646v2ATMFwVpEntry 1795162112}

sr1646v2ATMFwVpOamF4SegOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.segment.oamLB

       Possibilities:
               ready   (0)
               waitActRes   (1)
               waitActCon   (2)
               waitDeactCon   (3)
               active   (4)
               deactivated   (5)"
   ::= {sr1646v2ATMFwVpEntry 33628160}

sr1646v2ATMFwVpOamF4SegOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.segment.oamCC

       Possibilities:
               ready   (0)
               waitActRes   (1)
               waitActCon   (2)
               waitDeactCon   (3)
               active   (4)
               deactivated   (5)"
   ::= {sr1646v2ATMFwVpEntry 33636352}

sr1646v2ATMFwVpOamF4SegOamPMStatus OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.segment.oamPM.status

       Possibilities:
               ready   (0)
               waitActRes   (1)
               waitActCon   (2)
               waitDeactCon   (3)
               active   (4)
               deactivated   (5)"
   ::= {sr1646v2ATMFwVpEntry 33645568}

sr1646v2ATMFwVpOamF4SegOamPMBlockSizeAB OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.vp.oamF4.segment.oamPM.blockSizeAB

       Possibilities:
               128   (0)
               256   (1)
               512   (2)
               1024   (3)
               2048   (4)
               4096   (5)
               8192   (6)
               16384   (7)
               32768   (8)"
   ::= {sr1646v2ATMFwVpEntry 33646592}

sr1646v2ATMFwVpOamF4SegOamPMBlockSizeBA OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.vp.oamF4.segment.oamPM.blockSizeBA

       Possibilities:
               128   (0)
               256   (1)
               512   (2)
               1024   (3)
               2048   (4)
               4096   (5)
               8192   (6)
               16384   (7)
               32768   (8)"
   ::= {sr1646v2ATMFwVpEntry 33647616}

sr1646v2ATMFwVpOamF4SegAis OBJECT-TYPE
   SYNTAX      INTEGER
               {
               inactive (0),
               active (1)
               }
   MAX-ACCESS  read-only
   STATUS      current
   DESCRIPTION
      "Path: atm.status.vp.oamF4.segment.aisState

       Possibilities:
               inactive   (0)
               active   (1)"
   ::= {sr1646v2ATMFwVpEntry 33652736}

sr1646v2ATMFwVpOamF4SegRdi OBJECT-TYPE
   SYNTAX      INTEGER
               {
               inactive (0),
               active (1)
               }
   MAX-ACCESS  read-only
   STATUS      current
   DESCRIPTION
      "Path: atm.status.vp.oamF4.segment.rdiState

       Possibilities:
               inactive   (0)
               active   (1)"
   ::= {sr1646v2ATMFwVpEntry 33660928}

sr1646v2ATMFwVpOamF4EteOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.endToEnd.oamLB

       Possibilities:
               ready   (0)
               waitActRes   (1)
               waitActCon   (2)
               waitDeactCon   (3)
               active   (4)
               deactivated   (5)"
   ::= {sr1646v2ATMFwVpEntry 33693696}

sr1646v2ATMFwVpOamF4EteOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.endToEnd.oamCC

       Possibilities:
               ready   (0)
               waitActRes   (1)
               waitActCon   (2)
               waitDeactCon   (3)
               active   (4)
               deactivated   (5)"
   ::= {sr1646v2ATMFwVpEntry 33701888}

sr1646v2ATMFwVpOamF4EteOamPMStatus OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.endToEnd.oamPM.status

       Possibilities:
               ready   (0)
               waitActRes   (1)
               waitActCon   (2)
               waitDeactCon   (3)
               active   (4)
               deactivated   (5)"
   ::= {sr1646v2ATMFwVpEntry 33711104}

sr1646v2ATMFwVpOamF4EteOamPMBlockSizeAB OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.vp.oamF4.endToEnd.oamPM.blockSizeAB

       Possibilities:
               128   (0)
               256   (1)
               512   (2)
               1024   (3)
               2048   (4)
               4096   (5)
               8192   (6)
               16384   (7)
               32768   (8)"
   ::= {sr1646v2ATMFwVpEntry 33712128}

sr1646v2ATMFwVpOamF4EteOamPMBlockSizeBA OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.vp.oamF4.endToEnd.oamPM.blockSizeBA

       Possibilities:
               128   (0)
               256   (1)
               512   (2)
               1024   (3)
               2048   (4)
               4096   (5)
               8192   (6)
               16384   (7)
               32768   (8)"
   ::= {sr1646v2ATMFwVpEntry 33713152}

sr1646v2ATMFwVpOamF4EteAis OBJECT-TYPE
   SYNTAX      INTEGER
               {
               inactive (0),
               active (1)
               }
   MAX-ACCESS  read-only
   STATUS      current
   DESCRIPTION
      "Path: atm.status.vp.oamF4.endToEnd.aisState

       Possibilities:
               inactive   (0)
               active   (1)"
   ::= {sr1646v2ATMFwVpEntry 33718272}

sr1646v2ATMFwVpOamF4EteRdi OBJECT-TYPE
   SYNTAX      INTEGER
               {
               inactive (0),
               active (1)
               }
   MAX-ACCESS  read-only
   STATUS      current
   DESCRIPTION
      "Path: atm.status.vp.oamF4.endToEnd.rdiState

       Possibilities:
               inactive   (0)
               active   (1)"
   ::= {sr1646v2ATMFwVpEntry 33726464}

sr1646v2ATMFwVpOamF4SegEP OBJECT-TYPE
   SYNTAX      INTEGER
               {
               no (0),
               yes (1)
               }
   MAX-ACCESS  read-only
   STATUS      current
   DESCRIPTION
      "Path: atm.status.vp.oamF4.segmentEndPoint

       Possibilities:
               no   (0)
               yes   (1)"
   ::= {sr1646v2ATMFwVpEntry 33751040}

sr1646v2ATMFwVpOamF4CnxEP OBJECT-TYPE
   SYNTAX      INTEGER
               {
               no (0),
               yes (1)
               }
   MAX-ACCESS  read-only
   STATUS      current
   DESCRIPTION
      "Path: atm.status.vp.oamF4.connectionEndPoint

       Possibilities:
               no   (0)
               yes   (1)"
   ::= {sr1646v2ATMFwVpEntry 33816576}


sr1646v2ATMFwStat OBJECT IDENTIFIER ::= {sr1646v2ATMFw 2}

sr1646v2ATMFwStatSSCTable OBJECT-TYPE
   SYNTAX      SEQUENCE OF Sr1646v2ATMFwStatEntry
   MAX-ACCESS  not-accessible
   STATUS      current
   DESCRIPTION
      ""
   ::= {sr1646v2ATMFwStat 1}

sr1646v2ATMFwStatEntry OBJECT-TYPE
   SYNTAX      Sr1646v2ATMFwStatEntry
   MAX-ACCESS  not-accessible
   STATUS      current
   DESCRIPTION
      ""
   INDEX      { sr1646v2ATMFwStatGlobalIx,
                sr1646v2ATMFwStatTableIx }
   ::= {sr1646v2ATMFwStatSSCTable 1}

Sr1646v2ATMFwStatEntry ::=
   SEQUENCE
      {
      sr1646v2ATMFwStatGlobalIx
         GlobalIndex,
      sr1646v2ATMFwStatTableIx
         TableIndex,
      sr1646v2ATMFwStatName
         DisplayString,
      sr1646v2ATMFwStatMode
         INTEGER,
      sr1646v2ATMFwStatIfOperStatus
         INTEGER,
      sr1646v2ATMFwStatIfLastChange
         TimeTicks,
      sr1646v2ATMFwStatIfLastChangeDate
         DisplayString,
      sr1646v2ATMFwStatIpAddress
         IpAddress,
      sr1646v2ATMFwStatIpNetMask
         IpAddress,
      sr1646v2ATMFwStatIpRemote
         IpAddress,
      sr1646v2ATMFwStatIpV6State
         INTEGER,
      sr1646v2ATMFwStatIpV6InterfaceId
         OCTET STRING,
      sr1646v2ATMFwStatIpV6LinkMtu
         Integer32,
      sr1646v2ATMFwStatIpV6HopLimit
         Integer32,
      sr1646v2ATMFwStatIpV6DhcpIaid
         Counter32,
      sr1646v2ATMFwStatIpV6RaRcvOption
         Integer32,
      sr1646v2ATMFwStatBridgingStatus
         INTEGER,
      sr1646v2ATMFwStatBridgingSpanningTreePortRole
         INTEGER,
      sr1646v2ATMFwStatBridgingSpanningTreePortId
         Integer32,
      sr1646v2ATMFwStatBridgingSpanningTreePpCostExtPathCost
         Integer32,
      sr1646v2ATMFwStatBridgingSpanningTreePpCostIntPathCost
         Integer32,
      sr1646v2ATMFwStatBridgingSpanningTreeExtRpCost
         Integer32,
      sr1646v2ATMFwStatBridgingSpanningTreeIntRpCost
         Integer32,
      sr1646v2ATMFwStatBridgingSpanningTreeDesBrIdPriority
         Integer32,
      sr1646v2ATMFwStatBridgingSpanningTreeDesBrIdMacAddress
         OCTET STRING,
      sr1646v2ATMFwStatBridgingSpanningTreeDesPrtId
         Integer32,
      sr1646v2ATMFwStatBridgingSpanningTreeDesInt
         INTEGER,
      sr1646v2ATMFwStatBridgingSpanningTreeEdgeDetection
         INTEGER,
      sr1646v2ATMFwStatAtmVpi
         Integer32,
      sr1646v2ATMFwStatAtmVci
         Integer32,
      sr1646v2ATMFwStatAtmServCat
         INTEGER,
      sr1646v2ATMFwStatAtmPeakCellRate
         Integer32,
      sr1646v2ATMFwStatAtmSustCellRate
         Integer32,
      sr1646v2ATMFwStatAtmMaxBurstSize
         Integer32,
      sr1646v2ATMFwStatAtmPppOEthDiscState
         INTEGER,
      sr1646v2ATMFwStatAtmPppOEthPeerMac
         OCTET STRING,
      sr1646v2ATMFwStatAtmPppOEthServiceName
         DisplayString,
      sr1646v2ATMFwStatAtmPppLcpState
         INTEGER,
      sr1646v2ATMFwStatAtmPppIpcpState
         INTEGER,
      sr1646v2ATMFwStatAtmPppIp6cpState
         INTEGER,
      sr1646v2ATMFwStatAtmPppBcpState
         INTEGER,
      sr1646v2ATMFwStatAtmPppCcpState
         INTEGER,
      sr1646v2ATMFwStatAtmPppHisCompRat
         Integer32,
      sr1646v2ATMFwStatAtmPppMyCompRat
         Integer32,
      sr1646v2ATMFwStatAtmPppMyAutSt
         INTEGER,
      sr1646v2ATMFwStatAtmPppHisAutSt
         INTEGER,
      sr1646v2ATMFwStatAtmOamF5SegOamLB
         INTEGER,
      sr1646v2ATMFwStatAtmOamF5SegOamCC
         INTEGER,
      sr1646v2ATMFwStatAtmOamF5SegOamPMStatus
         INTEGER,
      sr1646v2ATMFwStatAtmOamF5SegOamPMBlockSizeAB
         INTEGER,
      sr1646v2ATMFwStatAtmOamF5SegOamPMBlockSizeBA
         INTEGER,
      sr1646v2ATMFwStatAtmOamF5SegAis
         INTEGER,
      sr1646v2ATMFwStatAtmOamF5SegRdi
         INTEGER,
      sr1646v2ATMFwStatAtmOamF5EteOamLB
         INTEGER,
      sr1646v2ATMFwStatAtmOamF5EteOamCC
         INTEGER,
      sr1646v2ATMFwStatAtmOamF5EteOamPMStatus
         INTEGER,
      sr1646v2ATMFwStatAtmOamF5EteOamPMBlockSizeAB
         INTEGER,
      sr1646v2ATMFwStatAtmOamF5EteOamPMBlockSizeBA
         INTEGER,
      sr1646v2ATMFwStatAtmOamF5EteAis
         INTEGER,
      sr1646v2ATMFwStatAtmOamF5EteRdi
         INTEGER,
      sr1646v2ATMFwStatAtmOamF5SegEP
         INTEGER,
      sr1646v2ATMFwStatAtmOamF5CnxEP
         INTEGER,
      sr1646v2ATMFwStatFrLmiMode
         INTEGER,
      sr1646v2ATMFwStatFrLmiType
         INTEGER,
      sr1646v2ATMFwStatFrLmiStatus
         INTEGER,
      sr1646v2ATMFwStatFrLmiLastChange
         TimeTicks,
      sr1646v2ATMFwStatFrLmiLastError
         INTEGER,
      sr1646v2ATMFwStatFrLmiNetTxSeqNum
         Integer32,
      sr1646v2ATMFwStatFrLmiNetRxSeqNum
         Integer32,
      sr1646v2ATMFwStatFrLmiNetErrors
         Integer32,
      sr1646v2ATMFwStatFrLmiUserTxSeqNum
         Integer32,
      sr1646v2ATMFwStatFrLmiUserRxSeqNum
         Integer32,
      sr1646v2ATMFwStatFrLmiUserErrors
         Integer32,
      sr1646v2ATMFwStatFrLmiUWaitFullEnq
         Integer32,
      sr1646v2ATMFwStatFrLmiULstRepTypeTx
         INTEGER
      }

sr1646v2ATMFwStatGlobalIx OBJECT-TYPE
   SYNTAX      GlobalIndex
   MAX-ACCESS  not-accessible
   STATUS      current
   DESCRIPTION
      "The value of the tlsCntTreeGlobalIndex of the MANAGED OBJECT."
   ::= {sr1646v2ATMFwStatEntry 10}

sr1646v2ATMFwStatTableIx OBJECT-TYPE
   SYNTAX      TableIndex
   MAX-ACCESS  not-accessible
   STATUS      current
   DESCRIPTION
      ""
   ::= {sr1646v2ATMFwStatEntry 11}

sr1646v2ATMFwStatName OBJECT-TYPE
   SYNTAX      DisplayString
   MAX-ACCESS  read-only
   STATUS      current
   DESCRIPTION
      "Path: atm.status.pvcTable.name"
   ::= {sr1646v2ATMFwStatEntry 16777216}

sr1646v2ATMFwStatMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: atm.status.pvcTable.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2ATMFwStatEntry 335544320}

sr1646v2ATMFwStatIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: atm.status.pvcTable.ifOperStatus

       Possibilities:
               up   (1)
               down   (2)
               testing   (3)
               unknown   (4)
               dormant   (5)
               notPresent   (6)
               lowerLayerDown   (7)"
   ::= {sr1646v2ATMFwStatEntry 1795162112}

sr1646v2ATMFwStatIfLastChange OBJECT-TYPE
   SYNTAX      TimeTicks
   MAX-ACCESS  read-only
   STATUS      current
   DESCRIPTION
      "Path: atm.status.pvcTable.ifLastChange

       Time in centi-second."
   ::= {sr1646v2ATMFwStatEntry 1811939328}

sr1646v2ATMFwStatIfLastChangeDate OBJECT-TYPE
   SYNTAX      DisplayString
   MAX-ACCESS  read-only
   STATUS      current
   DESCRIPTION
      "Path: atm.status.pvcTable.ifLastChangeDate"
   ::= {sr1646v2ATMFwStatEntry 3070230528}

sr1646v2ATMFwStatIpAddress OBJECT-TYPE
   SYNTAX      IpAddress
   MAX-ACCESS  read-only
   STATUS      current
   DESCRIPTION
      "Path: atm.status.pvcTable.ip.address"
   ::= {sr1646v2ATMFwStatEntry 51380224}

sr1646v2ATMFwStatIpNetMask OBJECT-TYPE
   SYNTAX      IpAddress
   MAX-ACCESS  read-only
   STATUS      current
   DESCRIPTION
      "Path: atm.status.pvcTable.ip.netMask"
   ::= {sr1646v2ATMFwStatEntry 51445760}

sr1646v2ATMFwStatIpRemote OBJECT-TYPE
   SYNTAX      IpAddress
   MAX-ACCESS  read-only
   STATUS      current
   DESCRIPTION
      "Path: atm.status.pvcTable.ip.remote"
   ::= {sr1646v2ATMFwStatEntry 51511296}

sr1646v2ATMFwStatIpV6State OBJECT-TYPE
   SYNTAX      INTEGER
               {
               disabled (0),
               enabled (1)
               }
   MAX-ACCESS  read-only
   STATUS      current
   DESCRIPTION
      "Path: atm.status.pvcTable.ipV6.state

       Possibilities:
               disabled   (0)
               enabled   (1)"
   ::= {sr1646v2ATMFwStatEntry 100728832}

sr1646v2ATMFwStatIpV6InterfaceId OBJECT-TYPE
   SYNTAX      OCTET STRING
   MAX-ACCESS  read-only
   STATUS      current
   DESCRIPTION
      "Path: atm.status.pvcTable.ipV6.interfaceId"
   ::= {sr1646v2ATMFwStatEntry 100794368}

sr1646v2ATMFwStatIpV6LinkMtu OBJECT-TYPE
   SYNTAX      Integer32
   MAX-ACCESS  read-only
   STATUS      current
   DESCRIPTION
      "Path: atm.status.pvcTable.ipV6.linkMtu"
   ::= {sr1646v2ATMFwStatEntry 100925440}

sr1646v2ATMFwStatIpV6HopLimit OBJECT-TYPE
   SYNTAX      Integer32
   MAX-ACCESS  read-only
   STATUS      current
   DESCRIPTION
      "Path: atm.status.pvcTable.ipV6.hopLimit"
   ::= {sr1646v2ATMFwStatEntry 100990976}

sr1646v2ATMFwStatIpV6DhcpIaid OBJECT-TYPE
   SYNTAX      Counter32
   MAX-ACCESS  read-only
   STATUS      current
   DESCRIPTION
      "Path: atm.status.pvcTable.ipV6.dhcp.iaid

       32 bit unsigned wrappable counter."
   ::= {sr1646v2ATMFwStatEntry 101056768}

sr1646v2ATMFwStatIpV6RaRcvOption OBJECT-TYPE
   SYNTAX      Integer32
   MAX-ACCESS  read-only
   STATUS      current
   DESCRIPTION
      "Path: atm.status.pvcTable.ipV6.raRcvOption

       Bit meanings:
               bit 0 = linkMtu,
               bit 1 = srcLinkLayer,
               bit 2 = prefixInfo,
               bit 3 = rdnss,
               bit 4 = dnssl"
   ::= {sr1646v2ATMFwStatEntry 101122048}

sr1646v2ATMFwStatBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: atm.status.pvcTable.bridging.status

       Possibilities:
               disabled   (0)
               discarding   (1)
               learning   (2)
               forwarding   (3)
               backupBlockedIntfDown   (256)
               backupBlockedIntfUp   (259)
               shutdown   (255)"
   ::= {sr1646v2ATMFwStatEntry 453050368}

sr1646v2ATMFwStatBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: atm.status.pvcTable.bridging.spanningTree.portRole

       Possibilities:
               none   (0)
               root   (1)
               designated   (2)
               alternate   (3)
               backup   (4)
               disabled   (5)
               master   (6)"
   ::= {sr1646v2ATMFwStatEntry 453116160}

sr1646v2ATMFwStatBridgingSpanningTreePortId OBJECT-TYPE
   SYNTAX      Integer32
   MAX-ACCESS  read-only
   STATUS      current
   DESCRIPTION
      "Path: atm.status.pvcTable.bridging.spanningTree.portId"
   ::= {sr1646v2ATMFwStatEntry 453116416}

sr1646v2ATMFwStatBridgingSpanningTreePpCostExtPathCost OBJECT-TYPE
   SYNTAX      Integer32
   MAX-ACCESS  read-only
   STATUS      current
   DESCRIPTION
      "Path: atm.status.pvcTable.bridging.spanningTree.portPathCosts.extPathCost"
   ::= {sr1646v2ATMFwStatEntry 453116673}

sr1646v2ATMFwStatBridgingSpanningTreePpCostIntPathCost OBJECT-TYPE
   SYNTAX      Integer32
   MAX-ACCESS  read-only
   STATUS      current
   DESCRIPTION
      "Path: atm.status.pvcTable.bridging.spanningTree.portPathCosts.intPathCost"
   ::= {sr1646v2ATMFwStatEntry 453116674}

sr1646v2ATMFwStatBridgingSpanningTreeExtRpCost OBJECT-TYPE
   SYNTAX      Integer32
   MAX-ACCESS  read-only
   STATUS      current
   DESCRIPTION
      "Path: atm.status.pvcTable.bridging.spanningTree.extRootPathCost"
   ::= {sr1646v2ATMFwStatEntry 453116928}

sr1646v2ATMFwStatBridgingSpanningTreeIntRpCost OBJECT-TYPE
   SYNTAX      Integer32
   MAX-ACCESS  read-only
   STATUS      current
   DESCRIPTION
      "Path: atm.status.pvcTable.bridging.spanningTree.intRootPathCost"
   ::= {sr1646v2ATMFwStatEntry 453117184}

sr1646v2ATMFwStatBridgingSpanningTreeDesBrIdPriority OBJECT-TYPE
   SYNTAX      Integer32
   MAX-ACCESS  read-only
   STATUS      current
   DESCRIPTION
      "Path: atm.status.pvcTable.bridging.spanningTree.designatedBridgeId.priority"
   ::= {sr1646v2ATMFwStatEntry 453117441}

sr1646v2ATMFwStatBridgingSpanningTreeDesBrIdMacAddress OBJECT-TYPE
   SYNTAX      OCTET STRING
   MAX-ACCESS  read-only
   STATUS      current
   DESCRIPTION
      "Path: atm.status.pvcTable.bridging.spanningTree.designatedBridgeId.macAddress

       MAC address."
   ::= {sr1646v2ATMFwStatEntry 453117442}

sr1646v2ATMFwStatBridgingSpanningTreeDesPrtId OBJECT-TYPE
   SYNTAX      Integer32
   MAX-ACCESS  read-only
   STATUS      current
   DESCRIPTION
      "Path: atm.status.pvcTable.bridging.spanningTree.designatedPortId"
   ::= {sr1646v2ATMFwStatEntry 453117696}

sr1646v2ATMFwStatBridgingSpanningTreeDesInt OBJECT-TYPE
   SYNTAX      INTEGER
               {
               no (0),
               yes (1)
               }
   MAX-ACCESS  read-only
   STATUS      current
   DESCRIPTION
      "Path: atm.status.pvcTable.bridging.spanningTree.designatedOrInternal

       Possibilities:
               no   (0)
               yes   (1)"
   ::= {sr1646v2ATMFwStatEntry 453117952}

sr1646v2ATMFwStatBridgingSpanningTreeEdgeDetection OBJECT-TYPE
   SYNTAX      INTEGER
               {
               none (0),
               edge (1),
               notEdge (2)
               }
   MAX-ACCESS  read-only
   STATUS      current
   DESCRIPTION
      "Path: atm.status.pvcTable.bridging.spanningTree.edgeDetection

       Possibilities:
               none   (0)
               edge   (1)
               notEdge   (2)"
   ::= {sr1646v2ATMFwStatEntry 453118208}

sr1646v2ATMFwStatAtmVpi OBJECT-TYPE
   SYNTAX      Integer32
   MAX-ACCESS  read-only
   STATUS      current
   DESCRIPTION
      "Path: atm.status.pvcTable.atm.vpi"
   ::= {sr1646v2ATMFwStatEntry 285278208}

sr1646v2ATMFwStatAtmVci OBJECT-TYPE
   SYNTAX      Integer32
   MAX-ACCESS  read-only
   STATUS      current
   DESCRIPTION
      "Path: atm.status.pvcTable.atm.vci"
   ::= {sr1646v2ATMFwStatEntry 285343744}

sr1646v2ATMFwStatAtmServCat OBJECT-TYPE
   SYNTAX      INTEGER
               {
               notAssigned (0),
               cbr (1),
               vbrmrt (2),
               vbrmnrt (3),
               ubr (4),
               cbrudg (5),
               vbrudgmrt (6),
               vbrudgmnrt (7),
               optional (50)
               }
   MAX-ACCESS  read-only
   STATUS      current
   DESCRIPTION
      "Path: atm.status.pvcTable.atm.serviceCategory

       Possibilities:
               notAssigned   (0)
               cbr   (1)
               vbr-rt   (2)
               vbr-nrt   (3)
               ubr   (4)
               cbr_dg   (5)
               vbr_dg-rt   (6)
               vbr_dg-nrt   (7)
               optional   (50)"
   ::= {sr1646v2ATMFwStatEntry 285736960}

sr1646v2ATMFwStatAtmPeakCellRate OBJECT-TYPE
   SYNTAX      Integer32
   UNITS       "bps"
   MAX-ACCESS  read-only
   STATUS      current
   DESCRIPTION
      "Path: atm.status.pvcTable.atm.peakCellRate

       unit name = bps"
   ::= {sr1646v2ATMFwStatEntry 285605888}

sr1646v2ATMFwStatAtmSustCellRate OBJECT-TYPE
   SYNTAX      Integer32
   UNITS       "bps"
   MAX-ACCESS  read-only
   STATUS      current
   DESCRIPTION
      "Path: atm.status.pvcTable.atm.sustCellRate

       unit name = bps"
   ::= {sr1646v2ATMFwStatEntry 285671424}

sr1646v2ATMFwStatAtmMaxBurstSize OBJECT-TYPE
   SYNTAX      Integer32
   UNITS       "cellTimes"
   MAX-ACCESS  read-only
   STATUS      current
   DESCRIPTION
      "Path: atm.status.pvcTable.atm.maxBurstSize

       unit name = cellTimes"
   ::= {sr1646v2ATMFwStatEntry 285802496}

sr1646v2ATMFwStatAtmPppOEthDiscState OBJECT-TYPE
   SYNTAX      INTEGER
               {
               idle (0),
               waitForPADO (1),
               waitForPADS (2),
               established (3)
               }
   MAX-ACCESS  read-only
   STATUS      current
   DESCRIPTION
      "Path: atm.status.pvcTable.atm.pppOverEth.discState

       Possibilities:
               idle   (0)
               waitForPADO   (1)
               waitForPADS   (2)
               established   (3)"
   ::= {sr1646v2ATMFwStatEntry 285409536}

sr1646v2ATMFwStatAtmPppOEthPeerMac OBJECT-TYPE
   SYNTAX      OCTET STRING
   MAX-ACCESS  read-only
   STATUS      current
   DESCRIPTION
      "Path: atm.status.pvcTable.atm.pppOverEth.remoteMacAddress

       MAC address."
   ::= {sr1646v2ATMFwStatEntry 285409792}

sr1646v2ATMFwStatAtmPppOEthServiceName OBJECT-TYPE
   SYNTAX      DisplayString
   MAX-ACCESS  read-only
   STATUS      current
   DESCRIPTION
      "Path: atm.status.pvcTable.atm.pppOverEth.serviceName"
   ::= {sr1646v2ATMFwStatEntry 285410048}

sr1646v2ATMFwStatAtmPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMFwStatEntry 285475072}

sr1646v2ATMFwStatAtmPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMFwStatEntry 285475328}

sr1646v2ATMFwStatAtmPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMFwStatEntry 285478656}

sr1646v2ATMFwStatAtmPppBcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMFwStatEntry 285475584}

sr1646v2ATMFwStatAtmPppCcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ccpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMFwStatEntry 285477888}

sr1646v2ATMFwStatAtmPppHisCompRat OBJECT-TYPE
   SYNTAX      Integer32
   UNITS       "%"
   MAX-ACCESS  read-only
   STATUS      current
   DESCRIPTION
      "Path: atm.status.pvcTable.atm.ppp.myCompressionRatio

       unit name = %"
   ::= {sr1646v2ATMFwStatEntry 285478144}

sr1646v2ATMFwStatAtmPppMyCompRat OBJECT-TYPE
   SYNTAX      Integer32
   UNITS       "%"
   MAX-ACCESS  read-only
   STATUS      current
   DESCRIPTION
      "Path: atm.status.pvcTable.atm.ppp.hisCompressionRatio

       unit name = %"
   ::= {sr1646v2ATMFwStatEntry 285478400}

sr1646v2ATMFwStatAtmPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: atm.status.pvcTable.atm.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2ATMFwStatEntry 285477376}

sr1646v2ATMFwStatAtmPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: atm.status.pvcTable.atm.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2ATMFwStatEntry 285477632}

sr1646v2ATMFwStatAtmOamF5SegOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.segment.oamLB

       Possibilities:
               ready   (0)
               waitActRes   (1)
               waitActCon   (2)
               waitDeactCon   (3)
               active   (4)
               deactivated   (5)"
   ::= {sr1646v2ATMFwStatEntry 285540640}

sr1646v2ATMFwStatAtmOamF5SegOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.segment.oamCC

       Possibilities:
               ready   (0)
               waitActRes   (1)
               waitActCon   (2)
               waitDeactCon   (3)
               active   (4)
               deactivated   (5)"
   ::= {sr1646v2ATMFwStatEntry 285540672}

sr1646v2ATMFwStatAtmOamF5SegOamPMStatus OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.segment.oamPM.status

       Possibilities:
               ready   (0)
               waitActRes   (1)
               waitActCon   (2)
               waitDeactCon   (3)
               active   (4)
               deactivated   (5)"
   ::= {sr1646v2ATMFwStatEntry 285540708}

sr1646v2ATMFwStatAtmOamF5SegOamPMBlockSizeAB OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.pvcTable.atm.oamF5.segment.oamPM.blockSizeAB

       Possibilities:
               128   (0)
               256   (1)
               512   (2)
               1024   (3)
               2048   (4)
               4096   (5)
               8192   (6)
               16384   (7)
               32768   (8)"
   ::= {sr1646v2ATMFwStatEntry 285540712}

sr1646v2ATMFwStatAtmOamF5SegOamPMBlockSizeBA OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.pvcTable.atm.oamF5.segment.oamPM.blockSizeBA

       Possibilities:
               128   (0)
               256   (1)
               512   (2)
               1024   (3)
               2048   (4)
               4096   (5)
               8192   (6)
               16384   (7)
               32768   (8)"
   ::= {sr1646v2ATMFwStatEntry 285540716}

sr1646v2ATMFwStatAtmOamF5SegAis OBJECT-TYPE
   SYNTAX      INTEGER
               {
               inactive (0),
               active (1)
               }
   MAX-ACCESS  read-only
   STATUS      current
   DESCRIPTION
      "Path: atm.status.pvcTable.atm.oamF5.segment.aisState

       Possibilities:
               inactive   (0)
               active   (1)"
   ::= {sr1646v2ATMFwStatEntry 285540736}

sr1646v2ATMFwStatAtmOamF5SegRdi OBJECT-TYPE
   SYNTAX      INTEGER
               {
               inactive (0),
               active (1)
               }
   MAX-ACCESS  read-only
   STATUS      current
   DESCRIPTION
      "Path: atm.status.pvcTable.atm.oamF5.segment.rdiState

       Possibilities:
               inactive   (0)
               active   (1)"
   ::= {sr1646v2ATMFwStatEntry 285540768}

sr1646v2ATMFwStatAtmOamF5EteOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.endToEnd.oamLB

       Possibilities:
               ready   (0)
               waitActRes   (1)
               waitActCon   (2)
               waitDeactCon   (3)
               active   (4)
               deactivated   (5)"
   ::= {sr1646v2ATMFwStatEntry 285540896}

sr1646v2ATMFwStatAtmOamF5EteOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.endToEnd.oamCC

       Possibilities:
               ready   (0)
               waitActRes   (1)
               waitActCon   (2)
               waitDeactCon   (3)
               active   (4)
               deactivated   (5)"
   ::= {sr1646v2ATMFwStatEntry 285540928}

sr1646v2ATMFwStatAtmOamF5EteOamPMStatus OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.endToEnd.oamPM.status

       Possibilities:
               ready   (0)
               waitActRes   (1)
               waitActCon   (2)
               waitDeactCon   (3)
               active   (4)
               deactivated   (5)"
   ::= {sr1646v2ATMFwStatEntry 285540964}

sr1646v2ATMFwStatAtmOamF5EteOamPMBlockSizeAB OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.pvcTable.atm.oamF5.endToEnd.oamPM.blockSizeAB

       Possibilities:
               128   (0)
               256   (1)
               512   (2)
               1024   (3)
               2048   (4)
               4096   (5)
               8192   (6)
               16384   (7)
               32768   (8)"
   ::= {sr1646v2ATMFwStatEntry 285540968}

sr1646v2ATMFwStatAtmOamF5EteOamPMBlockSizeBA OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.pvcTable.atm.oamF5.endToEnd.oamPM.blockSizeBA

       Possibilities:
               128   (0)
               256   (1)
               512   (2)
               1024   (3)
               2048   (4)
               4096   (5)
               8192   (6)
               16384   (7)
               32768   (8)"
   ::= {sr1646v2ATMFwStatEntry 285540972}

sr1646v2ATMFwStatAtmOamF5EteAis OBJECT-TYPE
   SYNTAX      INTEGER
               {
               inactive (0),
               active (1)
               }
   MAX-ACCESS  read-only
   STATUS      current
   DESCRIPTION
      "Path: atm.status.pvcTable.atm.oamF5.endToEnd.aisState

       Possibilities:
               inactive   (0)
               active   (1)"
   ::= {sr1646v2ATMFwStatEntry 285540992}

sr1646v2ATMFwStatAtmOamF5EteRdi OBJECT-TYPE
   SYNTAX      INTEGER
               {
               inactive (0),
               active (1)
               }
   MAX-ACCESS  read-only
   STATUS      current
   DESCRIPTION
      "Path: atm.status.pvcTable.atm.oamF5.endToEnd.rdiState

       Possibilities:
               inactive   (0)
               active   (1)"
   ::= {sr1646v2ATMFwStatEntry 285541024}

sr1646v2ATMFwStatAtmOamF5SegEP OBJECT-TYPE
   SYNTAX      INTEGER
               {
               no (0),
               yes (1)
               }
   MAX-ACCESS  read-only
   STATUS      current
   DESCRIPTION
      "Path: atm.status.pvcTable.atm.oamF5.segmentEndPoint

       Possibilities:
               no   (0)
               yes   (1)"
   ::= {sr1646v2ATMFwStatEntry 285541120}

sr1646v2ATMFwStatAtmOamF5CnxEP OBJECT-TYPE
   SYNTAX      INTEGER
               {
               no (0),
               yes (1)
               }
   MAX-ACCESS  read-only
   STATUS      current
   DESCRIPTION
      "Path: atm.status.pvcTable.atm.oamF5.connectionEndPoint

       Possibilities:
               no   (0)
               yes   (1)"
   ::= {sr1646v2ATMFwStatEntry 285541376}

sr1646v2ATMFwStatFrLmiMode OBJECT-TYPE
   SYNTAX      INTEGER
               {
               auto (0),
               network (1),
               user (2),
               noLmi (3),
               nni (4)
               }
   MAX-ACCESS  read-only
   STATUS      current
   DESCRIPTION
      "Path: atm.status.pvcTable.frameRelay.lmi.mode

       Possibilities:
               auto   (0)
               network   (1)
               user   (2)
               noLmi   (3)
               nni   (4)"
   ::= {sr1646v2ATMFwStatEntry 503382528}

sr1646v2ATMFwStatFrLmiType OBJECT-TYPE
   SYNTAX      INTEGER
               {
               lmiRev1 (1),
               ansiT1m617md (2),
               q933mAnnexmA (3),
               frf1m2 (4)
               }
   MAX-ACCESS  read-only
   STATUS      current
   DESCRIPTION
      "Path: atm.status.pvcTable.frameRelay.lmi.type

       Possibilities:
               lmiRev1   (1)
               ansiT1-617-d   (2)
               q933-Annex-A   (3)
               frf1-2   (4)"
   ::= {sr1646v2ATMFwStatEntry 503382272}

sr1646v2ATMFwStatFrLmiStatus OBJECT-TYPE
   SYNTAX      INTEGER
               {
               up (1),
               down (0)
               }
   MAX-ACCESS  read-only
   STATUS      current
   DESCRIPTION
      "Path: atm.status.pvcTable.frameRelay.lmi.status

       Possibilities:
               up   (1)
               down   (0)"
   ::= {sr1646v2ATMFwStatEntry 503382784}

sr1646v2ATMFwStatFrLmiLastChange OBJECT-TYPE
   SYNTAX      TimeTicks
   MAX-ACCESS  read-only
   STATUS      current
   DESCRIPTION
      "Path: atm.status.pvcTable.frameRelay.lmi.lastStatusChange

       Time in centi-second."
   ::= {sr1646v2ATMFwStatEntry 503383040}

sr1646v2ATMFwStatFrLmiLastError OBJECT-TYPE
   SYNTAX      INTEGER
               {
               none (10),
               protocolserror (6),
               unknownsinformationselement (7),
               sequenceserror (8),
               unknownsreport (9),
               timersexpired (38),
               invalidsreportstype (39),
               unsolicitedsstatus (54)
               }
   MAX-ACCESS  read-only
   STATUS      current
   DESCRIPTION
      "Path: atm.status.pvcTable.frameRelay.lmi.lastError

       Possibilities:
               none   (10)
               protocol error   (6)
               unknown information element   (7)
               sequence error   (8)
               unknown report   (9)
               timer expired   (38)
               invalid report type   (39)
               unsolicited status   (54)"
   ::= {sr1646v2ATMFwStatEntry 503383296}

sr1646v2ATMFwStatFrLmiNetTxSeqNum OBJECT-TYPE
   SYNTAX      Integer32
   MAX-ACCESS  read-only
   STATUS      current
   DESCRIPTION
      "Path: atm.status.pvcTable.frameRelay.lmi.netTxSeqNum"
   ::= {sr1646v2ATMFwStatEntry 503383552}

sr1646v2ATMFwStatFrLmiNetRxSeqNum OBJECT-TYPE
   SYNTAX      Integer32
   MAX-ACCESS  read-only
   STATUS      current
   DESCRIPTION
      "Path: atm.status.pvcTable.frameRelay.lmi.netRxSeqNum"
   ::= {sr1646v2ATMFwStatEntry 503383808}

sr1646v2ATMFwStatFrLmiNetErrors OBJECT-TYPE
   SYNTAX      Integer32
   MAX-ACCESS  read-only
   STATUS      current
   DESCRIPTION
      "Path: atm.status.pvcTable.frameRelay.lmi.netErrors"
   ::= {sr1646v2ATMFwStatEntry 503384064}

sr1646v2ATMFwStatFrLmiUserTxSeqNum OBJECT-TYPE
   SYNTAX      Integer32
   MAX-ACCESS  read-only
   STATUS      current
   DESCRIPTION
      "Path: atm.status.pvcTable.frameRelay.lmi.userTxSeqNum"
   ::= {sr1646v2ATMFwStatEntry 503387136}

sr1646v2ATMFwStatFrLmiUserRxSeqNum OBJECT-TYPE
   SYNTAX      Integer32
   MAX-ACCESS  read-only
   STATUS      current
   DESCRIPTION
      "Path: atm.status.pvcTable.frameRelay.lmi.userRxSeqNum"
   ::= {sr1646v2ATMFwStatEntry 503387392}

sr1646v2ATMFwStatFrLmiUserErrors OBJECT-TYPE
   SYNTAX      Integer32
   MAX-ACCESS  read-only
   STATUS      current
   DESCRIPTION
      "Path: atm.status.pvcTable.frameRelay.lmi.userErrors"
   ::= {sr1646v2ATMFwStatEntry 503387648}

sr1646v2ATMFwStatFrLmiUWaitFullEnq OBJECT-TYPE
   SYNTAX      Integer32
   MAX-ACCESS  read-only
   STATUS      current
   DESCRIPTION
      "Path: atm.status.pvcTable.frameRelay.lmi.userWaitFullEnquiry"
   ::= {sr1646v2ATMFwStatEntry 503387904}

sr1646v2ATMFwStatFrLmiULstRepTypeTx OBJECT-TYPE
   SYNTAX      INTEGER
               {
               fullsstatus (0),
               linksintegrity (1),
               singlesstatus (2),
               updatedsstatus (3),
               fullsstatusscontd (4),
               smmmmmmmm (170)
               }
   MAX-ACCESS  read-only
   STATUS      current
   DESCRIPTION
      "Path: atm.status.pvcTable.frameRelay.lmi.userLastReportTypeSent

       Possibilities:
               full status   (0)
               link integrity   (1)
               single status   (2)
               updated status   (3)
               full status cont.   (4)
               --------   (170)"
   ::= {sr1646v2ATMFwStatEntry 503388160}

sr1646v2ATMFwStatIpV6Addresses OBJECT-TYPE
   SYNTAX      SEQUENCE OF Sr1646v2ATMFwStatIpV6AddressesEntry
   MAX-ACCESS  not-accessible
   STATUS      current
   DESCRIPTION
      ""
   ::= {sr1646v2ATMFwStat 100859904}

sr1646v2ATMFwStatIpV6AddressesEntry OBJECT-TYPE
   SYNTAX      Sr1646v2ATMFwStatIpV6AddressesEntry
   MAX-ACCESS  not-accessible
   STATUS      current
   DESCRIPTION
      ""
   INDEX      { sr1646v2ATMFwStatIpV6AddressesGlobalIx,
                sr1646v2ATMFwStatTableIx,
                sr1646v2ATMFwStatIpV6AddressesTableIx }
   ::= {sr1646v2ATMFwStatIpV6Addresses 1}

Sr1646v2ATMFwStatIpV6AddressesEntry ::=
   SEQUENCE
      {
      sr1646v2ATMFwStatIpV6AddressesGlobalIx
         GlobalIndex,
      sr1646v2ATMFwStatIpV6AddressesTableIx
         TableIndex,
      sr1646v2ATMFwStatIpV6AddressesAddress
         Ipv6Address,
      sr1646v2ATMFwStatIpV6AddressesPrefixLength
         Integer32,
      sr1646v2ATMFwStatIpV6AddressesStatus
         INTEGER,
      sr1646v2ATMFwStatIpV6AddressesOrigin
         INTEGER,
      sr1646v2ATMFwStatIpV6AddressesFlagsInterfaceId
         INTEGER,
      sr1646v2ATMFwStatIpV6AddressesFlagsAnycast
         INTEGER,
      sr1646v2ATMFwStatIpV6AddressesTimersValidLifeTime
         TimeTicks,
      sr1646v2ATMFwStatIpV6AddressesTimersPrefLifeTime
         TimeTicks
      }

sr1646v2ATMFwStatIpV6AddressesGlobalIx OBJECT-TYPE
   SYNTAX      GlobalIndex
   MAX-ACCESS  not-accessible
   STATUS      current
   DESCRIPTION
      "The value of the tlsCntTreeGlobalIndex of the MANAGED OBJECT."
   ::= {sr1646v2ATMFwStatIpV6AddressesEntry 10}

sr1646v2ATMFwStatIpV6AddressesTableIx OBJECT-TYPE
   SYNTAX      TableIndex
   MAX-ACCESS  not-accessible
   STATUS      current
   DESCRIPTION
      ""
   ::= {sr1646v2ATMFwStatIpV6AddressesEntry 11}

sr1646v2ATMFwStatIpV6AddressesAddress OBJECT-TYPE
   SYNTAX      Ipv6Address
   MAX-ACCESS  read-only
   STATUS      current
   DESCRIPTION
      "Path: atm.status.pvcTable.ipV6.addresses.address

       ipv6 address"
   ::= {sr1646v2ATMFwStatIpV6AddressesEntry 16777216}

sr1646v2ATMFwStatIpV6AddressesPrefixLength OBJECT-TYPE
   SYNTAX      Integer32
   MAX-ACCESS  read-only
   STATUS      current
   DESCRIPTION
      "Path: atm.status.pvcTable.ipV6.addresses.prefixLength"
   ::= {sr1646v2ATMFwStatIpV6AddressesEntry 33554432}

sr1646v2ATMFwStatIpV6AddressesStatus OBJECT-TYPE
   SYNTAX      INTEGER
               {
               invalid (0),
               tentative (1),
               deprecated (2),
               preferred (3)
               }
   MAX-ACCESS  read-only
   STATUS      current
   DESCRIPTION
      "Path: atm.status.pvcTable.ipV6.addresses.status

       Possibilities:
               invalid   (0)
               tentative   (1)
               deprecated   (2)
               preferred   (3)"
   ::= {sr1646v2ATMFwStatIpV6AddressesEntry 50331648}

sr1646v2ATMFwStatIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: atm.status.pvcTable.ipV6.addresses.origin

       Possibilities:
               unknown   (0)
               manual   (1)
               generalPrefix   (2)
               statelessAuto   (3)
               statefullAuto   (4)"
   ::= {sr1646v2ATMFwStatIpV6AddressesEntry 67108864}

sr1646v2ATMFwStatIpV6AddressesFlagsInterfaceId OBJECT-TYPE
   SYNTAX      INTEGER
               {
               no (0),
               yes (1)
               }
   MAX-ACCESS  read-only
   STATUS      current
   DESCRIPTION
      "Path: atm.status.pvcTable.ipV6.addresses.flags.interfaceId

       Possibilities:
               no   (0)
               yes   (1)"
   ::= {sr1646v2ATMFwStatIpV6AddressesEntry 83951616}

sr1646v2ATMFwStatIpV6AddressesFlagsAnycast OBJECT-TYPE
   SYNTAX      INTEGER
               {
               no (0),
               yes (1)
               }
   MAX-ACCESS  read-only
   STATUS      current
   DESCRIPTION
      "Path: atm.status.pvcTable.ipV6.addresses.flags.anycast

       Possibilities:
               no   (0)
               yes   (1)"
   ::= {sr1646v2ATMFwStatIpV6AddressesEntry 84017152}

sr1646v2ATMFwStatIpV6AddressesTimersValidLifeTime OBJECT-TYPE
   SYNTAX      TimeTicks
   MAX-ACCESS  read-only
   STATUS      current
   DESCRIPTION
      "Path: atm.status.pvcTable.ipV6.addresses.timers.validLifeTime

       Time in centi-second."
   ::= {sr1646v2ATMFwStatIpV6AddressesEntry 100794368}

sr1646v2ATMFwStatIpV6AddressesTimersPrefLifeTime OBJECT-TYPE
   SYNTAX      TimeTicks
   MAX-ACCESS  read-only
   STATUS      current
   DESCRIPTION
      "Path: atm.status.pvcTable.ipV6.addresses.timers.prefLifeTime

       Time in centi-second."
   ::= {sr1646v2ATMFwStatIpV6AddressesEntry 100728832}

sr1646v2ATMFwStatFrDlci OBJECT-TYPE
   SYNTAX      SEQUENCE OF Sr1646v2ATMFwStatFrDlciEntry
   MAX-ACCESS  not-accessible
   STATUS      current
   DESCRIPTION
      ""
   ::= {sr1646v2ATMFwStat 503447552}

sr1646v2ATMFwStatFrDlciEntry OBJECT-TYPE
   SYNTAX      Sr1646v2ATMFwStatFrDlciEntry
   MAX-ACCESS  not-accessible
   STATUS      current
   DESCRIPTION
      ""
   INDEX      { sr1646v2ATMFwStatFrDlciGlobalIx,
                sr1646v2ATMFwStatTableIx,
                sr1646v2ATMFwStatFrDlciTableIx }
   ::= {sr1646v2ATMFwStatFrDlci 1}

Sr1646v2ATMFwStatFrDlciEntry ::=
   SEQUENCE
      {
      sr1646v2ATMFwStatFrDlciGlobalIx
         GlobalIndex,
      sr1646v2ATMFwStatFrDlciTableIx
         TableIndex,
      sr1646v2ATMFwStatFrDlciName
         DisplayString,
      sr1646v2ATMFwStatFrDlciMode
         INTEGER,
      sr1646v2ATMFwStatFrDlciIfOperStatus
         INTEGER,
      sr1646v2ATMFwStatFrDlciIfLastChange
         TimeTicks,
      sr1646v2ATMFwStatFrDlciIfLastChangeDate
         DisplayString,
      sr1646v2ATMFwStatFrDlciIpAddress
         IpAddress,
      sr1646v2ATMFwStatFrDlciIpNetMask
         IpAddress,
      sr1646v2ATMFwStatFrDlciIpRemote
         IpAddress,
      sr1646v2ATMFwStatFrDlciBridgingStatus
         INTEGER,
      sr1646v2ATMFwStatFrDlciBridgingSpanningTreePortRole
         INTEGER,
      sr1646v2ATMFwStatFrDlciBridgingSpanningTreePortId
         Integer32,
      sr1646v2ATMFwStatFrDlciBridgingSpanningTreePpCostExtPathCost
         Integer32,
      sr1646v2ATMFwStatFrDlciBridgingSpanningTreePpCostIntPathCost
         Integer32,
      sr1646v2ATMFwStatFrDlciBridgingSpanningTreeExtRpCost
         Integer32,
      sr1646v2ATMFwStatFrDlciBridgingSpanningTreeIntRpCost
         Integer32,
      sr1646v2ATMFwStatFrDlciBridgingSpanningTreeDesBrIdPriority
         Integer32,
      sr1646v2ATMFwStatFrDlciBridgingSpanningTreeDesBrIdMacAddress
         OCTET STRING,
      sr1646v2ATMFwStatFrDlciBridgingSpanningTreeDesPrtId
         Integer32,
      sr1646v2ATMFwStatFrDlciBridgingSpanningTreeDesInt
         INTEGER,
      sr1646v2ATMFwStatFrDlciBridgingSpanningTreeEdgeDetection
         INTEGER,
      sr1646v2ATMFwStatFrDlciFrDlci
         Integer32,
      sr1646v2ATMFwStatFrDlciFrActive
         INTEGER,
      sr1646v2ATMFwStatFrDlciFrNew
         INTEGER,
      sr1646v2ATMFwStatFrDlciFrDelete
         INTEGER,
      sr1646v2ATMFwStatFrDlciFrRr
         INTEGER,
      sr1646v2ATMFwStatFrDlciFrBandwidth
         Integer32,
      sr1646v2ATMFwStatFrDlciFrCllmLstCong
         INTEGER
      }

sr1646v2ATMFwStatFrDlciGlobalIx OBJECT-TYPE
   SYNTAX      GlobalIndex
   MAX-ACCESS  not-accessible
   STATUS      current
   DESCRIPTION
      "The value of the tlsCntTreeGlobalIndex of the MANAGED OBJECT."
   ::= {sr1646v2ATMFwStatFrDlciEntry 10}

sr1646v2ATMFwStatFrDlciTableIx OBJECT-TYPE
   SYNTAX      TableIndex
   MAX-ACCESS  not-accessible
   STATUS      current
   DESCRIPTION
      ""
   ::= {sr1646v2ATMFwStatFrDlciEntry 11}

sr1646v2ATMFwStatFrDlciName OBJECT-TYPE
   SYNTAX      DisplayString
   MAX-ACCESS  read-only
   STATUS      current
   DESCRIPTION
      "Path: atm.status.pvcTable.frameRelay.dlciTable.name"
   ::= {sr1646v2ATMFwStatFrDlciEntry 16777216}

sr1646v2ATMFwStatFrDlciMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: atm.status.pvcTable.frameRelay.dlciTable.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2ATMFwStatFrDlciEntry 335544320}

sr1646v2ATMFwStatFrDlciIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: atm.status.pvcTable.frameRelay.dlciTable.ifOperStatus

       Possibilities:
               up   (1)
               down   (2)
               testing   (3)
               unknown   (4)
               dormant   (5)
               notPresent   (6)
               lowerLayerDown   (7)"
   ::= {sr1646v2ATMFwStatFrDlciEntry 1795162112}

sr1646v2ATMFwStatFrDlciIfLastChange OBJECT-TYPE
   SYNTAX      TimeTicks
   MAX-ACCESS  read-only
   STATUS      current
   DESCRIPTION
      "Path: atm.status.pvcTable.frameRelay.dlciTable.ifLastChange

       Time in centi-second."
   ::= {sr1646v2ATMFwStatFrDlciEntry 1811939328}

sr1646v2ATMFwStatFrDlciIfLastChangeDate OBJECT-TYPE
   SYNTAX      DisplayString
   MAX-ACCESS  read-only
   STATUS      current
   DESCRIPTION
      "Path: atm.status.pvcTable.frameRelay.dlciTable.ifLastChangeDate"
   ::= {sr1646v2ATMFwStatFrDlciEntry 3070230528}

sr1646v2ATMFwStatFrDlciIpAddress OBJECT-TYPE
   SYNTAX      IpAddress
   MAX-ACCESS  read-only
   STATUS      current
   DESCRIPTION
      "Path: atm.status.pvcTable.frameRelay.dlciTable.ip.address"
   ::= {sr1646v2ATMFwStatFrDlciEntry 51380224}

sr1646v2ATMFwStatFrDlciIpNetMask OBJECT-TYPE
   SYNTAX      IpAddress
   MAX-ACCESS  read-only
   STATUS      current
   DESCRIPTION
      "Path: atm.status.pvcTable.frameRelay.dlciTable.ip.netMask"
   ::= {sr1646v2ATMFwStatFrDlciEntry 51445760}

sr1646v2ATMFwStatFrDlciIpRemote OBJECT-TYPE
   SYNTAX      IpAddress
   MAX-ACCESS  read-only
   STATUS      current
   DESCRIPTION
      "Path: atm.status.pvcTable.frameRelay.dlciTable.ip.remote"
   ::= {sr1646v2ATMFwStatFrDlciEntry 51511296}

sr1646v2ATMFwStatFrDlciBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: atm.status.pvcTable.frameRelay.dlciTable.bridging.status

       Possibilities:
               disabled   (0)
               discarding   (1)
               learning   (2)
               forwarding   (3)
               backupBlockedIntfDown   (256)
               backupBlockedIntfUp   (259)
               shutdown   (255)"
   ::= {sr1646v2ATMFwStatFrDlciEntry 453050368}

sr1646v2ATMFwStatFrDlciBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: atm.status.pvcTable.frameRelay.dlciTable.bridging.spanningTree.portRole

       Possibilities:
               none   (0)
               root   (1)
               designated   (2)
               alternate   (3)
               backup   (4)
               disabled   (5)
               master   (6)"
   ::= {sr1646v2ATMFwStatFrDlciEntry 453116160}

sr1646v2ATMFwStatFrDlciBridgingSpanningTreePortId OBJECT-TYPE
   SYNTAX      Integer32
   MAX-ACCESS  read-only
   STATUS      current
   DESCRIPTION
      "Path: atm.status.pvcTable.frameRelay.dlciTable.bridging.spanningTree.portId"
   ::= {sr1646v2ATMFwStatFrDlciEntry 453116416}

sr1646v2ATMFwStatFrDlciBridgingSpanningTreePpCostExtPathCost OBJECT-TYPE
   SYNTAX      Integer32
   MAX-ACCESS  read-only
   STATUS      current
   DESCRIPTION
      "Path: atm.status.pvcTable.frameRelay.dlciTable.bridging.spanningTree.portPathCosts.extPathCost"
   ::= {sr1646v2ATMFwStatFrDlciEntry 453116673}

sr1646v2ATMFwStatFrDlciBridgingSpanningTreePpCostIntPathCost OBJECT-TYPE
   SYNTAX      Integer32
   MAX-ACCESS  read-only
   STATUS      current
   DESCRIPTION
      "Path: atm.status.pvcTable.frameRelay.dlciTable.bridging.spanningTree.portPathCosts.intPathCost"
   ::= {sr1646v2ATMFwStatFrDlciEntry 453116674}

sr1646v2ATMFwStatFrDlciBridgingSpanningTreeExtRpCost OBJECT-TYPE
   SYNTAX      Integer32
   MAX-ACCESS  read-only
   STATUS      current
   DESCRIPTION
      "Path: atm.status.pvcTable.frameRelay.dlciTable.bridging.spanningTree.extRootPathCost"
   ::= {sr1646v2ATMFwStatFrDlciEntry 453116928}

sr1646v2ATMFwStatFrDlciBridgingSpanningTreeIntRpCost OBJECT-TYPE
   SYNTAX      Integer32
   MAX-ACCESS  read-only
   STATUS      current
   DESCRIPTION
      "Path: atm.status.pvcTable.frameRelay.dlciTable.bridging.spanningTree.intRootPathCost"
   ::= {sr1646v2ATMFwStatFrDlciEntry 453117184}

sr1646v2ATMFwStatFrDlciBridgingSpanningTreeDesBrIdPriority OBJECT-TYPE
   SYNTAX      Integer32
   MAX-ACCESS  read-only
   STATUS      current
   DESCRIPTION
      "Path: atm.status.pvcTable.frameRelay.dlciTable.bridging.spanningTree.designatedBridgeId.priority"
   ::= {sr1646v2ATMFwStatFrDlciEntry 453117441}

sr1646v2ATMFwStatFrDlciBridgingSpanningTreeDesBrIdMacAddress OBJECT-TYPE
   SYNTAX      OCTET STRING
   MAX-ACCESS  read-only
   STATUS      current
   DESCRIPTION
      "Path: atm.status.pvcTable.frameRelay.dlciTable.bridging.spanningTree.designatedBridgeId.macAddress

       MAC address."
   ::= {sr1646v2ATMFwStatFrDlciEntry 453117442}

sr1646v2ATMFwStatFrDlciBridgingSpanningTreeDesPrtId OBJECT-TYPE
   SYNTAX      Integer32
   MAX-ACCESS  read-only
   STATUS      current
   DESCRIPTION
      "Path: atm.status.pvcTable.frameRelay.dlciTable.bridging.spanningTree.designatedPortId"
   ::= {sr1646v2ATMFwStatFrDlciEntry 453117696}

sr1646v2ATMFwStatFrDlciBridgingSpanningTreeDesInt OBJECT-TYPE
   SYNTAX      INTEGER
               {
               no (0),
               yes (1)
               }
   MAX-ACCESS  read-only
   STATUS      current
   DESCRIPTION
      "Path: atm.status.pvcTable.frameRelay.dlciTable.bridging.spanningTree.designatedOrInternal

       Possibilities:
               no   (0)
               yes   (1)"
   ::= {sr1646v2ATMFwStatFrDlciEntry 453117952}

sr1646v2ATMFwStatFrDlciBridgingSpanningTreeEdgeDetection OBJECT-TYPE
   SYNTAX      INTEGER
               {
               none (0),
               edge (1),
               notEdge (2)
               }
   MAX-ACCESS  read-only
   STATUS      current
   DESCRIPTION
      "Path: atm.status.pvcTable.frameRelay.dlciTable.bridging.spanningTree.edgeDetection

       Possibilities:
               none   (0)
               edge   (1)
               notEdge   (2)"
   ::= {sr1646v2ATMFwStatFrDlciEntry 453118208}

sr1646v2ATMFwStatFrDlciFrDlci OBJECT-TYPE
   SYNTAX      Integer32
   MAX-ACCESS  read-only
   STATUS      current
   DESCRIPTION
      "Path: atm.status.pvcTable.frameRelay.dlciTable.frameRelay.dlci"
   ::= {sr1646v2ATMFwStatFrDlciEntry 218169344}

sr1646v2ATMFwStatFrDlciFrActive OBJECT-TYPE
   SYNTAX      INTEGER
               {
               off (0),
               on (1)
               }
   MAX-ACCESS  read-only
   STATUS      current
   DESCRIPTION
      "Path: atm.status.pvcTable.frameRelay.dlciTable.frameRelay.active

       Possibilities:
               off   (0)
               on   (1)"
   ::= {sr1646v2ATMFwStatFrDlciEntry 218234880}

sr1646v2ATMFwStatFrDlciFrNew OBJECT-TYPE
   SYNTAX      INTEGER
               {
               off (0),
               on (1)
               }
   MAX-ACCESS  read-only
   STATUS      current
   DESCRIPTION
      "Path: atm.status.pvcTable.frameRelay.dlciTable.frameRelay.new

       Possibilities:
               off   (0)
               on   (1)"
   ::= {sr1646v2ATMFwStatFrDlciEntry 218300416}

sr1646v2ATMFwStatFrDlciFrDelete OBJECT-TYPE
   SYNTAX      INTEGER
               {
               off (0),
               on (1)
               }
   MAX-ACCESS  read-only
   STATUS      current
   DESCRIPTION
      "Path: atm.status.pvcTable.frameRelay.dlciTable.frameRelay.delete

       Possibilities:
               off   (0)
               on   (1)"
   ::= {sr1646v2ATMFwStatFrDlciEntry 218365952}

sr1646v2ATMFwStatFrDlciFrRr OBJECT-TYPE
   SYNTAX      INTEGER
               {
               off (0),
               on (1)
               }
   MAX-ACCESS  read-only
   STATUS      current
   DESCRIPTION
      "Path: atm.status.pvcTable.frameRelay.dlciTable.frameRelay.rr

       Possibilities:
               off   (0)
               on   (1)"
   ::= {sr1646v2ATMFwStatFrDlciEntry 218431488}

sr1646v2ATMFwStatFrDlciFrBandwidth OBJECT-TYPE
   SYNTAX      Integer32
   MAX-ACCESS  read-only
   STATUS      current
   DESCRIPTION
      "Path: atm.status.pvcTable.frameRelay.dlciTable.frameRelay.bandwidth"
   ::= {sr1646v2ATMFwStatFrDlciEntry 218497024}

sr1646v2ATMFwStatFrDlciFrCllmLstCong OBJECT-TYPE
   SYNTAX      INTEGER
               {
               none (0),
               shortstermsexcessivestraffic (2),
               longstermsexcessivestraffic (3),
               shortstermsequipmentsfailure (6),
               longstermsequipmentsfailure (7),
               shortstermsmaintenancesaction (10),
               longstermsmaintenancesaction (11),
               shortstermsunknownscause (16),
               longstermsunknownscause (17),
               unknownscause (255)
               }
   MAX-ACCESS  read-only
   STATUS      current
   DESCRIPTION
      "Path: atm.status.pvcTable.frameRelay.dlciTable.frameRelay.cllmLastCongestionCause

       Possibilities:
               none   (0)
               short term, excessive traffic   (2)
               long term, excessive traffic   (3)
               short term, equipment failure   (6)
               long term, equipment failure   (7)
               short term, maintenance action   (10)
               long term, maintenance action   (11)
               short term, unknown cause   (16)
               long term, unknown cause   (17)
               unknown cause   (255)"
   ::= {sr1646v2ATMFwStatFrDlciEntry 218562560}


sr1646v2ATMFwSnmpIndex OBJECT IDENTIFIER ::= {sr1646v2ATMFw 269}

sr1646v2ATMFwSnmpIndexTable OBJECT-TYPE
   SYNTAX      SEQUENCE OF Sr1646v2ATMFwSnmpIndexEntry
   MAX-ACCESS  not-accessible
   STATUS      current
   DESCRIPTION
      "SNMP index assigned to this object"
   ::= {sr1646v2ATMFwSnmpIndex 1}

sr1646v2ATMFwSnmpIndexEntry OBJECT-TYPE
   SYNTAX      Sr1646v2ATMFwSnmpIndexEntry
   MAX-ACCESS  not-accessible
   STATUS      current
   DESCRIPTION
      ""
   INDEX      { sr1646v2ATMFwSnmpIndexGlobalIx }
   ::= {sr1646v2ATMFwSnmpIndexTable 1}

Sr1646v2ATMFwSnmpIndexEntry ::=
   SEQUENCE
      {
      sr1646v2ATMFwSnmpIndexGlobalIx
         GlobalIndex,
      sr1646v2ATMFwSnmpIndexValue
         Integer32
      }

sr1646v2ATMFwSnmpIndexGlobalIx OBJECT-TYPE
   SYNTAX      GlobalIndex
   MAX-ACCESS  not-accessible
   STATUS      current
   DESCRIPTION
      "The value of the tlsCntTreeGlobalIndex of the MANAGED OBJECT."
   ::= {sr1646v2ATMFwSnmpIndexEntry 10}

sr1646v2ATMFwSnmpIndexValue OBJECT-TYPE
   SYNTAX      Integer32
   MAX-ACCESS  read-only
   STATUS      current
   DESCRIPTION
      "Path: atm.status.snmpIndex"
   ::= {sr1646v2ATMFwSnmpIndexEntry 2147483648}



pr1646v2ATMFw OBJECT IDENTIFIER ::= {r1646v2ATMFw 12}


pr1646v2ATMFwUnknownCells OBJECT IDENTIFIER ::= {pr1646v2ATMFw 44}

pr1646v2ATMFwUnknownCellsTable OBJECT-TYPE
   SYNTAX      SEQUENCE OF Pr1646v2ATMFwUnknownCellsEntry
   MAX-ACCESS  not-accessible
   STATUS      current
   DESCRIPTION
      ""
   ::= {pr1646v2ATMFwUnknownCells 1}

pr1646v2ATMFwUnknownCellsEntry OBJECT-TYPE
   SYNTAX      Pr1646v2ATMFwUnknownCellsEntry
   MAX-ACCESS  not-accessible
   STATUS      current
   DESCRIPTION
      ""
   INDEX      { pr1646v2ATMFwUnknownCellsGlobalIx }
   ::= {pr1646v2ATMFwUnknownCellsTable 1}

Pr1646v2ATMFwUnknownCellsEntry ::=
   SEQUENCE
      {
      pr1646v2ATMFwUnknownCellsGlobalIx
         GlobalIndex,
      pr1646v2ATMFwUnknownCellsValue
         Gauge32
      }

pr1646v2ATMFwUnknownCellsGlobalIx OBJECT-TYPE
   SYNTAX      GlobalIndex
   MAX-ACCESS  not-accessible
   STATUS      current
   DESCRIPTION
      "The value of the tlsCntTreeGlobalIndex of the MANAGED OBJECT."
   ::= {pr1646v2ATMFwUnknownCellsEntry 10}

pr1646v2ATMFwUnknownCellsValue OBJECT-TYPE
   SYNTAX      Gauge32
   MAX-ACCESS  read-only
   STATUS      current
   DESCRIPTION
      "Path: atm.performance.unknownCells

       32 bit unsigned gauge value."
   ::= {pr1646v2ATMFwUnknownCellsEntry 2147483648}


pr1646v2ATMFwVp OBJECT IDENTIFIER ::= {pr1646v2ATMFw 94}

pr1646v2ATMFwVpSSCTable OBJECT-TYPE
   SYNTAX      SEQUENCE OF Pr1646v2ATMFwVpEntry
   MAX-ACCESS  not-accessible
   STATUS      current
   DESCRIPTION
      ""
   ::= {pr1646v2ATMFwVp 1}

pr1646v2ATMFwVpEntry OBJECT-TYPE
   SYNTAX      Pr1646v2ATMFwVpEntry
   MAX-ACCESS  not-accessible
   STATUS      current
   DESCRIPTION
      ""
   INDEX      { pr1646v2ATMFwVpGlobalIx,
                pr1646v2ATMFwVpTableIx }
   ::= {pr1646v2ATMFwVpSSCTable 1}

Pr1646v2ATMFwVpEntry ::=
   SEQUENCE
      {
      pr1646v2ATMFwVpGlobalIx
         GlobalIndex,
      pr1646v2ATMFwVpTableIx
         TableIndex,
      pr1646v2ATMFwVpVpi
         Integer32,
      pr1646v2ATMFwVpOamF4SegLbRx
         Gauge32,
      pr1646v2ATMFwVpOamF4SegLbTx
         Gauge32,
      pr1646v2ATMFwVpOamF4SegCcRx
         Gauge32,
      pr1646v2ATMFwVpOamF4SegCcTx
         Gauge32,
      pr1646v2ATMFwVpOamF4SegFpmRx
         Gauge32,
      pr1646v2ATMFwVpOamF4SegFpmTx
         Gauge32,
      pr1646v2ATMFwVpOamF4SegBrRx
         Gauge32,
      pr1646v2ATMFwVpOamF4SegBrTx
         Gauge32,
      pr1646v2ATMFwVpOamF4SegAdRx
         Gauge32,
      pr1646v2ATMFwVpOamF4SegAdTx
         Gauge32,
      pr1646v2ATMFwVpOamF4SegAisRx
         Gauge32,
      pr1646v2ATMFwVpOamF4SegAisTx
         Gauge32,
      pr1646v2ATMFwVpOamF4SegRdiRx
         Gauge32,
      pr1646v2ATMFwVpOamF4SegRdiTx
         Gauge32,
      pr1646v2ATMFwVpOamF4SegRxpmNLOC
         Gauge32,
      pr1646v2ATMFwVpOamF4SegRxpmNLUC
         Gauge32,
      pr1646v2ATMFwVpOamF4SegRxpmNEUC
         Gauge32,
      pr1646v2ATMFwVpOamF4SegRxpmNMUC
         Gauge32,
      pr1646v2ATMFwVpOamF4SegRxpmCer
         Integer32,
      pr1646v2ATMFwVpOamF4SegRxpmClr
         Integer32,
      pr1646v2ATMFwVpOamF4SegRxpmCmr
         Integer32,
      pr1646v2ATMFwVpOamF4SegRxpmSecb
         Integer32,
      pr1646v2ATMFwVpOamF4SegTxpmNLOC
         Gauge32,
      pr1646v2ATMFwVpOamF4SegTxpmNLUC
         Gauge32,
      pr1646v2ATMFwVpOamF4SegTxpmNEUC
         Gauge32,
      pr1646v2ATMFwVpOamF4SegTxpmNMUC
         Gauge32,
      pr1646v2ATMFwVpOamF4SegTxpmCer
         Integer32,
      pr1646v2ATMFwVpOamF4SegTxpmClr
         Integer32,
      pr1646v2ATMFwVpOamF4SegTxpmCmr
         Integer32,
      pr1646v2ATMFwVpOamF4SegTxpmSecb
         Integer32,
      pr1646v2ATMFwVpOamF4EteLbRx
         Gauge32,
      pr1646v2ATMFwVpOamF4EteLbTx
         Gauge32,
      pr1646v2ATMFwVpOamF4EteCcRx
         Gauge32,
      pr1646v2ATMFwVpOamF4EteCcTx
         Gauge32,
      pr1646v2ATMFwVpOamF4EteFpmRx
         Gauge32,
      pr1646v2ATMFwVpOamF4EteFpmTx
         Gauge32,
      pr1646v2ATMFwVpOamF4EteBrRx
         Gauge32,
      pr1646v2ATMFwVpOamF4EteBrTx
         Gauge32,
      pr1646v2ATMFwVpOamF4EteAdRx
         Gauge32,
      pr1646v2ATMFwVpOamF4EteAdTx
         Gauge32,
      pr1646v2ATMFwVpOamF4EteAisRx
         Gauge32,
      pr1646v2ATMFwVpOamF4EteAisTx
         Gauge32,
      pr1646v2ATMFwVpOamF4EteRdiRx
         Gauge32,
      pr1646v2ATMFwVpOamF4EteRdiTx
         Gauge32,
      pr1646v2ATMFwVpOamF4EteRxpmNLOC
         Gauge32,
      pr1646v2ATMFwVpOamF4EteRxpmNLUC
         Gauge32,
      pr1646v2ATMFwVpOamF4EteRxpmNEUC
         Gauge32,
      pr1646v2ATMFwVpOamF4EteRxpmNMUC
         Gauge32,
      pr1646v2ATMFwVpOamF4EteRxpmCer
         Integer32,
      pr1646v2ATMFwVpOamF4EteRxpmClr
         Integer32,
      pr1646v2ATMFwVpOamF4EteRxpmCmr
         Integer32,
      pr1646v2ATMFwVpOamF4EteRxpmSecb
         Integer32,
      pr1646v2ATMFwVpOamF4EteTxpmNLOC
         Gauge32,
      pr1646v2ATMFwVpOamF4EteTxpmNLUC
         Gauge32,
      pr1646v2ATMFwVpOamF4EteTxpmNEUC
         Gauge32,
      pr1646v2ATMFwVpOamF4EteTxpmNMUC
         Gauge32,
      pr1646v2ATMFwVpOamF4EteTxpmCer
         Integer32,
      pr1646v2ATMFwVpOamF4EteTxpmClr
         Integer32,
      pr1646v2ATMFwVpOamF4EteTxpmCmr
         Integer32,
      pr1646v2ATMFwVpOamF4EteTxpmSecb
         Integer32
      }

pr1646v2ATMFwVpGlobalIx OBJECT-TYPE
   SYNTAX      GlobalIndex
   MAX-ACCESS  not-accessible
   STATUS      current
   DESCRIPTION
      "The value of the tlsCntTreeGlobalIndex of the MANAGED OBJECT."
   ::= {pr1646v2ATMFwVpEntry 10}

pr1646v2ATMFwVpTableIx OBJECT-TYPE
   SYNTAX      TableIndex
   MAX-ACCESS  not-accessible
   STATUS      current
   DESCRIPTION
      ""
   ::= {pr1646v2ATMFwVpEntry 11}

pr1646v2ATMFwVpVpi OBJECT-TYPE
   SYNTAX      Integer32
   MAX-ACCESS  read-only
   STATUS      current
   DESCRIPTION
      "Path: atm.performance.vp.vpi"
   ::= {pr1646v2ATMFwVpEntry 268435456}

pr1646v2ATMFwVpOamF4SegLbRx OBJECT-TYPE
   SYNTAX      Gauge32
   MAX-ACCESS  read-only
   STATUS      current
   DESCRIPTION
      "Path: atm.performance.vp.oamF4.segment.lbRx

       32 bit unsigned gauge value."
   ::= {pr1646v2ATMFwVpEntry 571473920}

pr1646v2ATMFwVpOamF4SegLbTx OBJECT-TYPE
   SYNTAX      Gauge32
   MAX-ACCESS  read-only
   STATUS      current
   DESCRIPTION
      "Path: atm.performance.vp.oamF4.segment.lbTx

       32 bit unsigned gauge value."
   ::= {pr1646v2ATMFwVpEntry 572522496}

pr1646v2ATMFwVpOamF4SegCcRx OBJECT-TYPE
   SYNTAX      Gauge32
   MAX-ACCESS  read-only
   STATUS      current
   DESCRIPTION
      "Path: atm.performance.vp.oamF4.segment.ccRx

       32 bit unsigned gauge value."
   ::= {pr1646v2ATMFwVpEntry 573571072}

pr1646v2ATMFwVpOamF4SegCcTx OBJECT-TYPE
   SYNTAX      Gauge32
   MAX-ACCESS  read-only
   STATUS      current
   DESCRIPTION
      "Path: atm.performance.vp.oamF4.segment.ccTx

       32 bit unsigned gauge value."
   ::= {pr1646v2ATMFwVpEntry 574619648}

pr1646v2ATMFwVpOamF4SegFpmRx OBJECT-TYPE
   SYNTAX      Gauge32
   MAX-ACCESS  read-only
   STATUS      current
   DESCRIPTION
      "Path: atm.performance.vp.oamF4.segment.fpmRx

       32 bit unsigned gauge value."
   ::= {pr1646v2ATMFwVpEntry 575668224}

pr1646v2ATMFwVpOamF4SegFpmTx OBJECT-TYPE
   SYNTAX      Gauge32
   MAX-ACCESS  read-only
   STATUS      current
   DESCRIPTION
      "Path: atm.performance.vp.oamF4.segment.fpmTx

       32 bit unsigned gauge value."
   ::= {pr1646v2ATMFwVpEntry 576716800}

pr1646v2ATMFwVpOamF4SegBrRx OBJECT-TYPE
   SYNTAX      Gauge32
   MAX-ACCESS  read-only
   STATUS      current
   DESCRIPTION
      "Path: atm.performance.vp.oamF4.segment.brRx

       32 bit unsigned gauge value."
   ::= {pr1646v2ATMFwVpEntry 577765376}

pr1646v2ATMFwVpOamF4SegBrTx OBJECT-TYPE
   SYNTAX      Gauge32
   MAX-ACCESS  read-only
   STATUS      current
   DESCRIPTION
      "Path: atm.performance.vp.oamF4.segment.brTx

       32 bit unsigned gauge value."
   ::= {pr1646v2ATMFwVpEntry 578813952}

pr1646v2ATMFwVpOamF4SegAdRx OBJECT-TYPE
   SYNTAX      Gauge32
   MAX-ACCESS  read-only
   STATUS      current
   DESCRIPTION
      "Path: atm.performance.vp.oamF4.segment.actDeactRx

       32 bit unsigned gauge value."
   ::= {pr1646v2ATMFwVpEntry 579862528}

pr1646v2ATMFwVpOamF4SegAdTx OBJECT-TYPE
   SYNTAX      Gauge32
   MAX-ACCESS  read-only
   STATUS      current
   DESCRIPTION
      "Path: atm.performance.vp.oamF4.segment.actDeactTx

       32 bit unsigned gauge value."
   ::= {pr1646v2ATMFwVpEntry 580911104}

pr1646v2ATMFwVpOamF4SegAisRx OBJECT-TYPE
   SYNTAX      Gauge32
   MAX-ACCESS  read-only
   STATUS      current
   DESCRIPTION
      "Path: atm.performance.vp.oamF4.segment.aisRx

       32 bit unsigned gauge value."
   ::= {pr1646v2ATMFwVpEntry 581959680}

pr1646v2ATMFwVpOamF4SegAisTx OBJECT-TYPE
   SYNTAX      Gauge32
   MAX-ACCESS  read-only
   STATUS      current
   DESCRIPTION
      "Path: atm.performance.vp.oamF4.segment.aisTx

       32 bit unsigned gauge value."
   ::= {pr1646v2ATMFwVpEntry 583008256}

pr1646v2ATMFwVpOamF4SegRdiRx OBJECT-TYPE
   SYNTAX      Gauge32
   MAX-ACCESS  read-only
   STATUS      current
   DESCRIPTION
      "Path: atm.performance.vp.oamF4.segment.rdiRx

       32 bit unsigned gauge value."
   ::= {pr1646v2ATMFwVpEntry 584056832}

pr1646v2ATMFwVpOamF4SegRdiTx OBJECT-TYPE
   SYNTAX      Gauge32
   MAX-ACCESS  read-only
   STATUS      current
   DESCRIPTION
      "Path: atm.performance.vp.oamF4.segment.rdiTx

       32 bit unsigned gauge value."
   ::= {pr1646v2ATMFwVpEntry 585105408}

pr1646v2ATMFwVpOamF4SegRxpmNLOC OBJECT-TYPE
   SYNTAX      Gauge32
   MAX-ACCESS  read-only
   STATUS      current
   DESCRIPTION
      "Path: atm.performance.vp.oamF4.segment.pmRxStats.lostOamCells

       32 bit unsigned gauge value."
   ::= {pr1646v2ATMFwVpEntry 586158080}

pr1646v2ATMFwVpOamF4SegRxpmNLUC OBJECT-TYPE
   SYNTAX      Gauge32
   MAX-ACCESS  read-only
   STATUS      current
   DESCRIPTION
      "Path: atm.performance.vp.oamF4.segment.pmRxStats.lostUserCells

       32 bit unsigned gauge value."
   ::= {pr1646v2ATMFwVpEntry 586162176}

pr1646v2ATMFwVpOamF4SegRxpmNEUC OBJECT-TYPE
   SYNTAX      Gauge32
   MAX-ACCESS  read-only
   STATUS      current
   DESCRIPTION
      "Path: atm.performance.vp.oamF4.segment.pmRxStats.errUserCells

       32 bit unsigned gauge value."
   ::= {pr1646v2ATMFwVpEntry 586166272}

pr1646v2ATMFwVpOamF4SegRxpmNMUC OBJECT-TYPE
   SYNTAX      Gauge32
   MAX-ACCESS  read-only
   STATUS      current
   DESCRIPTION
      "Path: atm.performance.vp.oamF4.segment.pmRxStats.misInsertUserCells

       32 bit unsigned gauge value."
   ::= {pr1646v2ATMFwVpEntry 586170368}

pr1646v2ATMFwVpOamF4SegRxpmCer OBJECT-TYPE
   SYNTAX      Integer32
   MAX-ACCESS  read-only
   STATUS      current
   DESCRIPTION
      "Path: atm.performance.vp.oamF4.segment.pmRxStats.cellErrRatio

       formula = 1000000000 / ; 1000000000 *"
   ::= {pr1646v2ATMFwVpEntry 586174464}

pr1646v2ATMFwVpOamF4SegRxpmClr OBJECT-TYPE
   SYNTAX      Integer32
   MAX-ACCESS  read-only
   STATUS      current
   DESCRIPTION
      "Path: atm.performance.vp.oamF4.segment.pmRxStats.cellLossRatio

       formula = 1000000000 / ; 1000000000 *"
   ::= {pr1646v2ATMFwVpEntry 586178560}

pr1646v2ATMFwVpOamF4SegRxpmCmr OBJECT-TYPE
   SYNTAX      Integer32
   MAX-ACCESS  read-only
   STATUS      current
   DESCRIPTION
      "Path: atm.performance.vp.oamF4.segment.pmRxStats.cellMisinsertRatio

       unit name = misinserts/sec
       formula = 1000000000 / ; 1000000000 *"
   ::= {pr1646v2ATMFwVpEntry 586182656}

pr1646v2ATMFwVpOamF4SegRxpmSecb OBJECT-TYPE
   SYNTAX      Integer32
   MAX-ACCESS  read-only
   STATUS      current
   DESCRIPTION
      "Path: atm.performance.vp.oamF4.segment.pmRxStats.sevErrCellBlckRatio

       formula = 1000000000 / ; 1000000000 *"
   ::= {pr1646v2ATMFwVpEntry 586186752}

pr1646v2ATMFwVpOamF4SegTxpmNLOC OBJECT-TYPE
   SYNTAX      Gauge32
   MAX-ACCESS  read-only
   STATUS      current
   DESCRIPTION
      "Path: atm.performance.vp.oamF4.segment.pmTxStats.lostOamCells

       32 bit unsigned gauge value."
   ::= {pr1646v2ATMFwVpEntry 587206656}

pr1646v2ATMFwVpOamF4SegTxpmNLUC OBJECT-TYPE
   SYNTAX      Gauge32
   MAX-ACCESS  read-only
   STATUS      current
   DESCRIPTION
      "Path: atm.performance.vp.oamF4.segment.pmTxStats.lostUserCells

       32 bit unsigned gauge value."
   ::= {pr1646v2ATMFwVpEntry 587210752}

pr1646v2ATMFwVpOamF4SegTxpmNEUC OBJECT-TYPE
   SYNTAX      Gauge32
   MAX-ACCESS  read-only
   STATUS      current
   DESCRIPTION
      "Path: atm.performance.vp.oamF4.segment.pmTxStats.errUserCells

       32 bit unsigned gauge value."
   ::= {pr1646v2ATMFwVpEntry 587214848}

pr1646v2ATMFwVpOamF4SegTxpmNMUC OBJECT-TYPE
   SYNTAX      Gauge32
   MAX-ACCESS  read-only
   STATUS      current
   DESCRIPTION
      "Path: atm.performance.vp.oamF4.segment.pmTxStats.misInsertUserCells

       32 bit unsigned gauge value."
   ::= {pr1646v2ATMFwVpEntry 587218944}

pr1646v2ATMFwVpOamF4SegTxpmCer OBJECT-TYPE
   SYNTAX      Integer32
   MAX-ACCESS  read-only
   STATUS      current
   DESCRIPTION
      "Path: atm.performance.vp.oamF4.segment.pmTxStats.cellErrRatio

       formula = 1000000000 / ; 1000000000 *"
   ::= {pr1646v2ATMFwVpEntry 587223040}

pr1646v2ATMFwVpOamF4SegTxpmClr OBJECT-TYPE
   SYNTAX      Integer32
   MAX-ACCESS  read-only
   STATUS      current
   DESCRIPTION
      "Path: atm.performance.vp.oamF4.segment.pmTxStats.cellLossRatio

       formula = 1000000000 / ; 1000000000 *"
   ::= {pr1646v2ATMFwVpEntry 587227136}

pr1646v2ATMFwVpOamF4SegTxpmCmr OBJECT-TYPE
   SYNTAX      Integer32
   MAX-ACCESS  read-only
   STATUS      current
   DESCRIPTION
      "Path: atm.performance.vp.oamF4.segment.pmTxStats.cellMisinsertRatio

       unit name = misinserts/sec
       formula = 1000000000 / ; 1000000000 *"
   ::= {pr1646v2ATMFwVpEntry 587231232}

pr1646v2ATMFwVpOamF4SegTxpmSecb OBJECT-TYPE
   SYNTAX      Integer32
   MAX-ACCESS  read-only
   STATUS      current
   DESCRIPTION
      "Path: atm.performance.vp.oamF4.segment.pmTxStats.sevErrCellBlckRatio

       formula = 1000000000 / ; 1000000000 *"
   ::= {pr1646v2ATMFwVpEntry 587235328}

pr1646v2ATMFwVpOamF4EteLbRx OBJECT-TYPE
   SYNTAX      Gauge32
   MAX-ACCESS  read-only
   STATUS      current
   DESCRIPTION
      "Path: atm.performance.vp.oamF4.endToEnd.lbRx

       32 bit unsigned gauge value."
   ::= {pr1646v2ATMFwVpEntry 605028352}

pr1646v2ATMFwVpOamF4EteLbTx OBJECT-TYPE
   SYNTAX      Gauge32
   MAX-ACCESS  read-only
   STATUS      current
   DESCRIPTION
      "Path: atm.performance.vp.oamF4.endToEnd.lbTx

       32 bit unsigned gauge value."
   ::= {pr1646v2ATMFwVpEntry 606076928}

pr1646v2ATMFwVpOamF4EteCcRx OBJECT-TYPE
   SYNTAX      Gauge32
   MAX-ACCESS  read-only
   STATUS      current
   DESCRIPTION
      "Path: atm.performance.vp.oamF4.endToEnd.ccRx

       32 bit unsigned gauge value."
   ::= {pr1646v2ATMFwVpEntry 607125504}

pr1646v2ATMFwVpOamF4EteCcTx OBJECT-TYPE
   SYNTAX      Gauge32
   MAX-ACCESS  read-only
   STATUS      current
   DESCRIPTION
      "Path: atm.performance.vp.oamF4.endToEnd.ccTx

       32 bit unsigned gauge value."
   ::= {pr1646v2ATMFwVpEntry 608174080}

pr1646v2ATMFwVpOamF4EteFpmRx OBJECT-TYPE
   SYNTAX      Gauge32
   MAX-ACCESS  read-only
   STATUS      current
   DESCRIPTION
      "Path: atm.performance.vp.oamF4.endToEnd.fpmRx

       32 bit unsigned gauge value."
   ::= {pr1646v2ATMFwVpEntry 609222656}

pr1646v2ATMFwVpOamF4EteFpmTx OBJECT-TYPE
   SYNTAX      Gauge32
   MAX-ACCESS  read-only
   STATUS      current
   DESCRIPTION
      "Path: atm.performance.vp.oamF4.endToEnd.fpmTx

       32 bit unsigned gauge value."
   ::= {pr1646v2ATMFwVpEntry 610271232}

pr1646v2ATMFwVpOamF4EteBrRx OBJECT-TYPE
   SYNTAX      Gauge32
   MAX-ACCESS  read-only
   STATUS      current
   DESCRIPTION
      "Path: atm.performance.vp.oamF4.endToEnd.brRx

       32 bit unsigned gauge value."
   ::= {pr1646v2ATMFwVpEntry 611319808}

pr1646v2ATMFwVpOamF4EteBrTx OBJECT-TYPE
   SYNTAX      Gauge32
   MAX-ACCESS  read-only
   STATUS      current
   DESCRIPTION
      "Path: atm.performance.vp.oamF4.endToEnd.brTx

       32 bit unsigned gauge value."
   ::= {pr1646v2ATMFwVpEntry 612368384}

pr1646v2ATMFwVpOamF4EteAdRx OBJECT-TYPE
   SYNTAX      Gauge32
   MAX-ACCESS  read-only
   STATUS      current
   DESCRIPTION
      "Path: atm.performance.vp.oamF4.endToEnd.actDeactRx

       32 bit unsigned gauge value."
   ::= {pr1646v2ATMFwVpEntry 613416960}

pr1646v2ATMFwVpOamF4EteAdTx OBJECT-TYPE
   SYNTAX      Gauge32
   MAX-ACCESS  read-only
   STATUS      current
   DESCRIPTION
      "Path: atm.performance.vp.oamF4.endToEnd.actDeactTx

       32 bit unsigned gauge value."
   ::= {pr1646v2ATMFwVpEntry 614465536}

pr1646v2ATMFwVpOamF4EteAisRx OBJECT-TYPE
   SYNTAX      Gauge32
   MAX-ACCESS  read-only
   STATUS      current
   DESCRIPTION
      "Path: atm.performance.vp.oamF4.endToEnd.aisRx

       32 bit unsigned gauge value."
   ::= {pr1646v2ATMFwVpEntry 615514112}

pr1646v2ATMFwVpOamF4EteAisTx OBJECT-TYPE
   SYNTAX      Gauge32
   MAX-ACCESS  read-only
   STATUS      current
   DESCRIPTION
      "Path: atm.performance.vp.oamF4.endToEnd.aisTx

       32 bit unsigned gauge value."
   ::= {pr1646v2ATMFwVpEntry 616562688}

pr1646v2ATMFwVpOamF4EteRdiRx OBJECT-TYPE
   SYNTAX      Gauge32
   MAX-ACCESS  read-only
   STATUS      current
   DESCRIPTION
      "Path: atm.performance.vp.oamF4.endToEnd.rdiRx

       32 bit unsigned gauge value."
   ::= {pr1646v2ATMFwVpEntry 617611264}

pr1646v2ATMFwVpOamF4EteRdiTx OBJECT-TYPE
   SYNTAX      Gauge32
   MAX-ACCESS  read-only
   STATUS      current
   DESCRIPTION
      "Path: atm.performance.vp.oamF4.endToEnd.rdiTx

       32 bit unsigned gauge value."
   ::= {pr1646v2ATMFwVpEntry 618659840}

pr1646v2ATMFwVpOamF4EteRxpmNLOC OBJECT-TYPE
   SYNTAX      Gauge32
   MAX-ACCESS  read-only
   STATUS      current
   DESCRIPTION
      "Path: atm.performance.vp.oamF4.endToEnd.pmRxStats.lostOamCells

       32 bit unsigned gauge value."
   ::= {pr1646v2ATMFwVpEntry 619712512}

pr1646v2ATMFwVpOamF4EteRxpmNLUC OBJECT-TYPE
   SYNTAX      Gauge32
   MAX-ACCESS  read-only
   STATUS      current
   DESCRIPTION
      "Path: atm.performance.vp.oamF4.endToEnd.pmRxStats.lostUserCells

       32 bit unsigned gauge value."
   ::= {pr1646v2ATMFwVpEntry 619716608}

pr1646v2ATMFwVpOamF4EteRxpmNEUC OBJECT-TYPE
   SYNTAX      Gauge32
   MAX-ACCESS  read-only
   STATUS      current
   DESCRIPTION
      "Path: atm.performance.vp.oamF4.endToEnd.pmRxStats.errUserCells

       32 bit unsigned gauge value."
   ::= {pr1646v2ATMFwVpEntry 619720704}

pr1646v2ATMFwVpOamF4EteRxpmNMUC OBJECT-TYPE
   SYNTAX      Gauge32
   MAX-ACCESS  read-only
   STATUS      current
   DESCRIPTION
      "Path: atm.performance.vp.oamF4.endToEnd.pmRxStats.misInsertUserCells

       32 bit unsigned gauge value."
   ::= {pr1646v2ATMFwVpEntry 619724800}

pr1646v2ATMFwVpOamF4EteRxpmCer OBJECT-TYPE
   SYNTAX      Integer32
   MAX-ACCESS  read-only
   STATUS      current
   DESCRIPTION
      "Path: atm.performance.vp.oamF4.endToEnd.pmRxStats.cellErrRatio

       formula = 1000000000 / ; 1000000000 *"
   ::= {pr1646v2ATMFwVpEntry 619728896}

pr1646v2ATMFwVpOamF4EteRxpmClr OBJECT-TYPE
   SYNTAX      Integer32
   MAX-ACCESS  read-only
   STATUS      current
   DESCRIPTION
      "Path: atm.performance.vp.oamF4.endToEnd.pmRxStats.cellLossRatio

       formula = 1000000000 / ; 1000000000 *"
   ::= {pr1646v2ATMFwVpEntry 619732992}

pr1646v2ATMFwVpOamF4EteRxpmCmr OBJECT-TYPE
   SYNTAX      Integer32
   MAX-ACCESS  read-only
   STATUS      current
   DESCRIPTION
      "Path: atm.performance.vp.oamF4.endToEnd.pmRxStats.cellMisinsertRatio

       unit name = misinserts/sec
       formula = 1000000000 / ; 1000000000 *"
   ::= {pr1646v2ATMFwVpEntry 619737088}

pr1646v2ATMFwVpOamF4EteRxpmSecb OBJECT-TYPE
   SYNTAX      Integer32
   MAX-ACCESS  read-only
   STATUS      current
   DESCRIPTION
      "Path: atm.performance.vp.oamF4.endToEnd.pmRxStats.sevErrCellBlckRatio

       formula = 1000000000 / ; 1000000000 *"
   ::= {pr1646v2ATMFwVpEntry 619741184}

pr1646v2ATMFwVpOamF4EteTxpmNLOC OBJECT-TYPE
   SYNTAX      Gauge32
   MAX-ACCESS  read-only
   STATUS      current
   DESCRIPTION
      "Path: atm.performance.vp.oamF4.endToEnd.pmTxStats.lostOamCells

       32 bit unsigned gauge value."
   ::= {pr1646v2ATMFwVpEntry 620761088}

pr1646v2ATMFwVpOamF4EteTxpmNLUC OBJECT-TYPE
   SYNTAX      Gauge32
   MAX-ACCESS  read-only
   STATUS      current
   DESCRIPTION
      "Path: atm.performance.vp.oamF4.endToEnd.pmTxStats.lostUserCells

       32 bit unsigned gauge value."
   ::= {pr1646v2ATMFwVpEntry 620765184}

pr1646v2ATMFwVpOamF4EteTxpmNEUC OBJECT-TYPE
   SYNTAX      Gauge32
   MAX-ACCESS  read-only
   STATUS      current
   DESCRIPTION
      "Path: atm.performance.vp.oamF4.endToEnd.pmTxStats.errUserCells

       32 bit unsigned gauge value."
   ::= {pr1646v2ATMFwVpEntry 620769280}

pr1646v2ATMFwVpOamF4EteTxpmNMUC OBJECT-TYPE
   SYNTAX      Gauge32
   MAX-ACCESS  read-only
   STATUS      current
   DESCRIPTION
      "Path: atm.performance.vp.oamF4.endToEnd.pmTxStats.misInsertUserCells

       32 bit unsigned gauge value."
   ::= {pr1646v2ATMFwVpEntry 620773376}

pr1646v2ATMFwVpOamF4EteTxpmCer OBJECT-TYPE
   SYNTAX      Integer32
   MAX-ACCESS  read-only
   STATUS      current
   DESCRIPTION
      "Path: atm.performance.vp.oamF4.endToEnd.pmTxStats.cellErrRatio

       formula = 1000000000 / ; 1000000000 *"
   ::= {pr1646v2ATMFwVpEntry 620777472}

pr1646v2ATMFwVpOamF4EteTxpmClr OBJECT-TYPE
   SYNTAX      Integer32
   MAX-ACCESS  read-only
   STATUS      current
   DESCRIPTION
      "Path: atm.performance.vp.oamF4.endToEnd.pmTxStats.cellLossRatio

       formula = 1000000000 / ; 1000000000 *"
   ::= {pr1646v2ATMFwVpEntry 620781568}

pr1646v2ATMFwVpOamF4EteTxpmCmr OBJECT-TYPE
   SYNTAX      Integer32
   MAX-ACCESS  read-only
   STATUS      current
   DESCRIPTION
      "Path: atm.performance.vp.oamF4.endToEnd.pmTxStats.cellMisinsertRatio

       unit name = misinserts/sec
       formula = 1000000000 / ; 1000000000 *"
   ::= {pr1646v2ATMFwVpEntry 620785664}

pr1646v2ATMFwVpOamF4EteTxpmSecb OBJECT-TYPE
   SYNTAX      Integer32
   MAX-ACCESS  read-only
   STATUS      current
   DESCRIPTION
      "Path: atm.performance.vp.oamF4.endToEnd.pmTxStats.sevErrCellBlckRatio

       formula = 1000000000 / ; 1000000000 *"
   ::= {pr1646v2ATMFwVpEntry 620789760}


pr1646v2ATMFwPer OBJECT IDENTIFIER ::= {pr1646v2ATMFw 3}

pr1646v2ATMFwPerSSCTable OBJECT-TYPE
   SYNTAX      SEQUENCE OF Pr1646v2ATMFwPerEntry
   MAX-ACCESS  not-accessible
   STATUS      current
   DESCRIPTION
      ""
   ::= {pr1646v2ATMFwPer 1}

pr1646v2ATMFwPerEntry OBJECT-TYPE
   SYNTAX      Pr1646v2ATMFwPerEntry
   MAX-ACCESS  not-accessible
   STATUS      current
   DESCRIPTION
      ""
   INDEX      { pr1646v2ATMFwPerGlobalIx,
                pr1646v2ATMFwPerTableIx }
   ::= {pr1646v2ATMFwPerSSCTable 1}

Pr1646v2ATMFwPerEntry ::=
   SEQUENCE
      {
      pr1646v2ATMFwPerGlobalIx
         GlobalIndex,
      pr1646v2ATMFwPerTableIx
         TableIndex,
      pr1646v2ATMFwPerName
         DisplayString,
      pr1646v2ATMFwPerMCInOctets
         Counter64,
      pr1646v2ATMFwPerMCInUcast
         Counter64,
      pr1646v2ATMFwPerMCInNUcastPkts
         Counter64,
      pr1646v2ATMFwPerMCInBcastPkts
         Counter64,
      pr1646v2ATMFwPerMCInMcastPkts
         Counter64,
      pr1646v2ATMFwPerMCInDiscards
         Counter64,
      pr1646v2ATMFwPerMCInErrors
         Counter64,
      pr1646v2ATMFwPerMCInUnknownProtos
         Counter64,
      pr1646v2ATMFwPerMCInDropEx
         Counter64,
      pr1646v2ATMFwPerMCInDropNoMac
         Counter64,
      pr1646v2ATMFwPerMCInDropNUCast
         Counter64,
      pr1646v2ATMFwPerMCInDropFilter
         Counter64,
      pr1646v2ATMFwPerMCInBandwidth15sec
         Integer32,
      pr1646v2ATMFwPerMCInBandwidth30sec
         Integer32,
      pr1646v2ATMFwPerMCInBandwidth1min
         Integer32,
      pr1646v2ATMFwPerMCInBandwidth2min
         Integer32,
      pr1646v2ATMFwPerMCInBandwidth5min
         Integer32,
      pr1646v2ATMFwPerMCOutOctets
         Counter64,
      pr1646v2ATMFwPerMCOutUcastPkts
         Counter64,
      pr1646v2ATMFwPerMCOutNUcastPkts
         Counter64,
      pr1646v2ATMFwPerMCOutBcastPkts
         Counter64,
      pr1646v2ATMFwPerMCOutMcastPkts
         Counter64,
      pr1646v2ATMFwPerMCOutDiscards
         Counter64,
      pr1646v2ATMFwPerMCOutErrors
         Counter64,
      pr1646v2ATMFwPerMCOutQLen
         Counter32,
      pr1646v2ATMFwPerMCOutDropEx
         Counter64,
      pr1646v2ATMFwPerMCOutDropNoArp
         Counter64,
      pr1646v2ATMFwPerMCOutDropFilter
         Counter64,
      pr1646v2ATMFwPerMCOutBandwidth15sec
         Integer32,
      pr1646v2ATMFwPerMCOutBandwidth30sec
         Integer32,
      pr1646v2ATMFwPerMCOutBandwidth1min
         Integer32,
      pr1646v2ATMFwPerMCOutBandwidth2min
         Integer32,
      pr1646v2ATMFwPerMCOutBandwidth5min
         Integer32,
      pr1646v2ATMFwPerAtmVpi
         Integer32,
      pr1646v2ATMFwPerAtmVci
         Integer32,
      pr1646v2ATMFwPerAtmF5SegLbRx
         Gauge32,
      pr1646v2ATMFwPerAtmF5SegLbTx
         Gauge32,
      pr1646v2ATMFwPerAtmF5SegCcRx
         Gauge32,
      pr1646v2ATMFwPerAtmF5SegCcTx
         Gauge32,
      pr1646v2ATMFwPerAtmF5SegFpmRx
         Gauge32,
      pr1646v2ATMFwPerAtmF5SegFpmTx
         Gauge32,
      pr1646v2ATMFwPerAtmF5SegBrRx
         Gauge32,
      pr1646v2ATMFwPerAtmF5SegBrTx
         Gauge32,
      pr1646v2ATMFwPerAtmF5SegAdRx
         Gauge32,
      pr1646v2ATMFwPerAtmF5SegAdTx
         Gauge32,
      pr1646v2ATMFwPerAtmF5SegAisRx
         Gauge32,
      pr1646v2ATMFwPerAtmF5SegAisTx
         Gauge32,
      pr1646v2ATMFwPerAtmF5SegRdiRx
         Gauge32,
      pr1646v2ATMFwPerAtmF5SegRdiTx
         Gauge32,
      pr1646v2ATMFwPerAtmF5SegRxpmNLOC
         Gauge32,
      pr1646v2ATMFwPerAtmF5SegRxpmNLUC
         Gauge32,
      pr1646v2ATMFwPerAtmF5SegRxpmNEUC
         Gauge32,
      pr1646v2ATMFwPerAtmF5SegRxpmNMUC
         Gauge32,
      pr1646v2ATMFwPerAtmF5SegRxpmCer
         Integer32,
      pr1646v2ATMFwPerAtmF5SegRxpmClr
         Integer32,
      pr1646v2ATMFwPerAtmF5SegRxpmCmr
         Integer32,
      pr1646v2ATMFwPerAtmF5SegRxpmSecb
         Integer32,
      pr1646v2ATMFwPerAtmF5SegTxpmNLOC
         Gauge32,
      pr1646v2ATMFwPerAtmF5SegTxpmNLUC
         Gauge32,
      pr1646v2ATMFwPerAtmF5SegTxpmNEUC
         Gauge32,
      pr1646v2ATMFwPerAtmF5SegTxpmNMUC
         Gauge32,
      pr1646v2ATMFwPerAtmF5SegTxpmCer
         Integer32,
      pr1646v2ATMFwPerAtmF5SegTxpmClr
         Integer32,
      pr1646v2ATMFwPerAtmF5SegTxpmCmr
         Integer32,
      pr1646v2ATMFwPerAtmF5SegTxpmSecb
         Integer32,
      pr1646v2ATMFwPerAtmF5EteLbRx
         Gauge32,
      pr1646v2ATMFwPerAtmF5EteLbTx
         Gauge32,
      pr1646v2ATMFwPerAtmF5EteCcRx
         Gauge32,
      pr1646v2ATMFwPerAtmF5EteCcTx
         Gauge32,
      pr1646v2ATMFwPerAtmF5EteFpmRx
         Gauge32,
      pr1646v2ATMFwPerAtmF5EteFpmTx
         Gauge32,
      pr1646v2ATMFwPerAtmF5EteBrRx
         Gauge32,
      pr1646v2ATMFwPerAtmF5EteBrTx
         Gauge32,
      pr1646v2ATMFwPerAtmF5EteAdRx
         Gauge32,
      pr1646v2ATMFwPerAtmF5EteAdTx
         Gauge32,
      pr1646v2ATMFwPerAtmF5EteAisRx
         Gauge32,
      pr1646v2ATMFwPerAtmF5EteAisTx
         Gauge32,
      pr1646v2ATMFwPerAtmF5EteRdiRx
         Gauge32,
      pr1646v2ATMFwPerAtmF5EteRdiTx
         Gauge32,
      pr1646v2ATMFwPerAtmF5EteRxpmNLOC
         Gauge32,
      pr1646v2ATMFwPerAtmF5EteRxpmNLUC
         Gauge32,
      pr1646v2ATMFwPerAtmF5EteRxpmNEUC
         Gauge32,
      pr1646v2ATMFwPerAtmF5EteRxpmNMUC
         Gauge32,
      pr1646v2ATMFwPerAtmF5EteRxpmCer
         Integer32,
      pr1646v2ATMFwPerAtmF5EteRxpmClr
         Integer32,
      pr1646v2ATMFwPerAtmF5EteRxpmCmr
         Integer32,
      pr1646v2ATMFwPerAtmF5EteRxpmSecb
         Integer32,
      pr1646v2ATMFwPerAtmF5EteTxpmNLOC
         Gauge32,
      pr1646v2ATMFwPerAtmF5EteTxpmNLUC
         Gauge32,
      pr1646v2ATMFwPerAtmF5EteTxpmNEUC
         Gauge32,
      pr1646v2ATMFwPerAtmF5EteTxpmNMUC
         Gauge32,
      pr1646v2ATMFwPerAtmF5EteTxpmCer
         Integer32,
      pr1646v2ATMFwPerAtmF5EteTxpmClr
         Integer32,
      pr1646v2ATMFwPerAtmF5EteTxpmCmr
         Integer32,
      pr1646v2ATMFwPerAtmF5EteTxpmSecb
         Integer32,
      pr1646v2ATMFwPerAtmPppLinkMonitoringRequestsSent
         Gauge32,
      pr1646v2ATMFwPerAtmPppLinkMonitoringRepliesRcvd
         Gauge32,
      pr1646v2ATMFwPerAtmPppLinkMonitoringRequestsRcvd
         Gauge32,
      pr1646v2ATMFwPerAtmPppLinkMonitoringRepliesSent
         Gauge32,
      pr1646v2ATMFwPerFrLmiInStatusEnq
         Counter32,
      pr1646v2ATMFwPerFrLmiInStatus
         Counter32,
      pr1646v2ATMFwPerFrLmiInStatUpdate
         Counter32,
      pr1646v2ATMFwPerFrLmiOutStatusEnq
         Counter32,
      pr1646v2ATMFwPerFrLmiOutStatus
         Counter32,
      pr1646v2ATMFwPerFrLmiOutStatUpdate
         Counter32,
      pr1646v2ATMFwPerFrLmiNetPollNotRcvd
         Counter32,
      pr1646v2ATMFwPerFrLmiUsrNoRespRcvd
         Counter32,
      pr1646v2ATMFwPerFrLmiUsrBadRespRcvd
         Counter32
      }

pr1646v2ATMFwPerGlobalIx OBJECT-TYPE
   SYNTAX      GlobalIndex
   MAX-ACCESS  not-accessible
   STATUS      current
   DESCRIPTION
      "The value of the tlsCntTreeGlobalIndex of the MANAGED OBJECT."
   ::= {pr1646v2ATMFwPerEntry 10}

pr1646v2ATMFwPerTableIx OBJECT-TYPE
   SYNTAX      TableIndex
   MAX-ACCESS  not-accessible
   STATUS      current
   DESCRIPTION
      ""
   ::= {pr1646v2ATMFwPerEntry 11}

pr1646v2ATMFwPerName OBJECT-TYPE
   SYNTAX      DisplayString
   MAX-ACCESS  read-only
   STATUS      current
   DESCRIPTION
      "Path: atm.performance.pvcTable.name"
   ::= {pr1646v2ATMFwPerEntry 16777216}

pr1646v2ATMFwPerMCInOctets OBJECT-TYPE
   SYNTAX      Counter64
   MAX-ACCESS  read-only
   STATUS      current
   DESCRIPTION
      "Path: atm.performance.pvcTable.mibCounters.ifInOctets

       64 bit unsigned wrappable counter."
   ::= {pr1646v2ATMFwPerEntry 40697856}

pr1646v2ATMFwPerMCInUcast OBJECT-TYPE
   SYNTAX      Counter64
   MAX-ACCESS  read-only
   STATUS      current
   DESCRIPTION
      "Path: atm.performance.pvcTable.mibCounters.ifInUcastPkts

       64 bit unsigned wrappable counter."
   ::= {pr1646v2ATMFwPerEntry 40763392}

pr1646v2ATMFwPerMCInNUcastPkts OBJECT-TYPE
   SYNTAX      Counter64
   MAX-ACCESS  read-only
   STATUS      current
   DESCRIPTION
      "Path: atm.performance.pvcTable.mibCounters.ifInNUcastPkts

       64 bit unsigned wrappable counter."
   ::= {pr1646v2ATMFwPerEntry 40828928}

pr1646v2ATMFwPerMCInBcastPkts OBJECT-TYPE
   SYNTAX      Counter64
   MAX-ACCESS  read-only
   STATUS      current
   DESCRIPTION
      "Path: atm.performance.pvcTable.mibCounters.ifInBcastPkts

       64 bit unsigned wrappable counter."
   ::= {pr1646v2ATMFwPerEntry 47382528}

pr1646v2ATMFwPerMCInMcastPkts OBJECT-TYPE
   SYNTAX      Counter64
   MAX-ACCESS  read-only
   STATUS      current
   DESCRIPTION
      "Path: atm.performance.pvcTable.mibCounters.ifInMcastPkts

       64 bit unsigned wrappable counter."
   ::= {pr1646v2ATMFwPerEntry 48037888}

pr1646v2ATMFwPerMCInDiscards OBJECT-TYPE
   SYNTAX      Counter64
   MAX-ACCESS  read-only
   STATUS      current
   DESCRIPTION
      "Path: atm.performance.pvcTable.mibCounters.ifInDiscards

       64 bit unsigned wrappable counter."
   ::= {pr1646v2ATMFwPerEntry 40894464}

pr1646v2ATMFwPerMCInErrors OBJECT-TYPE
   SYNTAX      Counter64
   MAX-ACCESS  read-only
   STATUS      current
   DESCRIPTION
      "Path: atm.performance.pvcTable.mibCounters.ifInErrors

       64 bit unsigned wrappable counter."
   ::= {pr1646v2ATMFwPerEntry 40960000}

pr1646v2ATMFwPerMCInUnknownProtos OBJECT-TYPE
   SYNTAX      Counter64
   MAX-ACCESS  read-only
   STATUS      current
   DESCRIPTION
      "Path: atm.performance.pvcTable.mibCounters.ifInUnknownProtos

       64 bit unsigned wrappable counter."
   ::= {pr1646v2ATMFwPerEntry 41025536}

pr1646v2ATMFwPerMCInDropEx OBJECT-TYPE
   SYNTAX      Counter64
   MAX-ACCESS  read-only
   STATUS      current
   DESCRIPTION
      "Path: atm.performance.pvcTable.mibCounters.ifInDropLevelExceeded

       64 bit unsigned wrappable counter."
   ::= {pr1646v2ATMFwPerEntry 42074112}

pr1646v2ATMFwPerMCInDropNoMac OBJECT-TYPE
   SYNTAX      Counter64
   MAX-ACCESS  read-only
   STATUS      current
   DESCRIPTION
      "Path: atm.performance.pvcTable.mibCounters.ifInDiscardsNoMacFit

       64 bit unsigned wrappable counter."
   ::= {pr1646v2ATMFwPerEntry 42270720}

pr1646v2ATMFwPerMCInDropNUCast OBJECT-TYPE
   SYNTAX      Counter64
   MAX-ACCESS  read-only
   STATUS      current
   DESCRIPTION
      "Path: atm.performance.pvcTable.mibCounters.ifInDiscardsNUCast

       64 bit unsigned wrappable counter."
   ::= {pr1646v2ATMFwPerEntry 42467328}

pr1646v2ATMFwPerMCInDropFilter OBJECT-TYPE
   SYNTAX      Counter64
   MAX-ACCESS  read-only
   STATUS      current
   DESCRIPTION
      "Path: atm.performance.pvcTable.mibCounters.ifInDiscardsFilter

       64 bit unsigned wrappable counter."
   ::= {pr1646v2ATMFwPerEntry 42532864}

pr1646v2ATMFwPerMCInBandwidth15sec OBJECT-TYPE
   SYNTAX      Integer32
   MAX-ACCESS  read-only
   STATUS      current
   DESCRIPTION
      "Path: atm.performance.pvcTable.mibCounters.ifInBandwidth.15sec

       unit name = bps
       formula = 8 * ; 8 /"
   ::= {pr1646v2ATMFwPerEntry 45417728}

pr1646v2ATMFwPerMCInBandwidth30sec OBJECT-TYPE
   SYNTAX      Integer32
   MAX-ACCESS  read-only
   STATUS      current
   DESCRIPTION
      "Path: atm.performance.pvcTable.mibCounters.ifInBandwidth.30sec

       unit name = bps
       formula = 8 * ; 8 /"
   ::= {pr1646v2ATMFwPerEntry 45419008}

pr1646v2ATMFwPerMCInBandwidth1min OBJECT-TYPE
   SYNTAX      Integer32
   MAX-ACCESS  read-only
   STATUS      current
   DESCRIPTION
      "Path: atm.performance.pvcTable.mibCounters.ifInBandwidth.1min

       unit name = bps
       formula = 8 * ; 8 /"
   ::= {pr1646v2ATMFwPerEntry 45421568}

pr1646v2ATMFwPerMCInBandwidth2min OBJECT-TYPE
   SYNTAX      Integer32
   MAX-ACCESS  read-only
   STATUS      current
   DESCRIPTION
      "Path: atm.performance.pvcTable.mibCounters.ifInBandwidth.2min

       unit name = bps
       formula = 8 * ; 8 /"
   ::= {pr1646v2ATMFwPerEntry 45426688}

pr1646v2ATMFwPerMCInBandwidth5min OBJECT-TYPE
   SYNTAX      Integer32
   MAX-ACCESS  read-only
   STATUS      current
   DESCRIPTION
      "Path: atm.performance.pvcTable.mibCounters.ifInBandwidth.5min

       unit name = bps
       formula = 8 * ; 8 /"
   ::= {pr1646v2ATMFwPerEntry 45442048}

pr1646v2ATMFwPerMCOutOctets OBJECT-TYPE
   SYNTAX      Counter64
   MAX-ACCESS  read-only
   STATUS      current
   DESCRIPTION
      "Path: atm.performance.pvcTable.mibCounters.ifOutOctets

       64 bit unsigned wrappable counter."
   ::= {pr1646v2ATMFwPerEntry 41091072}

pr1646v2ATMFwPerMCOutUcastPkts OBJECT-TYPE
   SYNTAX      Counter64
   MAX-ACCESS  read-only
   STATUS      current
   DESCRIPTION
      "Path: atm.performance.pvcTable.mibCounters.ifOutUcastPkts

       64 bit unsigned wrappable counter."
   ::= {pr1646v2ATMFwPerEntry 41156608}

pr1646v2ATMFwPerMCOutNUcastPkts OBJECT-TYPE
   SYNTAX      Counter64
   MAX-ACCESS  read-only
   STATUS      current
   DESCRIPTION
      "Path: atm.performance.pvcTable.mibCounters.ifOutNUcastPkts

       64 bit unsigned wrappable counter."
   ::= {pr1646v2ATMFwPerEntry 41222144}

pr1646v2ATMFwPerMCOutBcastPkts OBJECT-TYPE
   SYNTAX      Counter64
   MAX-ACCESS  read-only
   STATUS      current
   DESCRIPTION
      "Path: atm.performance.pvcTable.mibCounters.ifOutBcastPkts

       64 bit unsigned wrappable counter."
   ::= {pr1646v2ATMFwPerEntry 47775744}

pr1646v2ATMFwPerMCOutMcastPkts OBJECT-TYPE
   SYNTAX      Counter64
   MAX-ACCESS  read-only
   STATUS      current
   DESCRIPTION
      "Path: atm.performance.pvcTable.mibCounters.ifOutMcastPkts

       64 bit unsigned wrappable counter."
   ::= {pr1646v2ATMFwPerEntry 48431104}

pr1646v2ATMFwPerMCOutDiscards OBJECT-TYPE
   SYNTAX      Counter64
   MAX-ACCESS  read-only
   STATUS      current
   DESCRIPTION
      "Path: atm.performance.pvcTable.mibCounters.ifOutDiscards

       64 bit unsigned wrappable counter."
   ::= {pr1646v2ATMFwPerEntry 41287680}

pr1646v2ATMFwPerMCOutErrors OBJECT-TYPE
   SYNTAX      Counter64
   MAX-ACCESS  read-only
   STATUS      current
   DESCRIPTION
      "Path: atm.performance.pvcTable.mibCounters.ifOutErrors

       64 bit unsigned wrappable counter."
   ::= {pr1646v2ATMFwPerEntry 41353216}

pr1646v2ATMFwPerMCOutQLen OBJECT-TYPE
   SYNTAX      Counter32
   MAX-ACCESS  read-only
   STATUS      current
   DESCRIPTION
      "Path: atm.performance.pvcTable.mibCounters.ifOutQLen

       32 bit unsigned wrappable counter."
   ::= {pr1646v2ATMFwPerEntry 41418752}

pr1646v2ATMFwPerMCOutDropEx OBJECT-TYPE
   SYNTAX      Counter64
   MAX-ACCESS  read-only
   STATUS      current
   DESCRIPTION
      "Path: atm.performance.pvcTable.mibCounters.ifOutDropLevelExceeded

       64 bit unsigned wrappable counter."
   ::= {pr1646v2ATMFwPerEntry 41484288}

pr1646v2ATMFwPerMCOutDropNoArp OBJECT-TYPE
   SYNTAX      Counter64
   MAX-ACCESS  read-only
   STATUS      current
   DESCRIPTION
      "Path: atm.performance.pvcTable.mibCounters.ifOutDiscardsNoArp

       64 bit unsigned wrappable counter."
   ::= {pr1646v2ATMFwPerEntry 42336256}

pr1646v2ATMFwPerMCOutDropFilter OBJECT-TYPE
   SYNTAX      Counter64
   MAX-ACCESS  read-only
   STATUS      current
   DESCRIPTION
      "Path: atm.performance.pvcTable.mibCounters.ifOutDiscardsFilter

       64 bit unsigned wrappable counter."
   ::= {pr1646v2ATMFwPerEntry 42598400}

pr1646v2ATMFwPerMCOutBandwidth15sec OBJECT-TYPE
   SYNTAX      Integer32
   MAX-ACCESS  read-only
   STATUS      current
   DESCRIPTION
      "Path: atm.performance.pvcTable.mibCounters.ifOutBandwidth.15sec

       unit name = bps
       formula = 8 * ; 8 /"
   ::= {pr1646v2ATMFwPerEntry 45483264}

pr1646v2ATMFwPerMCOutBandwidth30sec OBJECT-TYPE
   SYNTAX      Integer32
   MAX-ACCESS  read-only
   STATUS      current
   DESCRIPTION
      "Path: atm.performance.pvcTable.mibCounters.ifOutBandwidth.30sec

       unit name = bps
       formula = 8 * ; 8 /"
   ::= {pr1646v2ATMFwPerEntry 45484544}

pr1646v2ATMFwPerMCOutBandwidth1min OBJECT-TYPE
   SYNTAX      Integer32
   MAX-ACCESS  read-only
   STATUS      current
   DESCRIPTION
      "Path: atm.performance.pvcTable.mibCounters.ifOutBandwidth.1min

       unit name = bps
       formula = 8 * ; 8 /"
   ::= {pr1646v2ATMFwPerEntry 45487104}

pr1646v2ATMFwPerMCOutBandwidth2min OBJECT-TYPE
   SYNTAX      Integer32
   MAX-ACCESS  read-only
   STATUS      current
   DESCRIPTION
      "Path: atm.performance.pvcTable.mibCounters.ifOutBandwidth.2min

       unit name = bps
       formula = 8 * ; 8 /"
   ::= {pr1646v2ATMFwPerEntry 45492224}

pr1646v2ATMFwPerMCOutBandwidth5min OBJECT-TYPE
   SYNTAX      Integer32
   MAX-ACCESS  read-only
   STATUS      current
   DESCRIPTION
      "Path: atm.performance.pvcTable.mibCounters.ifOutBandwidth.5min

       unit name = bps
       formula = 8 * ; 8 /"
   ::= {pr1646v2ATMFwPerEntry 45507584}

pr1646v2ATMFwPerAtmVpi OBJECT-TYPE
   SYNTAX      Integer32
   MAX-ACCESS  read-only
   STATUS      current
   DESCRIPTION
      "Path: atm.performance.pvcTable.atm.vpi"
   ::= {pr1646v2ATMFwPerEntry 286261248}

pr1646v2ATMFwPerAtmVci OBJECT-TYPE
   SYNTAX      Integer32
   MAX-ACCESS  read-only
   STATUS      current
   DESCRIPTION
      "Path: atm.performance.pvcTable.atm.vci"
   ::= {pr1646v2ATMFwPerEntry 287309824}

pr1646v2ATMFwPerAtmF5SegLbRx OBJECT-TYPE
   SYNTAX      Gauge32
   MAX-ACCESS  read-only
   STATUS      current
   DESCRIPTION
      "Path: atm.performance.pvcTable.atm.oamF5.segment.lbRx

       32 bit unsigned gauge value."
   ::= {pr1646v2ATMFwPerEntry 288493568}

pr1646v2ATMFwPerAtmF5SegLbTx OBJECT-TYPE
   SYNTAX      Gauge32
   MAX-ACCESS  read-only
   STATUS      current
   DESCRIPTION
      "Path: atm.performance.pvcTable.atm.oamF5.segment.lbTx

       32 bit unsigned gauge value."
   ::= {pr1646v2ATMFwPerEntry 288497664}

pr1646v2ATMFwPerAtmF5SegCcRx OBJECT-TYPE
   SYNTAX      Gauge32
   MAX-ACCESS  read-only
   STATUS      current
   DESCRIPTION
      "Path: atm.performance.pvcTable.atm.oamF5.segment.ccRx

       32 bit unsigned gauge value."
   ::= {pr1646v2ATMFwPerEntry 288501760}

pr1646v2ATMFwPerAtmF5SegCcTx OBJECT-TYPE
   SYNTAX      Gauge32
   MAX-ACCESS  read-only
   STATUS      current
   DESCRIPTION
      "Path: atm.performance.pvcTable.atm.oamF5.segment.ccTx

       32 bit unsigned gauge value."
   ::= {pr1646v2ATMFwPerEntry 288505856}

pr1646v2ATMFwPerAtmF5SegFpmRx OBJECT-TYPE
   SYNTAX      Gauge32
   MAX-ACCESS  read-only
   STATUS      current
   DESCRIPTION
      "Path: atm.performance.pvcTable.atm.oamF5.segment.fpmRx

       32 bit unsigned gauge value."
   ::= {pr1646v2ATMFwPerEntry 288509952}

pr1646v2ATMFwPerAtmF5SegFpmTx OBJECT-TYPE
   SYNTAX      Gauge32
   MAX-ACCESS  read-only
   STATUS      current
   DESCRIPTION
      "Path: atm.performance.pvcTable.atm.oamF5.segment.fpmTx

       32 bit unsigned gauge value."
   ::= {pr1646v2ATMFwPerEntry 288514048}

pr1646v2ATMFwPerAtmF5SegBrRx OBJECT-TYPE
   SYNTAX      Gauge32
   MAX-ACCESS  read-only
   STATUS      current
   DESCRIPTION
      "Path: atm.performance.pvcTable.atm.oamF5.segment.brRx

       32 bit unsigned gauge value."
   ::= {pr1646v2ATMFwPerEntry 288518144}

pr1646v2ATMFwPerAtmF5SegBrTx OBJECT-TYPE
   SYNTAX      Gauge32
   MAX-ACCESS  read-only
   STATUS      current
   DESCRIPTION
      "Path: atm.performance.pvcTable.atm.oamF5.segment.brTx

       32 bit unsigned gauge value."
   ::= {pr1646v2ATMFwPerEntry 288522240}

pr1646v2ATMFwPerAtmF5SegAdRx OBJECT-TYPE
   SYNTAX      Gauge32
   MAX-ACCESS  read-only
   STATUS      current
   DESCRIPTION
      "Path: atm.performance.pvcTable.atm.oamF5.segment.actDeactRx

       32 bit unsigned gauge value."
   ::= {pr1646v2ATMFwPerEntry 288526336}

pr1646v2ATMFwPerAtmF5SegAdTx OBJECT-TYPE
   SYNTAX      Gauge32
   MAX-ACCESS  read-only
   STATUS      current
   DESCRIPTION
      "Path: atm.performance.pvcTable.atm.oamF5.segment.actDeactTx

       32 bit unsigned gauge value."
   ::= {pr1646v2ATMFwPerEntry 288530432}

pr1646v2ATMFwPerAtmF5SegAisRx OBJECT-TYPE
   SYNTAX      Gauge32
   MAX-ACCESS  read-only
   STATUS      current
   DESCRIPTION
      "Path: atm.performance.pvcTable.atm.oamF5.segment.aisRx

       32 bit unsigned gauge value."
   ::= {pr1646v2ATMFwPerEntry 288534528}

pr1646v2ATMFwPerAtmF5SegAisTx OBJECT-TYPE
   SYNTAX      Gauge32
   MAX-ACCESS  read-only
   STATUS      current
   DESCRIPTION
      "Path: atm.performance.pvcTable.atm.oamF5.segment.aisTx

       32 bit unsigned gauge value."
   ::= {pr1646v2ATMFwPerEntry 288538624}

pr1646v2ATMFwPerAtmF5SegRdiRx OBJECT-TYPE
   SYNTAX      Gauge32
   MAX-ACCESS  read-only
   STATUS      current
   DESCRIPTION
      "Path: atm.performance.pvcTable.atm.oamF5.segment.rdiRx

       32 bit unsigned gauge value."
   ::= {pr1646v2ATMFwPerEntry 288542720}

pr1646v2ATMFwPerAtmF5SegRdiTx OBJECT-TYPE
   SYNTAX      Gauge32
   MAX-ACCESS  read-only
   STATUS      current
   DESCRIPTION
      "Path: atm.performance.pvcTable.atm.oamF5.segment.rdiTx

       32 bit unsigned gauge value."
   ::= {pr1646v2ATMFwPerEntry 288546816}

pr1646v2ATMFwPerAtmF5SegRxpmNLOC OBJECT-TYPE
   SYNTAX      Gauge32
   MAX-ACCESS  read-only
   STATUS      current
   DESCRIPTION
      "Path: atm.performance.pvcTable.atm.oamF5.segment.pmRxStats.lostOamCells

       32 bit unsigned gauge value."
   ::= {pr1646v2ATMFwPerEntry 288550928}

pr1646v2ATMFwPerAtmF5SegRxpmNLUC OBJECT-TYPE
   SYNTAX      Gauge32
   MAX-ACCESS  read-only
   STATUS      current
   DESCRIPTION
      "Path: atm.performance.pvcTable.atm.oamF5.segment.pmRxStats.lostUserCells

       32 bit unsigned gauge value."
   ::= {pr1646v2ATMFwPerEntry 288550944}

pr1646v2ATMFwPerAtmF5SegRxpmNEUC OBJECT-TYPE
   SYNTAX      Gauge32
   MAX-ACCESS  read-only
   STATUS      current
   DESCRIPTION
      "Path: atm.performance.pvcTable.atm.oamF5.segment.pmRxStats.errUserCells

       32 bit unsigned gauge value."
   ::= {pr1646v2ATMFwPerEntry 288550960}

pr1646v2ATMFwPerAtmF5SegRxpmNMUC OBJECT-TYPE
   SYNTAX      Gauge32
   MAX-ACCESS  read-only
   STATUS      current
   DESCRIPTION
      "Path: atm.performance.pvcTable.atm.oamF5.segment.pmRxStats.misInsertUserCells

       32 bit unsigned gauge value."
   ::= {pr1646v2ATMFwPerEntry 288550976}

pr1646v2ATMFwPerAtmF5SegRxpmCer OBJECT-TYPE
   SYNTAX      Integer32
   MAX-ACCESS  read-only
   STATUS      current
   DESCRIPTION
      "Path: atm.performance.pvcTable.atm.oamF5.segment.pmRxStats.cellErrRatio

       formula = 1000000000 / ; 1000000000 *"
   ::= {pr1646v2ATMFwPerEntry 288550992}

pr1646v2ATMFwPerAtmF5SegRxpmClr OBJECT-TYPE
   SYNTAX      Integer32
   MAX-ACCESS  read-only
   STATUS      current
   DESCRIPTION
      "Path: atm.performance.pvcTable.atm.oamF5.segment.pmRxStats.cellLossRatio

       formula = 1000000000 / ; 1000000000 *"
   ::= {pr1646v2ATMFwPerEntry 288551008}

pr1646v2ATMFwPerAtmF5SegRxpmCmr OBJECT-TYPE
   SYNTAX      Integer32
   MAX-ACCESS  read-only
   STATUS      current
   DESCRIPTION
      "Path: atm.performance.pvcTable.atm.oamF5.segment.pmRxStats.cellMisinsertRatio

       unit name = misinserts/sec
       formula = 1000000000 / ; 1000000000 *"
   ::= {pr1646v2ATMFwPerEntry 288551024}

pr1646v2ATMFwPerAtmF5SegRxpmSecb OBJECT-TYPE
   SYNTAX      Integer32
   MAX-ACCESS  read-only
   STATUS      current
   DESCRIPTION
      "Path: atm.performance.pvcTable.atm.oamF5.segment.pmRxStats.sevErrCellBlckRatio

       formula = 1000000000 / ; 1000000000 *"
   ::= {pr1646v2ATMFwPerEntry 288551040}

pr1646v2ATMFwPerAtmF5SegTxpmNLOC OBJECT-TYPE
   SYNTAX      Gauge32
   MAX-ACCESS  read-only
   STATUS      current
   DESCRIPTION
      "Path: atm.performance.pvcTable.atm.oamF5.segment.pmTxStats.lostOamCells

       32 bit unsigned gauge value."
   ::= {pr1646v2ATMFwPerEntry 288555024}

pr1646v2ATMFwPerAtmF5SegTxpmNLUC OBJECT-TYPE
   SYNTAX      Gauge32
   MAX-ACCESS  read-only
   STATUS      current
   DESCRIPTION
      "Path: atm.performance.pvcTable.atm.oamF5.segment.pmTxStats.lostUserCells

       32 bit unsigned gauge value."
   ::= {pr1646v2ATMFwPerEntry 288555040}

pr1646v2ATMFwPerAtmF5SegTxpmNEUC OBJECT-TYPE
   SYNTAX      Gauge32
   MAX-ACCESS  read-only
   STATUS      current
   DESCRIPTION
      "Path: atm.performance.pvcTable.atm.oamF5.segment.pmTxStats.errUserCells

       32 bit unsigned gauge value."
   ::= {pr1646v2ATMFwPerEntry 288555056}

pr1646v2ATMFwPerAtmF5SegTxpmNMUC OBJECT-TYPE
   SYNTAX      Gauge32
   MAX-ACCESS  read-only
   STATUS      current
   DESCRIPTION
      "Path: atm.performance.pvcTable.atm.oamF5.segment.pmTxStats.misInsertUserCells

       32 bit unsigned gauge value."
   ::= {pr1646v2ATMFwPerEntry 288555072}

pr1646v2ATMFwPerAtmF5SegTxpmCer OBJECT-TYPE
   SYNTAX      Integer32
   MAX-ACCESS  read-only
   STATUS      current
   DESCRIPTION
      "Path: atm.performance.pvcTable.atm.oamF5.segment.pmTxStats.cellErrRatio

       formula = 1000000000 / ; 1000000000 *"
   ::= {pr1646v2ATMFwPerEntry 288555088}

pr1646v2ATMFwPerAtmF5SegTxpmClr OBJECT-TYPE
   SYNTAX      Integer32
   MAX-ACCESS  read-only
   STATUS      current
   DESCRIPTION
      "Path: atm.performance.pvcTable.atm.oamF5.segment.pmTxStats.cellLossRatio

       formula = 1000000000 / ; 1000000000 *"
   ::= {pr1646v2ATMFwPerEntry 288555104}

pr1646v2ATMFwPerAtmF5SegTxpmCmr OBJECT-TYPE
   SYNTAX      Integer32
   MAX-ACCESS  read-only
   STATUS      current
   DESCRIPTION
      "Path: atm.performance.pvcTable.atm.oamF5.segment.pmTxStats.cellMisinsertRatio

       unit name = misinserts/sec
       formula = 1000000000 / ; 1000000000 *"
   ::= {pr1646v2ATMFwPerEntry 288555120}

pr1646v2ATMFwPerAtmF5SegTxpmSecb OBJECT-TYPE
   SYNTAX      Integer32
   MAX-ACCESS  read-only
   STATUS      current
   DESCRIPTION
      "Path: atm.performance.pvcTable.atm.oamF5.segment.pmTxStats.sevErrCellBlckRatio

       formula = 1000000000 / ; 1000000000 *"
   ::= {pr1646v2ATMFwPerEntry 288555136}

pr1646v2ATMFwPerAtmF5EteLbRx OBJECT-TYPE
   SYNTAX      Gauge32
   MAX-ACCESS  read-only
   STATUS      current
   DESCRIPTION
      "Path: atm.performance.pvcTable.atm.oamF5.endToEnd.lbRx

       32 bit unsigned gauge value."
   ::= {pr1646v2ATMFwPerEntry 288624640}

pr1646v2ATMFwPerAtmF5EteLbTx OBJECT-TYPE
   SYNTAX      Gauge32
   MAX-ACCESS  read-only
   STATUS      current
   DESCRIPTION
      "Path: atm.performance.pvcTable.atm.oamF5.endToEnd.lbTx

       32 bit unsigned gauge value."
   ::= {pr1646v2ATMFwPerEntry 288628736}

pr1646v2ATMFwPerAtmF5EteCcRx OBJECT-TYPE
   SYNTAX      Gauge32
   MAX-ACCESS  read-only
   STATUS      current
   DESCRIPTION
      "Path: atm.performance.pvcTable.atm.oamF5.endToEnd.ccRx

       32 bit unsigned gauge value."
   ::= {pr1646v2ATMFwPerEntry 288632832}

pr1646v2ATMFwPerAtmF5EteCcTx OBJECT-TYPE
   SYNTAX      Gauge32
   MAX-ACCESS  read-only
   STATUS      current
   DESCRIPTION
      "Path: atm.performance.pvcTable.atm.oamF5.endToEnd.ccTx

       32 bit unsigned gauge value."
   ::= {pr1646v2ATMFwPerEntry 288636928}

pr1646v2ATMFwPerAtmF5EteFpmRx OBJECT-TYPE
   SYNTAX      Gauge32
   MAX-ACCESS  read-only
   STATUS      current
   DESCRIPTION
      "Path: atm.performance.pvcTable.atm.oamF5.endToEnd.fpmRx

       32 bit unsigned gauge value."
   ::= {pr1646v2ATMFwPerEntry 288641024}

pr1646v2ATMFwPerAtmF5EteFpmTx OBJECT-TYPE
   SYNTAX      Gauge32
   MAX-ACCESS  read-only
   STATUS      current
   DESCRIPTION
      "Path: atm.performance.pvcTable.atm.oamF5.endToEnd.fpmTx

       32 bit unsigned gauge value."
   ::= {pr1646v2ATMFwPerEntry 288645120}

pr1646v2ATMFwPerAtmF5EteBrRx OBJECT-TYPE
   SYNTAX      Gauge32
   MAX-ACCESS  read-only
   STATUS      current
   DESCRIPTION
      "Path: atm.performance.pvcTable.atm.oamF5.endToEnd.brRx

       32 bit unsigned gauge value."
   ::= {pr1646v2ATMFwPerEntry 288649216}

pr1646v2ATMFwPerAtmF5EteBrTx OBJECT-TYPE
   SYNTAX      Gauge32
   MAX-ACCESS  read-only
   STATUS      current
   DESCRIPTION
      "Path: atm.performance.pvcTable.atm.oamF5.endToEnd.brTx

       32 bit unsigned gauge value."
   ::= {pr1646v2ATMFwPerEntry 288653312}

pr1646v2ATMFwPerAtmF5EteAdRx OBJECT-TYPE
   SYNTAX      Gauge32
   MAX-ACCESS  read-only
   STATUS      current
   DESCRIPTION
      "Path: atm.performance.pvcTable.atm.oamF5.endToEnd.actDeactRx

       32 bit unsigned gauge value."
   ::= {pr1646v2ATMFwPerEntry 288657408}

pr1646v2ATMFwPerAtmF5EteAdTx OBJECT-TYPE
   SYNTAX      Gauge32
   MAX-ACCESS  read-only
   STATUS      current
   DESCRIPTION
      "Path: atm.performance.pvcTable.atm.oamF5.endToEnd.actDeactTx

       32 bit unsigned gauge value."
   ::= {pr1646v2ATMFwPerEntry 288661504}

pr1646v2ATMFwPerAtmF5EteAisRx OBJECT-TYPE
   SYNTAX      Gauge32
   MAX-ACCESS  read-only
   STATUS      current
   DESCRIPTION
      "Path: atm.performance.pvcTable.atm.oamF5.endToEnd.aisRx

       32 bit unsigned gauge value."
   ::= {pr1646v2ATMFwPerEntry 288665600}

pr1646v2ATMFwPerAtmF5EteAisTx OBJECT-TYPE
   SYNTAX      Gauge32
   MAX-ACCESS  read-only
   STATUS      current
   DESCRIPTION
      "Path: atm.performance.pvcTable.atm.oamF5.endToEnd.aisTx

       32 bit unsigned gauge value."
   ::= {pr1646v2ATMFwPerEntry 288669696}

pr1646v2ATMFwPerAtmF5EteRdiRx OBJECT-TYPE
   SYNTAX      Gauge32
   MAX-ACCESS  read-only
   STATUS      current
   DESCRIPTION
      "Path: atm.performance.pvcTable.atm.oamF5.endToEnd.rdiRx

       32 bit unsigned gauge value."
   ::= {pr1646v2ATMFwPerEntry 288673792}

pr1646v2ATMFwPerAtmF5EteRdiTx OBJECT-TYPE
   SYNTAX      Gauge32
   MAX-ACCESS  read-only
   STATUS      current
   DESCRIPTION
      "Path: atm.performance.pvcTable.atm.oamF5.endToEnd.rdiTx

       32 bit unsigned gauge value."
   ::= {pr1646v2ATMFwPerEntry 288677888}

pr1646v2ATMFwPerAtmF5EteRxpmNLOC OBJECT-TYPE
   SYNTAX      Gauge32
   MAX-ACCESS  read-only
   STATUS      current
   DESCRIPTION
      "Path: atm.performance.pvcTable.atm.oamF5.endToEnd.pmRxStats.lostOamCells

       32 bit unsigned gauge value."
   ::= {pr1646v2ATMFwPerEntry 288682000}

pr1646v2ATMFwPerAtmF5EteRxpmNLUC OBJECT-TYPE
   SYNTAX      Gauge32
   MAX-ACCESS  read-only
   STATUS      current
   DESCRIPTION
      "Path: atm.performance.pvcTable.atm.oamF5.endToEnd.pmRxStats.lostUserCells

       32 bit unsigned gauge value."
   ::= {pr1646v2ATMFwPerEntry 288682016}

pr1646v2ATMFwPerAtmF5EteRxpmNEUC OBJECT-TYPE
   SYNTAX      Gauge32
   MAX-ACCESS  read-only
   STATUS      current
   DESCRIPTION
      "Path: atm.performance.pvcTable.atm.oamF5.endToEnd.pmRxStats.errUserCells

       32 bit unsigned gauge value."
   ::= {pr1646v2ATMFwPerEntry 288682032}

pr1646v2ATMFwPerAtmF5EteRxpmNMUC OBJECT-TYPE
   SYNTAX      Gauge32
   MAX-ACCESS  read-only
   STATUS      current
   DESCRIPTION
      "Path: atm.performance.pvcTable.atm.oamF5.endToEnd.pmRxStats.misInsertUserCells

       32 bit unsigned gauge value."
   ::= {pr1646v2ATMFwPerEntry 288682048}

pr1646v2ATMFwPerAtmF5EteRxpmCer OBJECT-TYPE
   SYNTAX      Integer32
   MAX-ACCESS  read-only
   STATUS      current
   DESCRIPTION
      "Path: atm.performance.pvcTable.atm.oamF5.endToEnd.pmRxStats.cellErrRatio

       formula = 1000000000 / ; 1000000000 *"
   ::= {pr1646v2ATMFwPerEntry 288682064}

pr1646v2ATMFwPerAtmF5EteRxpmClr OBJECT-TYPE
   SYNTAX      Integer32
   MAX-ACCESS  read-only
   STATUS      current
   DESCRIPTION
      "Path: atm.performance.pvcTable.atm.oamF5.endToEnd.pmRxStats.cellLossRatio

       formula = 1000000000 / ; 1000000000 *"
   ::= {pr1646v2ATMFwPerEntry 288682080}

pr1646v2ATMFwPerAtmF5EteRxpmCmr OBJECT-TYPE
   SYNTAX      Integer32
   MAX-ACCESS  read-only
   STATUS      current
   DESCRIPTION
      "Path: atm.performance.pvcTable.atm.oamF5.endToEnd.pmRxStats.cellMisinsertRatio

       unit name = misinserts/sec
       formula = 1000000000 / ; 1000000000 *"
   ::= {pr1646v2ATMFwPerEntry 288682096}

pr1646v2ATMFwPerAtmF5EteRxpmSecb OBJECT-TYPE
   SYNTAX      Integer32
   MAX-ACCESS  read-only
   STATUS      current
   DESCRIPTION
      "Path: atm.performance.pvcTable.atm.oamF5.endToEnd.pmRxStats.sevErrCellBlckRatio

       formula = 1000000000 / ; 1000000000 *"
   ::= {pr1646v2ATMFwPerEntry 288682112}

pr1646v2ATMFwPerAtmF5EteTxpmNLOC OBJECT-TYPE
   SYNTAX      Gauge32
   MAX-ACCESS  read-only
   STATUS      current
   DESCRIPTION
      "Path: atm.performance.pvcTable.atm.oamF5.endToEnd.pmTxStats.lostOamCells

       32 bit unsigned gauge value."
   ::= {pr1646v2ATMFwPerEntry 288686096}

pr1646v2ATMFwPerAtmF5EteTxpmNLUC OBJECT-TYPE
   SYNTAX      Gauge32
   MAX-ACCESS  read-only
   STATUS      current
   DESCRIPTION
      "Path: atm.performance.pvcTable.atm.oamF5.endToEnd.pmTxStats.lostUserCells

       32 bit unsigned gauge value."
   ::= {pr1646v2ATMFwPerEntry 288686112}

pr1646v2ATMFwPerAtmF5EteTxpmNEUC OBJECT-TYPE
   SYNTAX      Gauge32
   MAX-ACCESS  read-only
   STATUS      current
   DESCRIPTION
      "Path: atm.performance.pvcTable.atm.oamF5.endToEnd.pmTxStats.errUserCells

       32 bit unsigned gauge value."
   ::= {pr1646v2ATMFwPerEntry 288686128}

pr1646v2ATMFwPerAtmF5EteTxpmNMUC OBJECT-TYPE
   SYNTAX      Gauge32
   MAX-ACCESS  read-only
   STATUS      current
   DESCRIPTION
      "Path: atm.performance.pvcTable.atm.oamF5.endToEnd.pmTxStats.misInsertUserCells

       32 bit unsigned gauge value."
   ::= {pr1646v2ATMFwPerEntry 288686144}

pr1646v2ATMFwPerAtmF5EteTxpmCer OBJECT-TYPE
   SYNTAX      Integer32
   MAX-ACCESS  read-only
   STATUS      current
   DESCRIPTION
      "Path: atm.performance.pvcTable.atm.oamF5.endToEnd.pmTxStats.cellErrRatio

       formula = 1000000000 / ; 1000000000 *"
   ::= {pr1646v2ATMFwPerEntry 288686160}

pr1646v2ATMFwPerAtmF5EteTxpmClr OBJECT-TYPE
   SYNTAX      Integer32
   MAX-ACCESS  read-only
   STATUS      current
   DESCRIPTION
      "Path: atm.performance.pvcTable.atm.oamF5.endToEnd.pmTxStats.cellLossRatio

       formula = 1000000000 / ; 1000000000 *"
   ::= {pr1646v2ATMFwPerEntry 288686176}

pr1646v2ATMFwPerAtmF5EteTxpmCmr OBJECT-TYPE
   SYNTAX      Integer32
   MAX-ACCESS  read-only
   STATUS      current
   DESCRIPTION
      "Path: atm.performance.pvcTable.atm.oamF5.endToEnd.pmTxStats.cellMisinsertRatio

       unit name = misinserts/sec
       formula = 1000000000 / ; 1000000000 *"
   ::= {pr1646v2ATMFwPerEntry 288686192}

pr1646v2ATMFwPerAtmF5EteTxpmSecb OBJECT-TYPE
   SYNTAX      Integer32
   MAX-ACCESS  read-only
   STATUS      current
   DESCRIPTION
      "Path: atm.performance.pvcTable.atm.oamF5.endToEnd.pmTxStats.sevErrCellBlckRatio

       formula = 1000000000 / ; 1000000000 *"
   ::= {pr1646v2ATMFwPerEntry 288686208}

pr1646v2ATMFwPerAtmPppLinkMonitoringRequestsSent OBJECT-TYPE
   SYNTAX      Gauge32
   MAX-ACCESS  read-only
   STATUS      current
   DESCRIPTION
      "Path: atm.performance.pvcTable.atm.ppp.linkMonitoring.requestsSent

       32 bit unsigned gauge value."
   ::= {pr1646v2ATMFwPerEntry 289411088}

pr1646v2ATMFwPerAtmPppLinkMonitoringRepliesRcvd OBJECT-TYPE
   SYNTAX      Gauge32
   MAX-ACCESS  read-only
   STATUS      current
   DESCRIPTION
      "Path: atm.performance.pvcTable.atm.ppp.linkMonitoring.repliesRcvd

       32 bit unsigned gauge value."
   ::= {pr1646v2ATMFwPerEntry 289411104}

pr1646v2ATMFwPerAtmPppLinkMonitoringRequestsRcvd OBJECT-TYPE
   SYNTAX      Gauge32
   MAX-ACCESS  read-only
   STATUS      current
   DESCRIPTION
      "Path: atm.performance.pvcTable.atm.ppp.linkMonitoring.requestsRcvd

       32 bit unsigned gauge value."
   ::= {pr1646v2ATMFwPerEntry 289411120}

pr1646v2ATMFwPerAtmPppLinkMonitoringRepliesSent OBJECT-TYPE
   SYNTAX      Gauge32
   MAX-ACCESS  read-only
   STATUS      current
   DESCRIPTION
      "Path: atm.performance.pvcTable.atm.ppp.linkMonitoring.repliesSent

       32 bit unsigned gauge value."
   ::= {pr1646v2ATMFwPerEntry 289411136}

pr1646v2ATMFwPerFrLmiInStatusEnq OBJECT-TYPE
   SYNTAX      Counter32
   MAX-ACCESS  read-only
   STATUS      current
   DESCRIPTION
      "Path: atm.performance.pvcTable.frameRelay.lmi.inStatusEnquiry

       32 bit unsigned wrappable counter."
   ::= {pr1646v2ATMFwPerEntry 503382272}

pr1646v2ATMFwPerFrLmiInStatus OBJECT-TYPE
   SYNTAX      Counter32
   MAX-ACCESS  read-only
   STATUS      current
   DESCRIPTION
      "Path: atm.performance.pvcTable.frameRelay.lmi.inStatus

       32 bit unsigned wrappable counter."
   ::= {pr1646v2ATMFwPerEntry 503382528}

pr1646v2ATMFwPerFrLmiInStatUpdate OBJECT-TYPE
   SYNTAX      Counter32
   MAX-ACCESS  read-only
   STATUS      current
   DESCRIPTION
      "Path: atm.performance.pvcTable.frameRelay.lmi.inStatusUpdate

       32 bit unsigned wrappable counter."
   ::= {pr1646v2ATMFwPerEntry 503382784}

pr1646v2ATMFwPerFrLmiOutStatusEnq OBJECT-TYPE
   SYNTAX      Counter32
   MAX-ACCESS  read-only
   STATUS      current
   DESCRIPTION
      "Path: atm.performance.pvcTable.frameRelay.lmi.outStatusEnquiry

       32 bit unsigned wrappable counter."
   ::= {pr1646v2ATMFwPerEntry 503383040}

pr1646v2ATMFwPerFrLmiOutStatus OBJECT-TYPE
   SYNTAX      Counter32
   MAX-ACCESS  read-only
   STATUS      current
   DESCRIPTION
      "Path: atm.performance.pvcTable.frameRelay.lmi.outStatus

       32 bit unsigned wrappable counter."
   ::= {pr1646v2ATMFwPerEntry 503383296}

pr1646v2ATMFwPerFrLmiOutStatUpdate OBJECT-TYPE
   SYNTAX      Counter32
   MAX-ACCESS  read-only
   STATUS      current
   DESCRIPTION
      "Path: atm.performance.pvcTable.frameRelay.lmi.outStatusUpdate

       32 bit unsigned wrappable counter."
   ::= {pr1646v2ATMFwPerEntry 503383552}

pr1646v2ATMFwPerFrLmiNetPollNotRcvd OBJECT-TYPE
   SYNTAX      Counter32
   MAX-ACCESS  read-only
   STATUS      current
   DESCRIPTION
      "Path: atm.performance.pvcTable.frameRelay.lmi.netPollNotRcvd

       32 bit unsigned wrappable counter."
   ::= {pr1646v2ATMFwPerEntry 503383808}

pr1646v2ATMFwPerFrLmiUsrNoRespRcvd OBJECT-TYPE
   SYNTAX      Counter32
   MAX-ACCESS  read-only
   STATUS      current
   DESCRIPTION
      "Path: atm.performance.pvcTable.frameRelay.lmi.userNoResponseRcvd

       32 bit unsigned wrappable counter."
   ::= {pr1646v2ATMFwPerEntry 503387136}

pr1646v2ATMFwPerFrLmiUsrBadRespRcvd OBJECT-TYPE
   SYNTAX      Counter32
   MAX-ACCESS  read-only
   STATUS      current
   DESCRIPTION
      "Path: atm.performance.pvcTable.frameRelay.lmi.userBadResponsesRcvd

       32 bit unsigned wrappable counter."
   ::= {pr1646v2ATMFwPerEntry 503387392}

pr1646v2ATMFwPerMCH2P OBJECT-TYPE
   SYNTAX      SEQUENCE OF Pr1646v2ATMFwPerMCH2PEntry
   MAX-ACCESS  not-accessible
   STATUS      current
   DESCRIPTION
      ""
   ::= {pr1646v2ATMFwPer 41549824}

pr1646v2ATMFwPerMCH2PEntry OBJECT-TYPE
   SYNTAX      Pr1646v2ATMFwPerMCH2PEntry
   MAX-ACCESS  not-accessible
   STATUS      current
   DESCRIPTION
      ""
   INDEX      { pr1646v2ATMFwPerMCH2PGlobalIx,
                pr1646v2ATMFwPerTableIx,
                pr1646v2ATMFwPerMCH2PTableIx }
   ::= {pr1646v2ATMFwPerMCH2P 1}

Pr1646v2ATMFwPerMCH2PEntry ::=
   SEQUENCE
      {
      pr1646v2ATMFwPerMCH2PGlobalIx
         GlobalIndex,
      pr1646v2ATMFwPerMCH2PTableIx
         TableIndex,
      pr1646v2ATMFwPerMCH2PSysUpTime
         TimeTicks,
      pr1646v2ATMFwPerMCH2PIfUpTime
         TimeTicks,
      pr1646v2ATMFwPerMCH2PIfStatChanges
         Counter32,
      pr1646v2ATMFwPerMCH2PIfInOctets
         Counter64,
      pr1646v2ATMFwPerMCH2PIfInUCPkts
         Counter64,
      pr1646v2ATMFwPerMCH2PIfInNUCPkts
         Counter64,
      pr1646v2ATMFwPerMCH2PIfInBCPkts
         Counter64,
      pr1646v2ATMFwPerMCH2PIfInMCPkts
         Counter64,
      pr1646v2ATMFwPerMCH2PIfInDiscards
         Counter64,
      pr1646v2ATMFwPerMCH2PIfInErrors
         Counter64,
      pr1646v2ATMFwPerMCH2PIfInUnkwn
         Counter64,
      pr1646v2ATMFwPerMCH2PInDropEx
         Counter64,
      pr1646v2ATMFwPerMCH2PInDropNoMac
         Counter64,
      pr1646v2ATMFwPerMCH2PInDropNUCast
         Counter64,
      pr1646v2ATMFwPerMCH2PInDropFilter
         Counter64,
      pr1646v2ATMFwPerMCH2PIfInBandwidth
         Integer32,
      pr1646v2ATMFwPerMCH2PIfOutOctets
         Counter64,
      pr1646v2ATMFwPerMCH2PIfOutUCPkts
         Counter64,
      pr1646v2ATMFwPerMCH2PIfOutNUCPkts
         Counter64,
      pr1646v2ATMFwPerMCH2PIfOutBCPkts
         Counter64,
      pr1646v2ATMFwPerMCH2PIfOutMCPkts
         Counter64,
      pr1646v2ATMFwPerMCH2PIfOutDiscards
         Counter64,
      pr1646v2ATMFwPerMCH2PIfOutErrors
         Counter64,
      pr1646v2ATMFwPerMCH2POutDropEx
         Counter64,
      pr1646v2ATMFwPerMCH2POutDropNoArp
         Counter64,
      pr1646v2ATMFwPerMCH2POutDropFilter
         Counter64,
      pr1646v2ATMFwPerMCH2PIfOutBandwidth
         Integer32,
      pr1646v2ATMFwPerMCH2PIfErrSec
         Counter32
      }

pr1646v2ATMFwPerMCH2PGlobalIx OBJECT-TYPE
   SYNTAX      GlobalIndex
   MAX-ACCESS  not-accessible
   STATUS      current
   DESCRIPTION
      "The value of the tlsCntTreeGlobalIndex of the MANAGED OBJECT."
   ::= {pr1646v2ATMFwPerMCH2PEntry 10}

pr1646v2ATMFwPerMCH2PTableIx OBJECT-TYPE
   SYNTAX      TableIndex
   MAX-ACCESS  not-accessible
   STATUS      current
   DESCRIPTION
      ""
   ::= {pr1646v2ATMFwPerMCH2PEntry 11}

pr1646v2ATMFwPerMCH2PSysUpTime OBJECT-TYPE
   SYNTAX      TimeTicks
   MAX-ACCESS  read-only
   STATUS      current
   DESCRIPTION
      "Path: atm.performance.pvcTable.mibCounters.h2Performance.sysUpTime

       Time in centi-second."
   ::= {pr1646v2ATMFwPerMCH2PEntry 16777216}

pr1646v2ATMFwPerMCH2PIfUpTime OBJECT-TYPE
   SYNTAX      TimeTicks
   MAX-ACCESS  read-only
   STATUS      current
   DESCRIPTION
      "Path: atm.performance.pvcTable.mibCounters.h2Performance.ifUpTime

       Time in centi-second."
   ::= {pr1646v2ATMFwPerMCH2PEntry 33554432}

pr1646v2ATMFwPerMCH2PIfStatChanges OBJECT-TYPE
   SYNTAX      Counter32
   MAX-ACCESS  read-only
   STATUS      current
   DESCRIPTION
      "Path: atm.performance.pvcTable.mibCounters.h2Performance.ifStatusChanges

       32 bit unsigned wrappable counter."
   ::= {pr1646v2ATMFwPerMCH2PEntry 50331648}

pr1646v2ATMFwPerMCH2PIfInOctets OBJECT-TYPE
   SYNTAX      Counter64
   MAX-ACCESS  read-only
   STATUS      current
   DESCRIPTION
      "Path: atm.performance.pvcTable.mibCounters.h2Performance.ifInOctets

       64 bit unsigned wrappable counter."
   ::= {pr1646v2ATMFwPerMCH2PEntry 67108864}

pr1646v2ATMFwPerMCH2PIfInUCPkts OBJECT-TYPE
   SYNTAX      Counter64
   MAX-ACCESS  read-only
   STATUS      current
   DESCRIPTION
      "Path: atm.performance.pvcTable.mibCounters.h2Performance.ifInUcastPkts

       64 bit unsigned wrappable counter."
   ::= {pr1646v2ATMFwPerMCH2PEntry 83886080}

pr1646v2ATMFwPerMCH2PIfInNUCPkts OBJECT-TYPE
   SYNTAX      Counter64
   MAX-ACCESS  read-only
   STATUS      current
   DESCRIPTION
      "Path: atm.performance.pvcTable.mibCounters.h2Performance.ifInNUcastPkts

       64 bit unsigned wrappable counter."
   ::= {pr1646v2ATMFwPerMCH2PEntry 100663296}

pr1646v2ATMFwPerMCH2PIfInBCPkts OBJECT-TYPE
   SYNTAX      Counter64
   MAX-ACCESS  read-only
   STATUS      current
   DESCRIPTION
      "Path: atm.performance.pvcTable.mibCounters.h2Performance.ifInBcastPkts

       64 bit unsigned wrappable counter."
   ::= {pr1646v2ATMFwPerMCH2PEntry 419430400}

pr1646v2ATMFwPerMCH2PIfInMCPkts OBJECT-TYPE
   SYNTAX      Counter64
   MAX-ACCESS  read-only
   STATUS      current
   DESCRIPTION
      "Path: atm.performance.pvcTable.mibCounters.h2Performance.ifInMcastPkts

       64 bit unsigned wrappable counter."
   ::= {pr1646v2ATMFwPerMCH2PEntry 436207616}

pr1646v2ATMFwPerMCH2PIfInDiscards OBJECT-TYPE
   SYNTAX      Counter64
   MAX-ACCESS  read-only
   STATUS      current
   DESCRIPTION
      "Path: atm.performance.pvcTable.mibCounters.h2Performance.ifInDiscards

       64 bit unsigned wrappable counter."
   ::= {pr1646v2ATMFwPerMCH2PEntry 117440512}

pr1646v2ATMFwPerMCH2PIfInErrors OBJECT-TYPE
   SYNTAX      Counter64
   MAX-ACCESS  read-only
   STATUS      current
   DESCRIPTION
      "Path: atm.performance.pvcTable.mibCounters.h2Performance.ifInErrors

       64 bit unsigned wrappable counter."
   ::= {pr1646v2ATMFwPerMCH2PEntry 134217728}

pr1646v2ATMFwPerMCH2PIfInUnkwn OBJECT-TYPE
   SYNTAX      Counter64
   MAX-ACCESS  read-only
   STATUS      current
   DESCRIPTION
      "Path: atm.performance.pvcTable.mibCounters.h2Performance.ifInUnknownProtos

       64 bit unsigned wrappable counter."
   ::= {pr1646v2ATMFwPerMCH2PEntry 150994944}

pr1646v2ATMFwPerMCH2PInDropEx OBJECT-TYPE
   SYNTAX      Counter64
   MAX-ACCESS  read-only
   STATUS      current
   DESCRIPTION
      "Path: atm.performance.pvcTable.mibCounters.h2Performance.ifInDropLevelExceeded

       64 bit unsigned wrappable counter."
   ::= {pr1646v2ATMFwPerMCH2PEntry 335544320}

pr1646v2ATMFwPerMCH2PInDropNoMac OBJECT-TYPE
   SYNTAX      Counter64
   MAX-ACCESS  read-only
   STATUS      current
   DESCRIPTION
      "Path: atm.performance.pvcTable.mibCounters.h2Performance.fInDiscardsNoMacFit

       64 bit unsigned wrappable counter."
   ::= {pr1646v2ATMFwPerMCH2PEntry 301989888}

pr1646v2ATMFwPerMCH2PInDropNUCast OBJECT-TYPE
   SYNTAX      Counter64
   MAX-ACCESS  read-only
   STATUS      current
   DESCRIPTION
      "Path: atm.performance.pvcTable.mibCounters.h2Performance.fInDiscardsNUCast

       64 bit unsigned wrappable counter."
   ::= {pr1646v2ATMFwPerMCH2PEntry 318767104}

pr1646v2ATMFwPerMCH2PInDropFilter OBJECT-TYPE
   SYNTAX      Counter64
   MAX-ACCESS  read-only
   STATUS      current
   DESCRIPTION
      "Path: atm.performance.pvcTable.mibCounters.h2Performance.fInDiscardsFilter

       64 bit unsigned wrappable counter."
   ::= {pr1646v2ATMFwPerMCH2PEntry 385875968}

pr1646v2ATMFwPerMCH2PIfInBandwidth OBJECT-TYPE
   SYNTAX      Integer32
   MAX-ACCESS  read-only
   STATUS      current
   DESCRIPTION
      "Path: atm.performance.pvcTable.mibCounters.h2Performance.ifInBandwidth

       unit name = bps
       formula = 8 * ; 8 /"
   ::= {pr1646v2ATMFwPerMCH2PEntry 268435456}

pr1646v2ATMFwPerMCH2PIfOutOctets OBJECT-TYPE
   SYNTAX      Counter64
   MAX-ACCESS  read-only
   STATUS      current
   DESCRIPTION
      "Path: atm.performance.pvcTable.mibCounters.h2Performance.ifOutOctets

       64 bit unsigned wrappable counter."
   ::= {pr1646v2ATMFwPerMCH2PEntry 167772160}

pr1646v2ATMFwPerMCH2PIfOutUCPkts OBJECT-TYPE
   SYNTAX      Counter64
   MAX-ACCESS  read-only
   STATUS      current
   DESCRIPTION
      "Path: atm.performance.pvcTable.mibCounters.h2Performance.ifOutUcastPkts

       64 bit unsigned wrappable counter."
   ::= {pr1646v2ATMFwPerMCH2PEntry 184549376}

pr1646v2ATMFwPerMCH2PIfOutNUCPkts OBJECT-TYPE
   SYNTAX      Counter64
   MAX-ACCESS  read-only
   STATUS      current
   DESCRIPTION
      "Path: atm.performance.pvcTable.mibCounters.h2Performance.ifOutNUcastPkts

       64 bit unsigned wrappable counter."
   ::= {pr1646v2ATMFwPerMCH2PEntry 201326592}

pr1646v2ATMFwPerMCH2PIfOutBCPkts OBJECT-TYPE
   SYNTAX      Counter64
   MAX-ACCESS  read-only
   STATUS      current
   DESCRIPTION
      "Path: atm.performance.pvcTable.mibCounters.h2Performance.ifOutBcastPkts

       64 bit unsigned wrappable counter."
   ::= {pr1646v2ATMFwPerMCH2PEntry 452984832}

pr1646v2ATMFwPerMCH2PIfOutMCPkts OBJECT-TYPE
   SYNTAX      Counter64
   MAX-ACCESS  read-only
   STATUS      current
   DESCRIPTION
      "Path: atm.performance.pvcTable.mibCounters.h2Performance.ifOutMcastPkts

       64 bit unsigned wrappable counter."
   ::= {pr1646v2ATMFwPerMCH2PEntry 469762048}

pr1646v2ATMFwPerMCH2PIfOutDiscards OBJECT-TYPE
   SYNTAX      Counter64
   MAX-ACCESS  read-only
   STATUS      current
   DESCRIPTION
      "Path: atm.performance.pvcTable.mibCounters.h2Performance.ifOutDiscards

       64 bit unsigned wrappable counter."
   ::= {pr1646v2ATMFwPerMCH2PEntry 218103808}

pr1646v2ATMFwPerMCH2PIfOutErrors OBJECT-TYPE
   SYNTAX      Counter64
   MAX-ACCESS  read-only
   STATUS      current
   DESCRIPTION
      "Path: atm.performance.pvcTable.mibCounters.h2Performance.ifOutErrors

       64 bit unsigned wrappable counter."
   ::= {pr1646v2ATMFwPerMCH2PEntry 234881024}

pr1646v2ATMFwPerMCH2POutDropEx OBJECT-TYPE
   SYNTAX      Counter64
   MAX-ACCESS  read-only
   STATUS      current
   DESCRIPTION
      "Path: atm.performance.pvcTable.mibCounters.h2Performance.ifOutDropLevelExceeded

       64 bit unsigned wrappable counter."
   ::= {pr1646v2ATMFwPerMCH2PEntry 352321536}

pr1646v2ATMFwPerMCH2POutDropNoArp OBJECT-TYPE
   SYNTAX      Counter64
   MAX-ACCESS  read-only
   STATUS      current
   DESCRIPTION
      "Path: atm.performance.pvcTable.mibCounters.h2Performance.ifOutDiscardsNoArp

       64 bit unsigned wrappable counter."
   ::= {pr1646v2ATMFwPerMCH2PEntry 369098752}

pr1646v2ATMFwPerMCH2POutDropFilter OBJECT-TYPE
   SYNTAX      Counter64
   MAX-ACCESS  read-only
   STATUS      current
   DESCRIPTION
      "Path: atm.performance.pvcTable.mibCounters.h2Performance.ifOutDiscardsFilter

       64 bit unsigned wrappable counter."
   ::= {pr1646v2ATMFwPerMCH2PEntry 402653184}

pr1646v2ATMFwPerMCH2PIfOutBandwidth OBJECT-TYPE
   SYNTAX      Integer32
   MAX-ACCESS  read-only
   STATUS      current
   DESCRIPTION
      "Path: atm.performance.pvcTable.mibCounters.h2Performance.ifOutBandwidth

       unit name = bps
       formula = 8 * ; 8 /"
   ::= {pr1646v2ATMFwPerMCH2PEntry 285212672}

pr1646v2ATMFwPerMCH2PIfErrSec OBJECT-TYPE
   SYNTAX      Counter32
   MAX-ACCESS  read-only
   STATUS      current
   DESCRIPTION
      "Path: atm.performance.pvcTable.mibCounters.h2Performance.ifErrSec

       32 bit unsigned wrappable counter."
   ::= {pr1646v2ATMFwPerMCH2PEntry 251658240}

pr1646v2ATMFwPerMCH24P OBJECT-TYPE
   SYNTAX      SEQUENCE OF Pr1646v2ATMFwPerMCH24PEntry
   MAX-ACCESS  not-accessible
   STATUS      current
   DESCRIPTION
      ""
   ::= {pr1646v2ATMFwPer 41615360}

pr1646v2ATMFwPerMCH24PEntry OBJECT-TYPE
   SYNTAX      Pr1646v2ATMFwPerMCH24PEntry
   MAX-ACCESS  not-accessible
   STATUS      current
   DESCRIPTION
      ""
   INDEX      { pr1646v2ATMFwPerMCH24PGlobalIx,
                pr1646v2ATMFwPerTableIx,
                pr1646v2ATMFwPerMCH24PTableIx }
   ::= {pr1646v2ATMFwPerMCH24P 1}

Pr1646v2ATMFwPerMCH24PEntry ::=
   SEQUENCE
      {
      pr1646v2ATMFwPerMCH24PGlobalIx
         GlobalIndex,
      pr1646v2ATMFwPerMCH24PTableIx
         TableIndex,
      pr1646v2ATMFwPerMCH24PSysUpTime
         TimeTicks,
      pr1646v2ATMFwPerMCH24PIfUpTime
         TimeTicks,
      pr1646v2ATMFwPerMCH24PIfStatChanges
         Counter32,
      pr1646v2ATMFwPerMCH24PIfInOctets
         Counter64,
      pr1646v2ATMFwPerMCH24PIfInUCPkts
         Counter64,
      pr1646v2ATMFwPerMCH24PIfInNUCPkts
         Counter64,
      pr1646v2ATMFwPerMCH24PIfInBCPkts
         Counter64,
      pr1646v2ATMFwPerMCH24PIfInMCPkts
         Counter64,
      pr1646v2ATMFwPerMCH24PIfInDiscards
         Counter64,
      pr1646v2ATMFwPerMCH24PIfInErrors
         Counter64,
      pr1646v2ATMFwPerMCH24PIfInUnkwn
         Counter64,
      pr1646v2ATMFwPerMCH24PInDropEx
         Counter64,
      pr1646v2ATMFwPerMCH24PInDropNoMac
         Counter64,
      pr1646v2ATMFwPerMCH24PInDropNUCast
         Counter64,
      pr1646v2ATMFwPerMCH24PInDropFilter
         Counter64,
      pr1646v2ATMFwPerMCH24PIfInBandwidth
         Integer32,
      pr1646v2ATMFwPerMCH24PIfOutOctets
         Counter64,
      pr1646v2ATMFwPerMCH24PIfOutUCPkts
         Counter64,
      pr1646v2ATMFwPerMCH24PIfOutNUCPkts
         Counter64,
      pr1646v2ATMFwPerMCH24PIfOutBCPkts
         Counter64,
      pr1646v2ATMFwPerMCH24PIfOutMCPkts
         Counter64,
      pr1646v2ATMFwPerMCH24PIfOutDiscards
         Counter64,
      pr1646v2ATMFwPerMCH24PIfOutErrors
         Counter64,
      pr1646v2ATMFwPerMCH24POutDropEx
         Counter64,
      pr1646v2ATMFwPerMCH24POutDropNoArp
         Counter64,
      pr1646v2ATMFwPerMCH24POutDropFilter
         Counter64,
      pr1646v2ATMFwPerMCH24PIfOutBandwidth
         Integer32,
      pr1646v2ATMFwPerMCH24PIfErrSec
         Counter32
      }

pr1646v2ATMFwPerMCH24PGlobalIx OBJECT-TYPE
   SYNTAX      GlobalIndex
   MAX-ACCESS  not-accessible
   STATUS      current
   DESCRIPTION
      "The value of the tlsCntTreeGlobalIndex of the MANAGED OBJECT."
   ::= {pr1646v2ATMFwPerMCH24PEntry 10}

pr1646v2ATMFwPerMCH24PTableIx OBJECT-TYPE
   SYNTAX      TableIndex
   MAX-ACCESS  not-accessible
   STATUS      current
   DESCRIPTION
      ""
   ::= {pr1646v2ATMFwPerMCH24PEntry 11}

pr1646v2ATMFwPerMCH24PSysUpTime OBJECT-TYPE
   SYNTAX      TimeTicks
   MAX-ACCESS  read-only
   STATUS      current
   DESCRIPTION
      "Path: atm.performance.pvcTable.mibCounters.h24Performance.sysUpTime

       Time in centi-second."
   ::= {pr1646v2ATMFwPerMCH24PEntry 16777216}

pr1646v2ATMFwPerMCH24PIfUpTime OBJECT-TYPE
   SYNTAX      TimeTicks
   MAX-ACCESS  read-only
   STATUS      current
   DESCRIPTION
      "Path: atm.performance.pvcTable.mibCounters.h24Performance.ifUpTime

       Time in centi-second."
   ::= {pr1646v2ATMFwPerMCH24PEntry 33554432}

pr1646v2ATMFwPerMCH24PIfStatChanges OBJECT-TYPE
   SYNTAX      Counter32
   MAX-ACCESS  read-only
   STATUS      current
   DESCRIPTION
      "Path: atm.performance.pvcTable.mibCounters.h24Performance.ifStatusChanges

       32 bit unsigned wrappable counter."
   ::= {pr1646v2ATMFwPerMCH24PEntry 50331648}

pr1646v2ATMFwPerMCH24PIfInOctets OBJECT-TYPE
   SYNTAX      Counter64
   MAX-ACCESS  read-only
   STATUS      current
   DESCRIPTION
      "Path: atm.performance.pvcTable.mibCounters.h24Performance.ifInOctets

       64 bit unsigned wrappable counter."
   ::= {pr1646v2ATMFwPerMCH24PEntry 67108864}

pr1646v2ATMFwPerMCH24PIfInUCPkts OBJECT-TYPE
   SYNTAX      Counter64
   MAX-ACCESS  read-only
   STATUS      current
   DESCRIPTION
      "Path: atm.performance.pvcTable.mibCounters.h24Performance.ifInUcastPkts

       64 bit unsigned wrappable counter."
   ::= {pr1646v2ATMFwPerMCH24PEntry 83886080}

pr1646v2ATMFwPerMCH24PIfInNUCPkts OBJECT-TYPE
   SYNTAX      Counter64
   MAX-ACCESS  read-only
   STATUS      current
   DESCRIPTION
      "Path: atm.performance.pvcTable.mibCounters.h24Performance.ifInNUcastPkts

       64 bit unsigned wrappable counter."
   ::= {pr1646v2ATMFwPerMCH24PEntry 100663296}

pr1646v2ATMFwPerMCH24PIfInBCPkts OBJECT-TYPE
   SYNTAX      Counter64
   MAX-ACCESS  read-only
   STATUS      current
   DESCRIPTION
      "Path: atm.performance.pvcTable.mibCounters.h24Performance.ifInBcastPkts

       64 bit unsigned wrappable counter."
   ::= {pr1646v2ATMFwPerMCH24PEntry 419430400}

pr1646v2ATMFwPerMCH24PIfInMCPkts OBJECT-TYPE
   SYNTAX      Counter64
   MAX-ACCESS  read-only
   STATUS      current
   DESCRIPTION
      "Path: atm.performance.pvcTable.mibCounters.h24Performance.ifInMcastPkts

       64 bit unsigned wrappable counter."
   ::= {pr1646v2ATMFwPerMCH24PEntry 436207616}

pr1646v2ATMFwPerMCH24PIfInDiscards OBJECT-TYPE
   SYNTAX      Counter64
   MAX-ACCESS  read-only
   STATUS      current
   DESCRIPTION
      "Path: atm.performance.pvcTable.mibCounters.h24Performance.ifInDiscards

       64 bit unsigned wrappable counter."
   ::= {pr1646v2ATMFwPerMCH24PEntry 117440512}

pr1646v2ATMFwPerMCH24PIfInErrors OBJECT-TYPE
   SYNTAX      Counter64
   MAX-ACCESS  read-only
   STATUS      current
   DESCRIPTION
      "Path: atm.performance.pvcTable.mibCounters.h24Performance.ifInErrors

       64 bit unsigned wrappable counter."
   ::= {pr1646v2ATMFwPerMCH24PEntry 134217728}

pr1646v2ATMFwPerMCH24PIfInUnkwn OBJECT-TYPE
   SYNTAX      Counter64
   MAX-ACCESS  read-only
   STATUS      current
   DESCRIPTION
      "Path: atm.performance.pvcTable.mibCounters.h24Performance.ifInUnknownProtos

       64 bit unsigned wrappable counter."
   ::= {pr1646v2ATMFwPerMCH24PEntry 150994944}

pr1646v2ATMFwPerMCH24PInDropEx OBJECT-TYPE
   SYNTAX      Counter64
   MAX-ACCESS  read-only
   STATUS      current
   DESCRIPTION
      "Path: atm.performance.pvcTable.mibCounters.h24Performance.ifInDropLevelExceeded

       64 bit unsigned wrappable counter."
   ::= {pr1646v2ATMFwPerMCH24PEntry 335544320}

pr1646v2ATMFwPerMCH24PInDropNoMac OBJECT-TYPE
   SYNTAX      Counter64
   MAX-ACCESS  read-only
   STATUS      current
   DESCRIPTION
      "Path: atm.performance.pvcTable.mibCounters.h24Performance.fInDiscardsNoMacFit

       64 bit unsigned wrappable counter."
   ::= {pr1646v2ATMFwPerMCH24PEntry 301989888}

pr1646v2ATMFwPerMCH24PInDropNUCast OBJECT-TYPE
   SYNTAX      Counter64
   MAX-ACCESS  read-only
   STATUS      current
   DESCRIPTION
      "Path: atm.performance.pvcTable.mibCounters.h24Performance.fInDiscardsNUCast

       64 bit unsigned wrappable counter."
   ::= {pr1646v2ATMFwPerMCH24PEntry 318767104}

pr1646v2ATMFwPerMCH24PInDropFilter OBJECT-TYPE
   SYNTAX      Counter64
   MAX-ACCESS  read-only
   STATUS      current
   DESCRIPTION
      "Path: atm.performance.pvcTable.mibCounters.h24Performance.fInDiscardsFilter

       64 bit unsigned wrappable counter."
   ::= {pr1646v2ATMFwPerMCH24PEntry 385875968}

pr1646v2ATMFwPerMCH24PIfInBandwidth OBJECT-TYPE
   SYNTAX      Integer32
   MAX-ACCESS  read-only
   STATUS      current
   DESCRIPTION
      "Path: atm.performance.pvcTable.mibCounters.h24Performance.ifInBandwidth

       unit name = bps
       formula = 8 * ; 8 /"
   ::= {pr1646v2ATMFwPerMCH24PEntry 268435456}

pr1646v2ATMFwPerMCH24PIfOutOctets OBJECT-TYPE
   SYNTAX      Counter64
   MAX-ACCESS  read-only
   STATUS      current
   DESCRIPTION
      "Path: atm.performance.pvcTable.mibCounters.h24Performance.ifOutOctets

       64 bit unsigned wrappable counter."
   ::= {pr1646v2ATMFwPerMCH24PEntry 167772160}

pr1646v2ATMFwPerMCH24PIfOutUCPkts OBJECT-TYPE
   SYNTAX      Counter64
   MAX-ACCESS  read-only
   STATUS      current
   DESCRIPTION
      "Path: atm.performance.pvcTable.mibCounters.h24Performance.ifOutUcastPkts

       64 bit unsigned wrappable counter."
   ::= {pr1646v2ATMFwPerMCH24PEntry 184549376}

pr1646v2ATMFwPerMCH24PIfOutNUCPkts OBJECT-TYPE
   SYNTAX      Counter64
   MAX-ACCESS  read-only
   STATUS      current
   DESCRIPTION
      "Path: atm.performance.pvcTable.mibCounters.h24Performance.ifOutNUcastPkts

       64 bit unsigned wrappable counter."
   ::= {pr1646v2ATMFwPerMCH24PEntry 201326592}

pr1646v2ATMFwPerMCH24PIfOutBCPkts OBJECT-TYPE
   SYNTAX      Counter64
   MAX-ACCESS  read-only
   STATUS      current
   DESCRIPTION
      "Path: atm.performance.pvcTable.mibCounters.h24Performance.ifOutBcastPkts

       64 bit unsigned wrappable counter."
   ::= {pr1646v2ATMFwPerMCH24PEntry 452984832}

pr1646v2ATMFwPerMCH24PIfOutMCPkts OBJECT-TYPE
   SYNTAX      Counter64
   MAX-ACCESS  read-only
   STATUS      current
   DESCRIPTION
      "Path: atm.performance.pvcTable.mibCounters.h24Performance.ifOutMcastPkts

       64 bit unsigned wrappable counter."
   ::= {pr1646v2ATMFwPerMCH24PEntry 469762048}

pr1646v2ATMFwPerMCH24PIfOutDiscards OBJECT-TYPE
   SYNTAX      Counter64
   MAX-ACCESS  read-only
   STATUS      current
   DESCRIPTION
      "Path: atm.performance.pvcTable.mibCounters.h24Performance.ifOutDiscards

       64 bit unsigned wrappable counter."
   ::= {pr1646v2ATMFwPerMCH24PEntry 218103808}

pr1646v2ATMFwPerMCH24PIfOutErrors OBJECT-TYPE
   SYNTAX      Counter64
   MAX-ACCESS  read-only
   STATUS      current
   DESCRIPTION
      "Path: atm.performance.pvcTable.mibCounters.h24Performance.ifOutErrors

       64 bit unsigned wrappable counter."
   ::= {pr1646v2ATMFwPerMCH24PEntry 234881024}

pr1646v2ATMFwPerMCH24POutDropEx OBJECT-TYPE
   SYNTAX      Counter64
   MAX-ACCESS  read-only
   STATUS      current
   DESCRIPTION
      "Path: atm.performance.pvcTable.mibCounters.h24Performance.ifOutDropLevelExceeded

       64 bit unsigned wrappable counter."
   ::= {pr1646v2ATMFwPerMCH24PEntry 352321536}

pr1646v2ATMFwPerMCH24POutDropNoArp OBJECT-TYPE
   SYNTAX      Counter64
   MAX-ACCESS  read-only
   STATUS      current
   DESCRIPTION
      "Path: atm.performance.pvcTable.mibCounters.h24Performance.ifOutDiscardsNoArp

       64 bit unsigned wrappable counter."
   ::= {pr1646v2ATMFwPerMCH24PEntry 369098752}

pr1646v2ATMFwPerMCH24POutDropFilter OBJECT-TYPE
   SYNTAX      Counter64
   MAX-ACCESS  read-only
   STATUS      current
   DESCRIPTION
      "Path: atm.performance.pvcTable.mibCounters.h24Performance.ifOutDiscardsFilter

       64 bit unsigned wrappable counter."
   ::= {pr1646v2ATMFwPerMCH24PEntry 402653184}

pr1646v2ATMFwPerMCH24PIfOutBandwidth OBJECT-TYPE
   SYNTAX      Integer32
   MAX-ACCESS  read-only
   STATUS      current
   DESCRIPTION
      "Path: atm.performance.pvcTable.mibCounters.h24Performance.ifOutBandwidth

       unit name = bps
       formula = 8 * ; 8 /"
   ::= {pr1646v2ATMFwPerMCH24PEntry 285212672}

pr1646v2ATMFwPerMCH24PIfErrSec OBJECT-TYPE
   SYNTAX      Counter32
   MAX-ACCESS  read-only
   STATUS      current
   DESCRIPTION
      "Path: atm.performance.pvcTable.mibCounters.h24Performance.ifErrSec

       32 bit unsigned wrappable counter."
   ::= {pr1646v2ATMFwPerMCH24PEntry 251658240}

pr1646v2ATMFwPerMCD7P OBJECT-TYPE
   SYNTAX      SEQUENCE OF Pr1646v2ATMFwPerMCD7PEntry
   MAX-ACCESS  not-accessible
   STATUS      current
   DESCRIPTION
      ""
   ::= {pr1646v2ATMFwPer 41680896}

pr1646v2ATMFwPerMCD7PEntry OBJECT-TYPE
   SYNTAX      Pr1646v2ATMFwPerMCD7PEntry
   MAX-ACCESS  not-accessible
   STATUS      current
   DESCRIPTION
      ""
   INDEX      { pr1646v2ATMFwPerMCD7PGlobalIx,
                pr1646v2ATMFwPerTableIx,
                pr1646v2ATMFwPerMCD7PTableIx }
   ::= {pr1646v2ATMFwPerMCD7P 1}

Pr1646v2ATMFwPerMCD7PEntry ::=
   SEQUENCE
      {
      pr1646v2ATMFwPerMCD7PGlobalIx
         GlobalIndex,
      pr1646v2ATMFwPerMCD7PTableIx
         TableIndex,
      pr1646v2ATMFwPerMCD7PSysUpTime
         TimeTicks,
      pr1646v2ATMFwPerMCD7PIfUpTime
         TimeTicks,
      pr1646v2ATMFwPerMCD7PIfStatChanges
         Counter32,
      pr1646v2ATMFwPerMCD7PIfInOctets
         Counter64,
      pr1646v2ATMFwPerMCD7PIfInUCPkts
         Counter64,
      pr1646v2ATMFwPerMCD7PIfInNUCPkts
         Counter64,
      pr1646v2ATMFwPerMCD7PIfInBCPkts
         Counter64,
      pr1646v2ATMFwPerMCD7PIfInMCPkts
         Counter64,
      pr1646v2ATMFwPerMCD7PIfInDiscards
         Counter64,
      pr1646v2ATMFwPerMCD7PIfInErrors
         Counter64,
      pr1646v2ATMFwPerMCD7PIfInUnkwn
         Counter64,
      pr1646v2ATMFwPerMCD7PInDropEx
         Counter64,
      pr1646v2ATMFwPerMCD7PInDropNoMac
         Counter64,
      pr1646v2ATMFwPerMCD7PInDropNUCast
         Counter64,
      pr1646v2ATMFwPerMCD7PInDropFilter
         Counter64,
      pr1646v2ATMFwPerMCD7PIfInBandwidth
         Integer32,
      pr1646v2ATMFwPerMCD7PIfOutOctets
         Counter64,
      pr1646v2ATMFwPerMCD7PIfOutUCPkts
         Counter64,
      pr1646v2ATMFwPerMCD7PIfOutNUCPkts
         Counter64,
      pr1646v2ATMFwPerMCD7PIfOutBCPkts
         Counter64,
      pr1646v2ATMFwPerMCD7PIfOutMCPkts
         Counter64,
      pr1646v2ATMFwPerMCD7PIfOutDiscards
         Counter64,
      pr1646v2ATMFwPerMCD7PIfOutErrors
         Counter64,
      pr1646v2ATMFwPerMCD7POutDropEx
         Counter64,
      pr1646v2ATMFwPerMCD7POutDropNoArp
         Counter64,
      pr1646v2ATMFwPerMCD7POutDropFilter
         Counter64,
      pr1646v2ATMFwPerMCD7PIfOutBandwidth
         Integer32,
      pr1646v2ATMFwPerMCD7PIfErrSec
         Counter32
      }

pr1646v2ATMFwPerMCD7PGlobalIx OBJECT-TYPE
   SYNTAX      GlobalIndex
   MAX-ACCESS  not-accessible
   STATUS      current
   DESCRIPTION
      "The value of the tlsCntTreeGlobalIndex of the MANAGED OBJECT."
   ::= {pr1646v2ATMFwPerMCD7PEntry 10}

pr1646v2ATMFwPerMCD7PTableIx OBJECT-TYPE
   SYNTAX      TableIndex
   MAX-ACCESS  not-accessible
   STATUS      current
   DESCRIPTION
      ""
   ::= {pr1646v2ATMFwPerMCD7PEntry 11}

pr1646v2ATMFwPerMCD7PSysUpTime OBJECT-TYPE
   SYNTAX      TimeTicks
   MAX-ACCESS  read-only
   STATUS      current
   DESCRIPTION
      "Path: atm.performance.pvcTable.mibCounters.d7Performance.sysUpTime

       Time in centi-second."
   ::= {pr1646v2ATMFwPerMCD7PEntry 16777216}

pr1646v2ATMFwPerMCD7PIfUpTime OBJECT-TYPE
   SYNTAX      TimeTicks
   MAX-ACCESS  read-only
   STATUS      current
   DESCRIPTION
      "Path: atm.performance.pvcTable.mibCounters.d7Performance.ifUpTime

       Time in centi-second."
   ::= {pr1646v2ATMFwPerMCD7PEntry 33554432}

pr1646v2ATMFwPerMCD7PIfStatChanges OBJECT-TYPE
   SYNTAX      Counter32
   MAX-ACCESS  read-only
   STATUS      current
   DESCRIPTION
      "Path: atm.performance.pvcTable.mibCounters.d7Performance.ifStatusChanges

       32 bit unsigned wrappable counter."
   ::= {pr1646v2ATMFwPerMCD7PEntry 50331648}

pr1646v2ATMFwPerMCD7PIfInOctets OBJECT-TYPE
   SYNTAX      Counter64
   MAX-ACCESS  read-only
   STATUS      current
   DESCRIPTION
      "Path: atm.performance.pvcTable.mibCounters.d7Performance.ifInOctets

       64 bit unsigned wrappable counter."
   ::= {pr1646v2ATMFwPerMCD7PEntry 67108864}

pr1646v2ATMFwPerMCD7PIfInUCPkts OBJECT-TYPE
   SYNTAX      Counter64
   MAX-ACCESS  read-only
   STATUS      current
   DESCRIPTION
      "Path: atm.performance.pvcTable.mibCounters.d7Performance.ifInUcastPkts

       64 bit unsigned wrappable counter."
   ::= {pr1646v2ATMFwPerMCD7PEntry 83886080}

pr1646v2ATMFwPerMCD7PIfInNUCPkts OBJECT-TYPE
   SYNTAX      Counter64
   MAX-ACCESS  read-only
   STATUS      current
   DESCRIPTION
      "Path: atm.performance.pvcTable.mibCounters.d7Performance.ifInNUcastPkts

       64 bit unsigned wrappable counter."
   ::= {pr1646v2ATMFwPerMCD7PEntry 100663296}

pr1646v2ATMFwPerMCD7PIfInBCPkts OBJECT-TYPE
   SYNTAX      Counter64
   MAX-ACCESS  read-only
   STATUS      current
   DESCRIPTION
      "Path: atm.performance.pvcTable.mibCounters.d7Performance.ifInBcastPkts

       64 bit unsigned wrappable counter."
   ::= {pr1646v2ATMFwPerMCD7PEntry 419430400}

pr1646v2ATMFwPerMCD7PIfInMCPkts OBJECT-TYPE
   SYNTAX      Counter64
   MAX-ACCESS  read-only
   STATUS      current
   DESCRIPTION
      "Path: atm.performance.pvcTable.mibCounters.d7Performance.ifInMcastPkts

       64 bit unsigned wrappable counter."
   ::= {pr1646v2ATMFwPerMCD7PEntry 436207616}

pr1646v2ATMFwPerMCD7PIfInDiscards OBJECT-TYPE
   SYNTAX      Counter64
   MAX-ACCESS  read-only
   STATUS      current
   DESCRIPTION
      "Path: atm.performance.pvcTable.mibCounters.d7Performance.ifInDiscards

       64 bit unsigned wrappable counter."
   ::= {pr1646v2ATMFwPerMCD7PEntry 117440512}

pr1646v2ATMFwPerMCD7PIfInErrors OBJECT-TYPE
   SYNTAX      Counter64
   MAX-ACCESS  read-only
   STATUS      current
   DESCRIPTION
      "Path: atm.performance.pvcTable.mibCounters.d7Performance.ifInErrors

       64 bit unsigned wrappable counter."
   ::= {pr1646v2ATMFwPerMCD7PEntry 134217728}

pr1646v2ATMFwPerMCD7PIfInUnkwn OBJECT-TYPE
   SYNTAX      Counter64
   MAX-ACCESS  read-only
   STATUS      current
   DESCRIPTION
      "Path: atm.performance.pvcTable.mibCounters.d7Performance.ifInUnknownProtos

       64 bit unsigned wrappable counter."
   ::= {pr1646v2ATMFwPerMCD7PEntry 150994944}

pr1646v2ATMFwPerMCD7PInDropEx OBJECT-TYPE
   SYNTAX      Counter64
   MAX-ACCESS  read-only
   STATUS      current
   DESCRIPTION
      "Path: atm.performance.pvcTable.mibCounters.d7Performance.ifInDropLevelExceeded

       64 bit unsigned wrappable counter."
   ::= {pr1646v2ATMFwPerMCD7PEntry 335544320}

pr1646v2ATMFwPerMCD7PInDropNoMac OBJECT-TYPE
   SYNTAX      Counter64
   MAX-ACCESS  read-only
   STATUS      current
   DESCRIPTION
      "Path: atm.performance.pvcTable.mibCounters.d7Performance.fInDiscardsNoMacFit

       64 bit unsigned wrappable counter."
   ::= {pr1646v2ATMFwPerMCD7PEntry 301989888}

pr1646v2ATMFwPerMCD7PInDropNUCast OBJECT-TYPE
   SYNTAX      Counter64
   MAX-ACCESS  read-only
   STATUS      current
   DESCRIPTION
      "Path: atm.performance.pvcTable.mibCounters.d7Performance.fInDiscardsNUCast

       64 bit unsigned wrappable counter."
   ::= {pr1646v2ATMFwPerMCD7PEntry 318767104}

pr1646v2ATMFwPerMCD7PInDropFilter OBJECT-TYPE
   SYNTAX      Counter64
   MAX-ACCESS  read-only
   STATUS      current
   DESCRIPTION
      "Path: atm.performance.pvcTable.mibCounters.d7Performance.fInDiscardsFilter

       64 bit unsigned wrappable counter."
   ::= {pr1646v2ATMFwPerMCD7PEntry 385875968}

pr1646v2ATMFwPerMCD7PIfInBandwidth OBJECT-TYPE
   SYNTAX      Integer32
   MAX-ACCESS  read-only
   STATUS      current
   DESCRIPTION
      "Path: atm.performance.pvcTable.mibCounters.d7Performance.ifInBandwidth

       unit name = bps
       formula = 8 * ; 8 /"
   ::= {pr1646v2ATMFwPerMCD7PEntry 268435456}

pr1646v2ATMFwPerMCD7PIfOutOctets OBJECT-TYPE
   SYNTAX      Counter64
   MAX-ACCESS  read-only
   STATUS      current
   DESCRIPTION
      "Path: atm.performance.pvcTable.mibCounters.d7Performance.ifOutOctets

       64 bit unsigned wrappable counter."
   ::= {pr1646v2ATMFwPerMCD7PEntry 167772160}

pr1646v2ATMFwPerMCD7PIfOutUCPkts OBJECT-TYPE
   SYNTAX      Counter64
   MAX-ACCESS  read-only
   STATUS      current
   DESCRIPTION
      "Path: atm.performance.pvcTable.mibCounters.d7Performance.ifOutUcastPkts

       64 bit unsigned wrappable counter."
   ::= {pr1646v2ATMFwPerMCD7PEntry 184549376}

pr1646v2ATMFwPerMCD7PIfOutNUCPkts OBJECT-TYPE
   SYNTAX      Counter64
   MAX-ACCESS  read-only
   STATUS      current
   DESCRIPTION
      "Path: atm.performance.pvcTable.mibCounters.d7Performance.ifOutNUcastPkts

       64 bit unsigned wrappable counter."
   ::= {pr1646v2ATMFwPerMCD7PEntry 201326592}

pr1646v2ATMFwPerMCD7PIfOutBCPkts OBJECT-TYPE
   SYNTAX      Counter64
   MAX-ACCESS  read-only
   STATUS      current
   DESCRIPTION
      "Path: atm.performance.pvcTable.mibCounters.d7Performance.ifOutBcastPkts

       64 bit unsigned wrappable counter."
   ::= {pr1646v2ATMFwPerMCD7PEntry 452984832}

pr1646v2ATMFwPerMCD7PIfOutMCPkts OBJECT-TYPE
   SYNTAX      Counter64
   MAX-ACCESS  read-only
   STATUS      current
   DESCRIPTION
      "Path: atm.performance.pvcTable.mibCounters.d7Performance.ifOutMcastPkts

       64 bit unsigned wrappable counter."
   ::= {pr1646v2ATMFwPerMCD7PEntry 469762048}

pr1646v2ATMFwPerMCD7PIfOutDiscards OBJECT-TYPE
   SYNTAX      Counter64
   MAX-ACCESS  read-only
   STATUS      current
   DESCRIPTION
      "Path: atm.performance.pvcTable.mibCounters.d7Performance.ifOutDiscards

       64 bit unsigned wrappable counter."
   ::= {pr1646v2ATMFwPerMCD7PEntry 218103808}

pr1646v2ATMFwPerMCD7PIfOutErrors OBJECT-TYPE
   SYNTAX      Counter64
   MAX-ACCESS  read-only
   STATUS      current
   DESCRIPTION
      "Path: atm.performance.pvcTable.mibCounters.d7Performance.ifOutErrors

       64 bit unsigned wrappable counter."
   ::= {pr1646v2ATMFwPerMCD7PEntry 234881024}

pr1646v2ATMFwPerMCD7POutDropEx OBJECT-TYPE
   SYNTAX      Counter64
   MAX-ACCESS  read-only
   STATUS      current
   DESCRIPTION
      "Path: atm.performance.pvcTable.mibCounters.d7Performance.ifOutDropLevelExceeded

       64 bit unsigned wrappable counter."
   ::= {pr1646v2ATMFwPerMCD7PEntry 352321536}

pr1646v2ATMFwPerMCD7POutDropNoArp OBJECT-TYPE
   SYNTAX      Counter64
   MAX-ACCESS  read-only
   STATUS      current
   DESCRIPTION
      "Path: atm.performance.pvcTable.mibCounters.d7Performance.ifOutDiscardsNoArp

       64 bit unsigned wrappable counter."
   ::= {pr1646v2ATMFwPerMCD7PEntry 369098752}

pr1646v2ATMFwPerMCD7POutDropFilter OBJECT-TYPE
   SYNTAX      Counter64
   MAX-ACCESS  read-only
   STATUS      current
   DESCRIPTION
      "Path: atm.performance.pvcTable.mibCounters.d7Performance.ifOutDiscardsFilter

       64 bit unsigned wrappable counter."
   ::= {pr1646v2ATMFwPerMCD7PEntry 402653184}

pr1646v2ATMFwPerMCD7PIfOutBandwidth OBJECT-TYPE
   SYNTAX      Integer32
   MAX-ACCESS  read-only
   STATUS      current
   DESCRIPTION
      "Path: atm.performance.pvcTable.mibCounters.d7Performance.ifOutBandwidth

       unit name = bps
       formula = 8 * ; 8 /"
   ::= {pr1646v2ATMFwPerMCD7PEntry 285212672}

pr1646v2ATMFwPerMCD7PIfErrSec OBJECT-TYPE
   SYNTAX      Counter32
   MAX-ACCESS  read-only
   STATUS      current
   DESCRIPTION
      "Path: atm.performance.pvcTable.mibCounters.d7Performance.ifErrSec

       32 bit unsigned wrappable counter."
   ::= {pr1646v2ATMFwPerMCD7PEntry 251658240}

pr1646v2ATMFwPerInPQs OBJECT-TYPE
   SYNTAX      SEQUENCE OF Pr1646v2ATMFwPerInPQsEntry
   MAX-ACCESS  not-accessible
   STATUS      current
   DESCRIPTION
      ""
   ::= {pr1646v2ATMFwPer 100663296}

pr1646v2ATMFwPerInPQsEntry OBJECT-TYPE
   SYNTAX      Pr1646v2ATMFwPerInPQsEntry
   MAX-ACCESS  not-accessible
   STATUS      current
   DESCRIPTION
      ""
   INDEX      { pr1646v2ATMFwPerInPQsGlobalIx,
                pr1646v2ATMFwPerTableIx,
                pr1646v2ATMFwPerInPQsTableIx }
   ::= {pr1646v2ATMFwPerInPQs 1}

Pr1646v2ATMFwPerInPQsEntry ::=
   SEQUENCE
      {
      pr1646v2ATMFwPerInPQsGlobalIx
         GlobalIndex,
      pr1646v2ATMFwPerInPQsTableIx
         TableIndex,
      pr1646v2ATMFwPerInPQsName
         INTEGER,
      pr1646v2ATMFwPerInPQsLength
         Integer32,
      pr1646v2ATMFwPerInPQsOctetLength
         Integer32,
      pr1646v2ATMFwPerInPQsRedLength
         Integer32,
      pr1646v2ATMFwPerInPQsPacketsTotal
         Counter64,
      pr1646v2ATMFwPerInPQsPacketsDirectTx
         Counter64,
      pr1646v2ATMFwPerInPQsPacketsQueued
         Counter64,
      pr1646v2ATMFwPerInPQsPacketsDropped
         Counter64,
      pr1646v2ATMFwPerInPQsPacketsRedDropped
         Counter64,
      pr1646v2ATMFwPerInPQsPacketsCirTx
         Counter64,
      pr1646v2ATMFwPerInPQsPacketsEirTx
         Counter64,
      pr1646v2ATMFwPerInPQsPacketsViolateTx
         Counter64,
      pr1646v2ATMFwPerInPQsOctetsTotal
         Counter64,
      pr1646v2ATMFwPerInPQsOctetsDirectTx
         Counter64,
      pr1646v2ATMFwPerInPQsOctetsQueued
         Counter64,
      pr1646v2ATMFwPerInPQsOctetsDropped
         Counter64,
      pr1646v2ATMFwPerInPQsOctetsRedDropped
         Counter64,
      pr1646v2ATMFwPerInPQsOctetsCirTx
         Counter64,
      pr1646v2ATMFwPerInPQsOctetsEirTx
         Counter64,
      pr1646v2ATMFwPerInPQsOctetsViolateTx
         Counter64,
      pr1646v2ATMFwPerInPQsOctetsBandwidth15sec
         Integer32,
      pr1646v2ATMFwPerInPQsOctetsBandwidth30sec
         Integer32,
      pr1646v2ATMFwPerInPQsOctetsBandwidth1min
         Integer32,
      pr1646v2ATMFwPerInPQsOctetsBandwidth2min
         Integer32,
      pr1646v2ATMFwPerInPQsOctetsBandwidth5min
         Integer32
      }

pr1646v2ATMFwPerInPQsGlobalIx OBJECT-TYPE
   SYNTAX      GlobalIndex
   MAX-ACCESS  not-accessible
   STATUS      current
   DESCRIPTION
      "The value of the tlsCntTreeGlobalIndex of the MANAGED OBJECT."
   ::= {pr1646v2ATMFwPerInPQsEntry 10}

pr1646v2ATMFwPerInPQsTableIx OBJECT-TYPE
   SYNTAX      TableIndex
   MAX-ACCESS  not-accessible
   STATUS      current
   DESCRIPTION
      ""
   ::= {pr1646v2ATMFwPerInPQsEntry 11}

pr1646v2ATMFwPerInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2ATMFwPerInPQsEntry 16777216}

pr1646v2ATMFwPerInPQsLength OBJECT-TYPE
   SYNTAX      Integer32
   MAX-ACCESS  read-only
   STATUS      current
   DESCRIPTION
      "Path: atm.performance.pvcTable.inPriorityQueues.length"
   ::= {pr1646v2ATMFwPerInPQsEntry 33554432}

pr1646v2ATMFwPerInPQsOctetLength OBJECT-TYPE
   SYNTAX      Integer32
   MAX-ACCESS  read-only
   STATUS      current
   DESCRIPTION
      "Path: atm.performance.pvcTable.inPriorityQueues.octetLength"
   ::= {pr1646v2ATMFwPerInPQsEntry 150994944}

pr1646v2ATMFwPerInPQsRedLength OBJECT-TYPE
   SYNTAX      Integer32
   MAX-ACCESS  read-only
   STATUS      current
   DESCRIPTION
      "Path: atm.performance.pvcTable.inPriorityQueues.redLength"
   ::= {pr1646v2ATMFwPerInPQsEntry 134217728}

pr1646v2ATMFwPerInPQsPacketsTotal OBJECT-TYPE
   SYNTAX      Counter64
   MAX-ACCESS  read-only
   STATUS      current
   DESCRIPTION
      "Path: atm.performance.pvcTable.inPriorityQueues.packets.total

       64 bit unsigned wrappable counter."
   ::= {pr1646v2ATMFwPerInPQsEntry 50790400}

pr1646v2ATMFwPerInPQsPacketsDirectTx OBJECT-TYPE
   SYNTAX      Counter64
   MAX-ACCESS  read-only
   STATUS      current
   DESCRIPTION
      "Path: atm.performance.pvcTable.inPriorityQueues.packets.directTx

       64 bit unsigned wrappable counter."
   ::= {pr1646v2ATMFwPerInPQsEntry 50397184}

pr1646v2ATMFwPerInPQsPacketsQueued OBJECT-TYPE
   SYNTAX      Counter64
   MAX-ACCESS  read-only
   STATUS      current
   DESCRIPTION
      "Path: atm.performance.pvcTable.inPriorityQueues.packets.queued

       64 bit unsigned wrappable counter."
   ::= {pr1646v2ATMFwPerInPQsEntry 50462720}

pr1646v2ATMFwPerInPQsPacketsDropped OBJECT-TYPE
   SYNTAX      Counter64
   MAX-ACCESS  read-only
   STATUS      current
   DESCRIPTION
      "Path: atm.performance.pvcTable.inPriorityQueues.packets.dropped

       64 bit unsigned wrappable counter."
   ::= {pr1646v2ATMFwPerInPQsEntry 50528256}

pr1646v2ATMFwPerInPQsPacketsRedDropped OBJECT-TYPE
   SYNTAX      Counter64
   MAX-ACCESS  read-only
   STATUS      current
   DESCRIPTION
      "Path: atm.performance.pvcTable.inPriorityQueues.packets.redDropped

       64 bit unsigned wrappable counter."
   ::= {pr1646v2ATMFwPerInPQsEntry 50724864}

pr1646v2ATMFwPerInPQsPacketsCirTx OBJECT-TYPE
   SYNTAX      Counter64
   MAX-ACCESS  read-only
   STATUS      current
   DESCRIPTION
      "Path: atm.performance.pvcTable.inPriorityQueues.packets.cirTx

       64 bit unsigned wrappable counter."
   ::= {pr1646v2ATMFwPerInPQsEntry 50593792}

pr1646v2ATMFwPerInPQsPacketsEirTx OBJECT-TYPE
   SYNTAX      Counter64
   MAX-ACCESS  read-only
   STATUS      current
   DESCRIPTION
      "Path: atm.performance.pvcTable.inPriorityQueues.packets.eirTx

       64 bit unsigned wrappable counter."
   ::= {pr1646v2ATMFwPerInPQsEntry 50659328}

pr1646v2ATMFwPerInPQsPacketsViolateTx OBJECT-TYPE
   SYNTAX      Counter64
   MAX-ACCESS  read-only
   STATUS      current
   DESCRIPTION
      "Path: atm.performance.pvcTable.inPriorityQueues.packets.violateTx

       64 bit unsigned wrappable counter."
   ::= {pr1646v2ATMFwPerInPQsEntry 50855936}

pr1646v2ATMFwPerInPQsOctetsTotal OBJECT-TYPE
   SYNTAX      Counter64
   MAX-ACCESS  read-only
   STATUS      current
   DESCRIPTION
      "Path: atm.performance.pvcTable.inPriorityQueues.octets.total

       64 bit unsigned wrappable counter."
   ::= {pr1646v2ATMFwPerInPQsEntry 67567616}

pr1646v2ATMFwPerInPQsOctetsDirectTx OBJECT-TYPE
   SYNTAX      Counter64
   MAX-ACCESS  read-only
   STATUS      current
   DESCRIPTION
      "Path: atm.performance.pvcTable.inPriorityQueues.octets.directTx

       64 bit unsigned wrappable counter."
   ::= {pr1646v2ATMFwPerInPQsEntry 67174400}

pr1646v2ATMFwPerInPQsOctetsQueued OBJECT-TYPE
   SYNTAX      Counter64
   MAX-ACCESS  read-only
   STATUS      current
   DESCRIPTION
      "Path: atm.performance.pvcTable.inPriorityQueues.octets.queued

       64 bit unsigned wrappable counter."
   ::= {pr1646v2ATMFwPerInPQsEntry 67239936}

pr1646v2ATMFwPerInPQsOctetsDropped OBJECT-TYPE
   SYNTAX      Counter64
   MAX-ACCESS  read-only
   STATUS      current
   DESCRIPTION
      "Path: atm.performance.pvcTable.inPriorityQueues.octets.dropped

       64 bit unsigned wrappable counter."
   ::= {pr1646v2ATMFwPerInPQsEntry 67305472}

pr1646v2ATMFwPerInPQsOctetsRedDropped OBJECT-TYPE
   SYNTAX      Counter64
   MAX-ACCESS  read-only
   STATUS      current
   DESCRIPTION
      "Path: atm.performance.pvcTable.inPriorityQueues.octets.redDropped

       64 bit unsigned wrappable counter."
   ::= {pr1646v2ATMFwPerInPQsEntry 67502080}

pr1646v2ATMFwPerInPQsOctetsCirTx OBJECT-TYPE
   SYNTAX      Counter64
   MAX-ACCESS  read-only
   STATUS      current
   DESCRIPTION
      "Path: atm.performance.pvcTable.inPriorityQueues.octets.cirTx

       64 bit unsigned wrappable counter."
   ::= {pr1646v2ATMFwPerInPQsEntry 67371008}

pr1646v2ATMFwPerInPQsOctetsEirTx OBJECT-TYPE
   SYNTAX      Counter64
   MAX-ACCESS  read-only
   STATUS      current
   DESCRIPTION
      "Path: atm.performance.pvcTable.inPriorityQueues.octets.eirTx

       64 bit unsigned wrappable counter."
   ::= {pr1646v2ATMFwPerInPQsEntry 67436544}

pr1646v2ATMFwPerInPQsOctetsViolateTx OBJECT-TYPE
   SYNTAX      Counter64
   MAX-ACCESS  read-only
   STATUS      current
   DESCRIPTION
      "Path: atm.performance.pvcTable.inPriorityQueues.octets.violateTx

       64 bit unsigned wrappable counter."
   ::= {pr1646v2ATMFwPerInPQsEntry 67633152}

pr1646v2ATMFwPerInPQsOctetsBandwidth15sec OBJECT-TYPE
   SYNTAX      Integer32
   MAX-ACCESS  read-only
   STATUS      current
   DESCRIPTION
      "Path: atm.performance.pvcTable.inPriorityQueues.octets.bandwidth.15sec

       unit name = bps
       formula = 8 * ; 8 /"
   ::= {pr1646v2ATMFwPerInPQsEntry 70386944}

pr1646v2ATMFwPerInPQsOctetsBandwidth30sec OBJECT-TYPE
   SYNTAX      Integer32
   MAX-ACCESS  read-only
   STATUS      current
   DESCRIPTION
      "Path: atm.performance.pvcTable.inPriorityQueues.octets.bandwidth.30sec

       unit name = bps
       formula = 8 * ; 8 /"
   ::= {pr1646v2ATMFwPerInPQsEntry 70388224}

pr1646v2ATMFwPerInPQsOctetsBandwidth1min OBJECT-TYPE
   SYNTAX      Integer32
   MAX-ACCESS  read-only
   STATUS      current
   DESCRIPTION
      "Path: atm.performance.pvcTable.inPriorityQueues.octets.bandwidth.1min

       unit name = bps
       formula = 8 * ; 8 /"
   ::= {pr1646v2ATMFwPerInPQsEntry 70390784}

pr1646v2ATMFwPerInPQsOctetsBandwidth2min OBJECT-TYPE
   SYNTAX      Integer32
   MAX-ACCESS  read-only
   STATUS      current
   DESCRIPTION
      "Path: atm.performance.pvcTable.inPriorityQueues.octets.bandwidth.2min

       unit name = bps
       formula = 8 * ; 8 /"
   ::= {pr1646v2ATMFwPerInPQsEntry 70395904}

pr1646v2ATMFwPerInPQsOctetsBandwidth5min OBJECT-TYPE
   SYNTAX      Integer32
   MAX-ACCESS  read-only
   STATUS      current
   DESCRIPTION
      "Path: atm.performance.pvcTable.inPriorityQueues.octets.bandwidth.5min

       unit name = bps
       formula = 8 * ; 8 /"
   ::= {pr1646v2ATMFwPerInPQsEntry 70411264}

pr1646v2ATMFwPerInPQsH2Performance OBJECT-TYPE
   SYNTAX      SEQUENCE OF Pr1646v2ATMFwPerInPQsH2PerformanceEntry
   MAX-ACCESS  not-accessible
   STATUS      current
   DESCRIPTION
      ""
   ::= {pr1646v2ATMFwPer 100990976}

pr1646v2ATMFwPerInPQsH2PerformanceEntry OBJECT-TYPE
   SYNTAX      Pr1646v2ATMFwPerInPQsH2PerformanceEntry
   MAX-ACCESS  not-accessible
   STATUS      current
   DESCRIPTION
      ""
   INDEX      { pr1646v2ATMFwPerInPQsH2PerformanceGlobalIx,
                pr1646v2ATMFwPerTableIx,
                pr1646v2ATMFwPerInPQsTableIx,
                pr1646v2ATMFwPerInPQsH2PerformanceTableIx }
   ::= {pr1646v2ATMFwPerInPQsH2Performance 1}

Pr1646v2ATMFwPerInPQsH2PerformanceEntry ::=
   SEQUENCE
      {
      pr1646v2ATMFwPerInPQsH2PerformanceGlobalIx
         GlobalIndex,
      pr1646v2ATMFwPerInPQsH2PerformanceTableIx
         TableIndex,
      pr1646v2ATMFwPerInPQsH2PerformanceSysUpTime
         TimeTicks,
      pr1646v2ATMFwPerInPQsH2PerformanceTotPkts
         Counter64,
      pr1646v2ATMFwPerInPQsH2PerformanceDirTxPkts
         Counter64,
      pr1646v2ATMFwPerInPQsH2PerformanceQdPkts
         Counter64,
      pr1646v2ATMFwPerInPQsH2PerformanceDropPkts
         Counter64,
      pr1646v2ATMFwPerInPQsH2PerformanceRDropPkts
         Counter64,
      pr1646v2ATMFwPerInPQsH2PerformanceCirTxPkts
         Counter64,
      pr1646v2ATMFwPerInPQsH2PerformanceEirTxPkts
         Counter64,
      pr1646v2ATMFwPerInPQsH2PerformanceViolTxPkts
         Counter64,
      pr1646v2ATMFwPerInPQsH2PerformanceTotOcts
         Counter64,
      pr1646v2ATMFwPerInPQsH2PerformanceDirTxOcts
         Counter64,
      pr1646v2ATMFwPerInPQsH2PerformanceQdOcts
         Counter64,
      pr1646v2ATMFwPerInPQsH2PerformanceDropOcts
         Counter64,
      pr1646v2ATMFwPerInPQsH2PerformanceRDropOcts
         Counter64,
      pr1646v2ATMFwPerInPQsH2PerformanceCirTxOcts
         Counter64,
      pr1646v2ATMFwPerInPQsH2PerformanceEirTxOcts
         Counter64,
      pr1646v2ATMFwPerInPQsH2PerformanceViolTxOcts
         Counter64,
      pr1646v2ATMFwPerInPQsH2PerformanceBandwidth
         Integer32
      }

pr1646v2ATMFwPerInPQsH2PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerInPQsH2PerformanceEntry 10}

pr1646v2ATMFwPerInPQsH2PerformanceTableIx OBJECT-TYPE
   SYNTAX      TableIndex
   MAX-ACCESS  not-accessible
   STATUS      current
   DESCRIPTION
      ""
   ::= {pr1646v2ATMFwPerInPQsH2PerformanceEntry 11}

pr1646v2ATMFwPerInPQsH2PerformanceSysUpTime OBJECT-TYPE
   SYNTAX      TimeTicks
   MAX-ACCESS  read-only
   STATUS      current
   DESCRIPTION
      "Path: atm.performance.pvcTable.inPriorityQueues.h2Performance.sysUpTime

       Time in centi-second."
   ::= {pr1646v2ATMFwPerInPQsH2PerformanceEntry 16777216}

pr1646v2ATMFwPerInPQsH2PerformanceTotPkts OBJECT-TYPE
   SYNTAX      Counter64
   MAX-ACCESS  read-only
   STATUS      current
   DESCRIPTION
      "Path: atm.performance.pvcTable.inPriorityQueues.h2Performance.totalPkts

       64 bit unsigned wrappable counter."
   ::= {pr1646v2ATMFwPerInPQsH2PerformanceEntry 234881024}

pr1646v2ATMFwPerInPQsH2PerformanceDirTxPkts OBJECT-TYPE
   SYNTAX      Counter64
   MAX-ACCESS  read-only
   STATUS      current
   DESCRIPTION
      "Path: atm.performance.pvcTable.inPriorityQueues.h2Performance.directTxPkts

       64 bit unsigned wrappable counter."
   ::= {pr1646v2ATMFwPerInPQsH2PerformanceEntry 33554432}

pr1646v2ATMFwPerInPQsH2PerformanceQdPkts OBJECT-TYPE
   SYNTAX      Counter64
   MAX-ACCESS  read-only
   STATUS      current
   DESCRIPTION
      "Path: atm.performance.pvcTable.inPriorityQueues.h2Performance.queuedPkts

       64 bit unsigned wrappable counter."
   ::= {pr1646v2ATMFwPerInPQsH2PerformanceEntry 50331648}

pr1646v2ATMFwPerInPQsH2PerformanceDropPkts OBJECT-TYPE
   SYNTAX      Counter64
   MAX-ACCESS  read-only
   STATUS      current
   DESCRIPTION
      "Path: atm.performance.pvcTable.inPriorityQueues.h2Performance.droppedPkts

       64 bit unsigned wrappable counter."
   ::= {pr1646v2ATMFwPerInPQsH2PerformanceEntry 67108864}

pr1646v2ATMFwPerInPQsH2PerformanceRDropPkts OBJECT-TYPE
   SYNTAX      Counter64
   MAX-ACCESS  read-only
   STATUS      current
   DESCRIPTION
      "Path: atm.performance.pvcTable.inPriorityQueues.h2Performance.redDroppedPkts

       64 bit unsigned wrappable counter."
   ::= {pr1646v2ATMFwPerInPQsH2PerformanceEntry 201326592}

pr1646v2ATMFwPerInPQsH2PerformanceCirTxPkts OBJECT-TYPE
   SYNTAX      Counter64
   MAX-ACCESS  read-only
   STATUS      current
   DESCRIPTION
      "Path: atm.performance.pvcTable.inPriorityQueues.h2Performance.cirTxPkts

       64 bit unsigned wrappable counter."
   ::= {pr1646v2ATMFwPerInPQsH2PerformanceEntry 83886080}

pr1646v2ATMFwPerInPQsH2PerformanceEirTxPkts OBJECT-TYPE
   SYNTAX      Counter64
   MAX-ACCESS  read-only
   STATUS      current
   DESCRIPTION
      "Path: atm.performance.pvcTable.inPriorityQueues.h2Performance.eirTxPkts

       64 bit unsigned wrappable counter."
   ::= {pr1646v2ATMFwPerInPQsH2PerformanceEntry 100663296}

pr1646v2ATMFwPerInPQsH2PerformanceViolTxPkts OBJECT-TYPE
   SYNTAX      Counter64
   MAX-ACCESS  read-only
   STATUS      current
   DESCRIPTION
      "Path: atm.performance.pvcTable.inPriorityQueues.h2Performance.violateTxPkts

       64 bit unsigned wrappable counter."
   ::= {pr1646v2ATMFwPerInPQsH2PerformanceEntry 301989888}

pr1646v2ATMFwPerInPQsH2PerformanceTotOcts OBJECT-TYPE
   SYNTAX      Counter64
   MAX-ACCESS  read-only
   STATUS      current
   DESCRIPTION
      "Path: atm.performance.pvcTable.inPriorityQueues.h2Performance.totalOctets

       64 bit unsigned wrappable counter."
   ::= {pr1646v2ATMFwPerInPQsH2PerformanceEntry 251658240}

pr1646v2ATMFwPerInPQsH2PerformanceDirTxOcts OBJECT-TYPE
   SYNTAX      Counter64
   MAX-ACCESS  read-only
   STATUS      current
   DESCRIPTION
      "Path: atm.performance.pvcTable.inPriorityQueues.h2Performance.directTxOctets

       64 bit unsigned wrappable counter."
   ::= {pr1646v2ATMFwPerInPQsH2PerformanceEntry 117440512}

pr1646v2ATMFwPerInPQsH2PerformanceQdOcts OBJECT-TYPE
   SYNTAX      Counter64
   MAX-ACCESS  read-only
   STATUS      current
   DESCRIPTION
      "Path: atm.performance.pvcTable.inPriorityQueues.h2Performance.queuedOctets

       64 bit unsigned wrappable counter."
   ::= {pr1646v2ATMFwPerInPQsH2PerformanceEntry 134217728}

pr1646v2ATMFwPerInPQsH2PerformanceDropOcts OBJECT-TYPE
   SYNTAX      Counter64
   MAX-ACCESS  read-only
   STATUS      current
   DESCRIPTION
      "Path: atm.performance.pvcTable.inPriorityQueues.h2Performance.droppedOctets

       64 bit unsigned wrappable counter."
   ::= {pr1646v2ATMFwPerInPQsH2PerformanceEntry 150994944}

pr1646v2ATMFwPerInPQsH2PerformanceRDropOcts OBJECT-TYPE
   SYNTAX      Counter64
   MAX-ACCESS  read-only
   STATUS      current
   DESCRIPTION
      "Path: atm.performance.pvcTable.inPriorityQueues.h2Performance.redDroppedOctets

       64 bit unsigned wrappable counter."
   ::= {pr1646v2ATMFwPerInPQsH2PerformanceEntry 218103808}

pr1646v2ATMFwPerInPQsH2PerformanceCirTxOcts OBJECT-TYPE
   SYNTAX      Counter64
   MAX-ACCESS  read-only
   STATUS      current
   DESCRIPTION
      "Path: atm.performance.pvcTable.inPriorityQueues.h2Performance.cirTxOctets

       64 bit unsigned wrappable counter."
   ::= {pr1646v2ATMFwPerInPQsH2PerformanceEntry 167772160}

pr1646v2ATMFwPerInPQsH2PerformanceEirTxOcts OBJECT-TYPE
   SYNTAX      Counter64
   MAX-ACCESS  read-only
   STATUS      current
   DESCRIPTION
      "Path: atm.performance.pvcTable.inPriorityQueues.h2Performance.eirTxOctets

       64 bit unsigned wrappable counter."
   ::= {pr1646v2ATMFwPerInPQsH2PerformanceEntry 184549376}

pr1646v2ATMFwPerInPQsH2PerformanceViolTxOcts OBJECT-TYPE
   SYNTAX      Counter64
   MAX-ACCESS  read-only
   STATUS      current
   DESCRIPTION
      "Path: atm.performance.pvcTable.inPriorityQueues.h2Performance.violateTxOctets

       64 bit unsigned wrappable counter."
   ::= {pr1646v2ATMFwPerInPQsH2PerformanceEntry 318767104}

pr1646v2ATMFwPerInPQsH2PerformanceBandwidth OBJECT-TYPE
   SYNTAX      Integer32
   MAX-ACCESS  read-only
   STATUS      current
   DESCRIPTION
      "Path: atm.performance.pvcTable.inPriorityQueues.h2Performance.bandwidth

       unit name = bps
       formula = 8 * ; 8 /"
   ::= {pr1646v2ATMFwPerInPQsH2PerformanceEntry 268435456}

pr1646v2ATMFwPerInPQsH24Performance OBJECT-TYPE
   SYNTAX      SEQUENCE OF Pr1646v2ATMFwPerInPQsH24PerformanceEntry
   MAX-ACCESS  not-accessible
   STATUS      current
   DESCRIPTION
      ""
   ::= {pr1646v2ATMFwPer 101056512}

pr1646v2ATMFwPerInPQsH24PerformanceEntry OBJECT-TYPE
   SYNTAX      Pr1646v2ATMFwPerInPQsH24PerformanceEntry
   MAX-ACCESS  not-accessible
   STATUS      current
   DESCRIPTION
      ""
   INDEX      { pr1646v2ATMFwPerInPQsH24PerformanceGlobalIx,
                pr1646v2ATMFwPerTableIx,
                pr1646v2ATMFwPerInPQsTableIx,
                pr1646v2ATMFwPerInPQsH24PerformanceTableIx }
   ::= {pr1646v2ATMFwPerInPQsH24Performance 1}

Pr1646v2ATMFwPerInPQsH24PerformanceEntry ::=
   SEQUENCE
      {
      pr1646v2ATMFwPerInPQsH24PerformanceGlobalIx
         GlobalIndex,
      pr1646v2ATMFwPerInPQsH24PerformanceTableIx
         TableIndex,
      pr1646v2ATMFwPerInPQsH24PerformanceSysUpTime
         TimeTicks,
      pr1646v2ATMFwPerInPQsH24PerformanceTotPkts
         Counter64,
      pr1646v2ATMFwPerInPQsH24PerformanceDirTxPkts
         Counter64,
      pr1646v2ATMFwPerInPQsH24PerformanceQdPkts
         Counter64,
      pr1646v2ATMFwPerInPQsH24PerformanceDropPkts
         Counter64,
      pr1646v2ATMFwPerInPQsH24PerformanceRDropPkts
         Counter64,
      pr1646v2ATMFwPerInPQsH24PerformanceCirTxPkts
         Counter64,
      pr1646v2ATMFwPerInPQsH24PerformanceEirTxPkts
         Counter64,
      pr1646v2ATMFwPerInPQsH24PerformanceViolTxPkts
         Counter64,
      pr1646v2ATMFwPerInPQsH24PerformanceTotOcts
         Counter64,
      pr1646v2ATMFwPerInPQsH24PerformanceDirTxOcts
         Counter64,
      pr1646v2ATMFwPerInPQsH24PerformanceQdOcts
         Counter64,
      pr1646v2ATMFwPerInPQsH24PerformanceDropOcts
         Counter64,
      pr1646v2ATMFwPerInPQsH24PerformanceRDropOcts
         Counter64,
      pr1646v2ATMFwPerInPQsH24PerformanceCirTxOcts
         Counter64,
      pr1646v2ATMFwPerInPQsH24PerformanceEirTxOcts
         Counter64,
      pr1646v2ATMFwPerInPQsH24PerformanceViolTxOcts
         Counter64,
      pr1646v2ATMFwPerInPQsH24PerformanceBandwidth
         Integer32
      }

pr1646v2ATMFwPerInPQsH24PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerInPQsH24PerformanceEntry 10}

pr1646v2ATMFwPerInPQsH24PerformanceTableIx OBJECT-TYPE
   SYNTAX      TableIndex
   MAX-ACCESS  not-accessible
   STATUS      current
   DESCRIPTION
      ""
   ::= {pr1646v2ATMFwPerInPQsH24PerformanceEntry 11}

pr1646v2ATMFwPerInPQsH24PerformanceSysUpTime OBJECT-TYPE
   SYNTAX      TimeTicks
   MAX-ACCESS  read-only
   STATUS      current
   DESCRIPTION
      "Path: atm.performance.pvcTable.inPriorityQueues.h24Performance.sysUpTime

       Time in centi-second."
   ::= {pr1646v2ATMFwPerInPQsH24PerformanceEntry 16777216}

pr1646v2ATMFwPerInPQsH24PerformanceTotPkts OBJECT-TYPE
   SYNTAX      Counter64
   MAX-ACCESS  read-only
   STATUS      current
   DESCRIPTION
      "Path: atm.performance.pvcTable.inPriorityQueues.h24Performance.totalPkts

       64 bit unsigned wrappable counter."
   ::= {pr1646v2ATMFwPerInPQsH24PerformanceEntry 234881024}

pr1646v2ATMFwPerInPQsH24PerformanceDirTxPkts OBJECT-TYPE
   SYNTAX      Counter64
   MAX-ACCESS  read-only
   STATUS      current
   DESCRIPTION
      "Path: atm.performance.pvcTable.inPriorityQueues.h24Performance.directTxPkts

       64 bit unsigned wrappable counter."
   ::= {pr1646v2ATMFwPerInPQsH24PerformanceEntry 33554432}

pr1646v2ATMFwPerInPQsH24PerformanceQdPkts OBJECT-TYPE
   SYNTAX      Counter64
   MAX-ACCESS  read-only
   STATUS      current
   DESCRIPTION
      "Path: atm.performance.pvcTable.inPriorityQueues.h24Performance.queuedPkts

       64 bit unsigned wrappable counter."
   ::= {pr1646v2ATMFwPerInPQsH24PerformanceEntry 50331648}

pr1646v2ATMFwPerInPQsH24PerformanceDropPkts OBJECT-TYPE
   SYNTAX      Counter64
   MAX-ACCESS  read-only
   STATUS      current
   DESCRIPTION
      "Path: atm.performance.pvcTable.inPriorityQueues.h24Performance.droppedPkts

       64 bit unsigned wrappable counter."
   ::= {pr1646v2ATMFwPerInPQsH24PerformanceEntry 67108864}

pr1646v2ATMFwPerInPQsH24PerformanceRDropPkts OBJECT-TYPE
   SYNTAX      Counter64
   MAX-ACCESS  read-only
   STATUS      current
   DESCRIPTION
      "Path: atm.performance.pvcTable.inPriorityQueues.h24Performance.redDroppedPkts

       64 bit unsigned wrappable counter."
   ::= {pr1646v2ATMFwPerInPQsH24PerformanceEntry 201326592}

pr1646v2ATMFwPerInPQsH24PerformanceCirTxPkts OBJECT-TYPE
   SYNTAX      Counter64
   MAX-ACCESS  read-only
   STATUS      current
   DESCRIPTION
      "Path: atm.performance.pvcTable.inPriorityQueues.h24Performance.cirTxPkts

       64 bit unsigned wrappable counter."
   ::= {pr1646v2ATMFwPerInPQsH24PerformanceEntry 83886080}

pr1646v2ATMFwPerInPQsH24PerformanceEirTxPkts OBJECT-TYPE
   SYNTAX      Counter64
   MAX-ACCESS  read-only
   STATUS      current
   DESCRIPTION
      "Path: atm.performance.pvcTable.inPriorityQueues.h24Performance.eirTxPkts

       64 bit unsigned wrappable counter."
   ::= {pr1646v2ATMFwPerInPQsH24PerformanceEntry 100663296}

pr1646v2ATMFwPerInPQsH24PerformanceViolTxPkts OBJECT-TYPE
   SYNTAX      Counter64
   MAX-ACCESS  read-only
   STATUS      current
   DESCRIPTION
      "Path: atm.performance.pvcTable.inPriorityQueues.h24Performance.violateTxPkts

       64 bit unsigned wrappable counter."
   ::= {pr1646v2ATMFwPerInPQsH24PerformanceEntry 301989888}

pr1646v2ATMFwPerInPQsH24PerformanceTotOcts OBJECT-TYPE
   SYNTAX      Counter64
   MAX-ACCESS  read-only
   STATUS      current
   DESCRIPTION
      "Path: atm.performance.pvcTable.inPriorityQueues.h24Performance.totalOctets

       64 bit unsigned wrappable counter."
   ::= {pr1646v2ATMFwPerInPQsH24PerformanceEntry 251658240}

pr1646v2ATMFwPerInPQsH24PerformanceDirTxOcts OBJECT-TYPE
   SYNTAX      Counter64
   MAX-ACCESS  read-only
   STATUS      current
   DESCRIPTION
      "Path: atm.performance.pvcTable.inPriorityQueues.h24Performance.directTxOctets

       64 bit unsigned wrappable counter."
   ::= {pr1646v2ATMFwPerInPQsH24PerformanceEntry 117440512}

pr1646v2ATMFwPerInPQsH24PerformanceQdOcts OBJECT-TYPE
   SYNTAX      Counter64
   MAX-ACCESS  read-only
   STATUS      current
   DESCRIPTION
      "Path: atm.performance.pvcTable.inPriorityQueues.h24Performance.queuedOctets

       64 bit unsigned wrappable counter."
   ::= {pr1646v2ATMFwPerInPQsH24PerformanceEntry 134217728}

pr1646v2ATMFwPerInPQsH24PerformanceDropOcts OBJECT-TYPE
   SYNTAX      Counter64
   MAX-ACCESS  read-only
   STATUS      current
   DESCRIPTION
      "Path: atm.performance.pvcTable.inPriorityQueues.h24Performance.droppedOctets

       64 bit unsigned wrappable counter."
   ::= {pr1646v2ATMFwPerInPQsH24PerformanceEntry 150994944}

pr1646v2ATMFwPerInPQsH24PerformanceRDropOcts OBJECT-TYPE
   SYNTAX      Counter64
   MAX-ACCESS  read-only
   STATUS      current
   DESCRIPTION
      "Path: atm.performance.pvcTable.inPriorityQueues.h24Performance.redDroppedOctets

       64 bit unsigned wrappable counter."
   ::= {pr1646v2ATMFwPerInPQsH24PerformanceEntry 218103808}

pr1646v2ATMFwPerInPQsH24PerformanceCirTxOcts OBJECT-TYPE
   SYNTAX      Counter64
   MAX-ACCESS  read-only
   STATUS      current
   DESCRIPTION
      "Path: atm.performance.pvcTable.inPriorityQueues.h24Performance.cirTxOctets

       64 bit unsigned wrappable counter."
   ::= {pr1646v2ATMFwPerInPQsH24PerformanceEntry 167772160}

pr1646v2ATMFwPerInPQsH24PerformanceEirTxOcts OBJECT-TYPE
   SYNTAX      Counter64
   MAX-ACCESS  read-only
   STATUS      current
   DESCRIPTION
      "Path: atm.performance.pvcTable.inPriorityQueues.h24Performance.eirTxOctets

       64 bit unsigned wrappable counter."
   ::= {pr1646v2ATMFwPerInPQsH24PerformanceEntry 184549376}

pr1646v2ATMFwPerInPQsH24PerformanceViolTxOcts OBJECT-TYPE
   SYNTAX      Counter64
   MAX-ACCESS  read-only
   STATUS      current
   DESCRIPTION
      "Path: atm.performance.pvcTable.inPriorityQueues.h24Performance.violateTxOctets

       64 bit unsigned wrappable counter."
   ::= {pr1646v2ATMFwPerInPQsH24PerformanceEntry 318767104}

pr1646v2ATMFwPerInPQsH24PerformanceBandwidth OBJECT-TYPE
   SYNTAX      Integer32
   MAX-ACCESS  read-only
   STATUS      current
   DESCRIPTION
      "Path: atm.performance.pvcTable.inPriorityQueues.h24Performance.bandwidth

       unit name = bps
       formula = 8 * ; 8 /"
   ::= {pr1646v2ATMFwPerInPQsH24PerformanceEntry 268435456}

pr1646v2ATMFwPerInPQsD7Performance OBJECT-TYPE
   SYNTAX      SEQUENCE OF Pr1646v2ATMFwPerInPQsD7PerformanceEntry
   MAX-ACCESS  not-accessible
   STATUS      current
   DESCRIPTION
      ""
   ::= {pr1646v2ATMFwPer 101122048}

pr1646v2ATMFwPerInPQsD7PerformanceEntry OBJECT-TYPE
   SYNTAX      Pr1646v2ATMFwPerInPQsD7PerformanceEntry
   MAX-ACCESS  not-accessible
   STATUS      current
   DESCRIPTION
      ""
   INDEX      { pr1646v2ATMFwPerInPQsD7PerformanceGlobalIx,
                pr1646v2ATMFwPerTableIx,
                pr1646v2ATMFwPerInPQsTableIx,
                pr1646v2ATMFwPerInPQsD7PerformanceTableIx }
   ::= {pr1646v2ATMFwPerInPQsD7Performance 1}

Pr1646v2ATMFwPerInPQsD7PerformanceEntry ::=
   SEQUENCE
      {
      pr1646v2ATMFwPerInPQsD7PerformanceGlobalIx
         GlobalIndex,
      pr1646v2ATMFwPerInPQsD7PerformanceTableIx
         TableIndex,
      pr1646v2ATMFwPerInPQsD7PerformanceSysUpTime
         TimeTicks,
      pr1646v2ATMFwPerInPQsD7PerformanceTotPkts
         Counter64,
      pr1646v2ATMFwPerInPQsD7PerformanceDirTxPkts
         Counter64,
      pr1646v2ATMFwPerInPQsD7PerformanceQdPkts
         Counter64,
      pr1646v2ATMFwPerInPQsD7PerformanceDropPkts
         Counter64,
      pr1646v2ATMFwPerInPQsD7PerformanceRDropPkts
         Counter64,
      pr1646v2ATMFwPerInPQsD7PerformanceCirTxPkts
         Counter64,
      pr1646v2ATMFwPerInPQsD7PerformanceEirTxPkts
         Counter64,
      pr1646v2ATMFwPerInPQsD7PerformanceViolTxPkts
         Counter64,
      pr1646v2ATMFwPerInPQsD7PerformanceTotOcts
         Counter64,
      pr1646v2ATMFwPerInPQsD7PerformanceDirTxOcts
         Counter64,
      pr1646v2ATMFwPerInPQsD7PerformanceQdOcts
         Counter64,
      pr1646v2ATMFwPerInPQsD7PerformanceDropOcts
         Counter64,
      pr1646v2ATMFwPerInPQsD7PerformanceRDropOcts
         Counter64,
      pr1646v2ATMFwPerInPQsD7PerformanceCirTxOcts
         Counter64,
      pr1646v2ATMFwPerInPQsD7PerformanceEirTxOcts
         Counter64,
      pr1646v2ATMFwPerInPQsD7PerformanceViolTxOcts
         Counter64,
      pr1646v2ATMFwPerInPQsD7PerformanceBandwidth
         Integer32
      }

pr1646v2ATMFwPerInPQsD7PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerInPQsD7PerformanceEntry 10}

pr1646v2ATMFwPerInPQsD7PerformanceTableIx OBJECT-TYPE
   SYNTAX      TableIndex
   MAX-ACCESS  not-accessible
   STATUS      current
   DESCRIPTION
      ""
   ::= {pr1646v2ATMFwPerInPQsD7PerformanceEntry 11}

pr1646v2ATMFwPerInPQsD7PerformanceSysUpTime OBJECT-TYPE
   SYNTAX      TimeTicks
   MAX-ACCESS  read-only
   STATUS      current
   DESCRIPTION
      "Path: atm.performance.pvcTable.inPriorityQueues.d7Performance.sysUpTime

       Time in centi-second."
   ::= {pr1646v2ATMFwPerInPQsD7PerformanceEntry 16777216}

pr1646v2ATMFwPerInPQsD7PerformanceTotPkts OBJECT-TYPE
   SYNTAX      Counter64
   MAX-ACCESS  read-only
   STATUS      current
   DESCRIPTION
      "Path: atm.performance.pvcTable.inPriorityQueues.d7Performance.totalPkts

       64 bit unsigned wrappable counter."
   ::= {pr1646v2ATMFwPerInPQsD7PerformanceEntry 234881024}

pr1646v2ATMFwPerInPQsD7PerformanceDirTxPkts OBJECT-TYPE
   SYNTAX      Counter64
   MAX-ACCESS  read-only
   STATUS      current
   DESCRIPTION
      "Path: atm.performance.pvcTable.inPriorityQueues.d7Performance.directTxPkts

       64 bit unsigned wrappable counter."
   ::= {pr1646v2ATMFwPerInPQsD7PerformanceEntry 33554432}

pr1646v2ATMFwPerInPQsD7PerformanceQdPkts OBJECT-TYPE
   SYNTAX      Counter64
   MAX-ACCESS  read-only
   STATUS      current
   DESCRIPTION
      "Path: atm.performance.pvcTable.inPriorityQueues.d7Performance.queuedPkts

       64 bit unsigned wrappable counter."
   ::= {pr1646v2ATMFwPerInPQsD7PerformanceEntry 50331648}

pr1646v2ATMFwPerInPQsD7PerformanceDropPkts OBJECT-TYPE
   SYNTAX      Counter64
   MAX-ACCESS  read-only
   STATUS      current
   DESCRIPTION
      "Path: atm.performance.pvcTable.inPriorityQueues.d7Performance.droppedPkts

       64 bit unsigned wrappable counter."
   ::= {pr1646v2ATMFwPerInPQsD7PerformanceEntry 67108864}

pr1646v2ATMFwPerInPQsD7PerformanceRDropPkts OBJECT-TYPE
   SYNTAX      Counter64
   MAX-ACCESS  read-only
   STATUS      current
   DESCRIPTION
      "Path: atm.performance.pvcTable.inPriorityQueues.d7Performance.redDroppedPkts

       64 bit unsigned wrappable counter."
   ::= {pr1646v2ATMFwPerInPQsD7PerformanceEntry 201326592}

pr1646v2ATMFwPerInPQsD7PerformanceCirTxPkts OBJECT-TYPE
   SYNTAX      Counter64
   MAX-ACCESS  read-only
   STATUS      current
   DESCRIPTION
      "Path: atm.performance.pvcTable.inPriorityQueues.d7Performance.cirTxPkts

       64 bit unsigned wrappable counter."
   ::= {pr1646v2ATMFwPerInPQsD7PerformanceEntry 83886080}

pr1646v2ATMFwPerInPQsD7PerformanceEirTxPkts OBJECT-TYPE
   SYNTAX      Counter64
   MAX-ACCESS  read-only
   STATUS      current
   DESCRIPTION
      "Path: atm.performance.pvcTable.inPriorityQueues.d7Performance.eirTxPkts

       64 bit unsigned wrappable counter."
   ::= {pr1646v2ATMFwPerInPQsD7PerformanceEntry 100663296}

pr1646v2ATMFwPerInPQsD7PerformanceViolTxPkts OBJECT-TYPE
   SYNTAX      Counter64
   MAX-ACCESS  read-only
   STATUS      current
   DESCRIPTION
      "Path: atm.performance.pvcTable.inPriorityQueues.d7Performance.violateTxPkts

       64 bit unsigned wrappable counter."
   ::= {pr1646v2ATMFwPerInPQsD7PerformanceEntry 301989888}

pr1646v2ATMFwPerInPQsD7PerformanceTotOcts OBJECT-TYPE
   SYNTAX      Counter64
   MAX-ACCESS  read-only
   STATUS      current
   DESCRIPTION
      "Path: atm.performance.pvcTable.inPriorityQueues.d7Performance.totalOctets

       64 bit unsigned wrappable counter."
   ::= {pr1646v2ATMFwPerInPQsD7PerformanceEntry 251658240}

pr1646v2ATMFwPerInPQsD7PerformanceDirTxOcts OBJECT-TYPE
   SYNTAX      Counter64
   MAX-ACCESS  read-only
   STATUS      current
   DESCRIPTION
      "Path: atm.performance.pvcTable.inPriorityQueues.d7Performance.directTxOctets

       64 bit unsigned wrappable counter."
   ::= {pr1646v2ATMFwPerInPQsD7PerformanceEntry 117440512}

pr1646v2ATMFwPerInPQsD7PerformanceQdOcts OBJECT-TYPE
   SYNTAX      Counter64
   MAX-ACCESS  read-only
   STATUS      current
   DESCRIPTION
      "Path: atm.performance.pvcTable.inPriorityQueues.d7Performance.queuedOctets

       64 bit unsigned wrappable counter."
   ::= {pr1646v2ATMFwPerInPQsD7PerformanceEntry 134217728}

pr1646v2ATMFwPerInPQsD7PerformanceDropOcts OBJECT-TYPE
   SYNTAX      Counter64
   MAX-ACCESS  read-only
   STATUS      current
   DESCRIPTION
      "Path: atm.performance.pvcTable.inPriorityQueues.d7Performance.droppedOctets

       64 bit unsigned wrappable counter."
   ::= {pr1646v2ATMFwPerInPQsD7PerformanceEntry 150994944}

pr1646v2ATMFwPerInPQsD7PerformanceRDropOcts OBJECT-TYPE
   SYNTAX      Counter64
   MAX-ACCESS  read-only
   STATUS      current
   DESCRIPTION
      "Path: atm.performance.pvcTable.inPriorityQueues.d7Performance.redDroppedOctets

       64 bit unsigned wrappable counter."
   ::= {pr1646v2ATMFwPerInPQsD7PerformanceEntry 218103808}

pr1646v2ATMFwPerInPQsD7PerformanceCirTxOcts OBJECT-TYPE
   SYNTAX      Counter64
   MAX-ACCESS  read-only
   STATUS      current
   DESCRIPTION
      "Path: atm.performance.pvcTable.inPriorityQueues.d7Performance.cirTxOctets

       64 bit unsigned wrappable counter."
   ::= {pr1646v2ATMFwPerInPQsD7PerformanceEntry 167772160}

pr1646v2ATMFwPerInPQsD7PerformanceEirTxOcts OBJECT-TYPE
   SYNTAX      Counter64
   MAX-ACCESS  read-only
   STATUS      current
   DESCRIPTION
      "Path: atm.performance.pvcTable.inPriorityQueues.d7Performance.eirTxOctets

       64 bit unsigned wrappable counter."
   ::= {pr1646v2ATMFwPerInPQsD7PerformanceEntry 184549376}

pr1646v2ATMFwPerInPQsD7PerformanceViolTxOcts OBJECT-TYPE
   SYNTAX      Counter64
   MAX-ACCESS  read-only
   STATUS      current
   DESCRIPTION
      "Path: atm.performance.pvcTable.inPriorityQueues.d7Performance.violateTxOctets

       64 bit unsigned wrappable counter."
   ::= {pr1646v2ATMFwPerInPQsD7PerformanceEntry 318767104}

pr1646v2ATMFwPerInPQsD7PerformanceBandwidth OBJECT-TYPE
   SYNTAX      Integer32
   MAX-ACCESS  read-only
   STATUS      current
   DESCRIPTION
      "Path: atm.performance.pvcTable.inPriorityQueues.d7Performance.bandwidth

       unit name = bps
       formula = 8 * ; 8 /"
   ::= {pr1646v2ATMFwPerInPQsD7PerformanceEntry 268435456}

pr1646v2ATMFwPerOutPQs OBJECT-TYPE
   SYNTAX      SEQUENCE OF Pr1646v2ATMFwPerOutPQsEntry
   MAX-ACCESS  not-accessible
   STATUS      current
   DESCRIPTION
      ""
   ::= {pr1646v2ATMFwPer 83886080}

pr1646v2ATMFwPerOutPQsEntry OBJECT-TYPE
   SYNTAX      Pr1646v2ATMFwPerOutPQsEntry
   MAX-ACCESS  not-accessible
   STATUS      current
   DESCRIPTION
      ""
   INDEX      { pr1646v2ATMFwPerOutPQsGlobalIx,
                pr1646v2ATMFwPerTableIx,
                pr1646v2ATMFwPerOutPQsTableIx }
   ::= {pr1646v2ATMFwPerOutPQs 1}

Pr1646v2ATMFwPerOutPQsEntry ::=
   SEQUENCE
      {
      pr1646v2ATMFwPerOutPQsGlobalIx
         GlobalIndex,
      pr1646v2ATMFwPerOutPQsTableIx
         TableIndex,
      pr1646v2ATMFwPerOutPQsName
         INTEGER,
      pr1646v2ATMFwPerOutPQsLength
         Integer32,
      pr1646v2ATMFwPerOutPQsOctetLength
         Integer32,
      pr1646v2ATMFwPerOutPQsRedLength
         Integer32,
      pr1646v2ATMFwPerOutPQsPacketsTotal
         Counter64,
      pr1646v2ATMFwPerOutPQsPacketsDirectTx
         Counter64,
      pr1646v2ATMFwPerOutPQsPacketsQueued
         Counter64,
      pr1646v2ATMFwPerOutPQsPacketsDropped
         Counter64,
      pr1646v2ATMFwPerOutPQsPacketsRedDropped
         Counter64,
      pr1646v2ATMFwPerOutPQsPacketsCirTx
         Counter64,
      pr1646v2ATMFwPerOutPQsPacketsEirTx
         Counter64,
      pr1646v2ATMFwPerOutPQsPacketsViolateTx
         Counter64,
      pr1646v2ATMFwPerOutPQsOctetsTotal
         Counter64,
      pr1646v2ATMFwPerOutPQsOctetsDirectTx
         Counter64,
      pr1646v2ATMFwPerOutPQsOctetsQueued
         Counter64,
      pr1646v2ATMFwPerOutPQsOctetsDropped
         Counter64,
      pr1646v2ATMFwPerOutPQsOctetsRedDropped
         Counter64,
      pr1646v2ATMFwPerOutPQsOctetsCirTx
         Counter64,
      pr1646v2ATMFwPerOutPQsOctetsEirTx
         Counter64,
      pr1646v2ATMFwPerOutPQsOctetsViolateTx
         Counter64,
      pr1646v2ATMFwPerOutPQsOctetsBandwidth15sec
         Integer32,
      pr1646v2ATMFwPerOutPQsOctetsBandwidth30sec
         Integer32,
      pr1646v2ATMFwPerOutPQsOctetsBandwidth1min
         Integer32,
      pr1646v2ATMFwPerOutPQsOctetsBandwidth2min
         Integer32,
      pr1646v2ATMFwPerOutPQsOctetsBandwidth5min
         Integer32
      }

pr1646v2ATMFwPerOutPQsGlobalIx OBJECT-TYPE
   SYNTAX      GlobalIndex
   MAX-ACCESS  not-accessible
   STATUS      current
   DESCRIPTION
      "The value of the tlsCntTreeGlobalIndex of the MANAGED OBJECT."
   ::= {pr1646v2ATMFwPerOutPQsEntry 10}

pr1646v2ATMFwPerOutPQsTableIx OBJECT-TYPE
   SYNTAX      TableIndex
   MAX-ACCESS  not-accessible
   STATUS      current
   DESCRIPTION
      ""
   ::= {pr1646v2ATMFwPerOutPQsEntry 11}

pr1646v2ATMFwPerOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2ATMFwPerOutPQsEntry 16777216}

pr1646v2ATMFwPerOutPQsLength OBJECT-TYPE
   SYNTAX      Integer32
   MAX-ACCESS  read-only
   STATUS      current
   DESCRIPTION
      "Path: atm.performance.pvcTable.outPriorityQueues.length"
   ::= {pr1646v2ATMFwPerOutPQsEntry 33554432}

pr1646v2ATMFwPerOutPQsOctetLength OBJECT-TYPE
   SYNTAX      Integer32
   MAX-ACCESS  read-only
   STATUS      current
   DESCRIPTION
      "Path: atm.performance.pvcTable.outPriorityQueues.octetLength"
   ::= {pr1646v2ATMFwPerOutPQsEntry 150994944}

pr1646v2ATMFwPerOutPQsRedLength OBJECT-TYPE
   SYNTAX      Integer32
   MAX-ACCESS  read-only
   STATUS      current
   DESCRIPTION
      "Path: atm.performance.pvcTable.outPriorityQueues.redLength"
   ::= {pr1646v2ATMFwPerOutPQsEntry 134217728}

pr1646v2ATMFwPerOutPQsPacketsTotal OBJECT-TYPE
   SYNTAX      Counter64
   MAX-ACCESS  read-only
   STATUS      current
   DESCRIPTION
      "Path: atm.performance.pvcTable.outPriorityQueues.packets.total

       64 bit unsigned wrappable counter."
   ::= {pr1646v2ATMFwPerOutPQsEntry 50790400}

pr1646v2ATMFwPerOutPQsPacketsDirectTx OBJECT-TYPE
   SYNTAX      Counter64
   MAX-ACCESS  read-only
   STATUS      current
   DESCRIPTION
      "Path: atm.performance.pvcTable.outPriorityQueues.packets.directTx

       64 bit unsigned wrappable counter."
   ::= {pr1646v2ATMFwPerOutPQsEntry 50397184}

pr1646v2ATMFwPerOutPQsPacketsQueued OBJECT-TYPE
   SYNTAX      Counter64
   MAX-ACCESS  read-only
   STATUS      current
   DESCRIPTION
      "Path: atm.performance.pvcTable.outPriorityQueues.packets.queued

       64 bit unsigned wrappable counter."
   ::= {pr1646v2ATMFwPerOutPQsEntry 50462720}

pr1646v2ATMFwPerOutPQsPacketsDropped OBJECT-TYPE
   SYNTAX      Counter64
   MAX-ACCESS  read-only
   STATUS      current
   DESCRIPTION
      "Path: atm.performance.pvcTable.outPriorityQueues.packets.dropped

       64 bit unsigned wrappable counter."
   ::= {pr1646v2ATMFwPerOutPQsEntry 50528256}

pr1646v2ATMFwPerOutPQsPacketsRedDropped OBJECT-TYPE
   SYNTAX      Counter64
   MAX-ACCESS  read-only
   STATUS      current
   DESCRIPTION
      "Path: atm.performance.pvcTable.outPriorityQueues.packets.redDropped

       64 bit unsigned wrappable counter."
   ::= {pr1646v2ATMFwPerOutPQsEntry 50724864}

pr1646v2ATMFwPerOutPQsPacketsCirTx OBJECT-TYPE
   SYNTAX      Counter64
   MAX-ACCESS  read-only
   STATUS      current
   DESCRIPTION
      "Path: atm.performance.pvcTable.outPriorityQueues.packets.cirTx

       64 bit unsigned wrappable counter."
   ::= {pr1646v2ATMFwPerOutPQsEntry 50593792}

pr1646v2ATMFwPerOutPQsPacketsEirTx OBJECT-TYPE
   SYNTAX      Counter64
   MAX-ACCESS  read-only
   STATUS      current
   DESCRIPTION
      "Path: atm.performance.pvcTable.outPriorityQueues.packets.eirTx

       64 bit unsigned wrappable counter."
   ::= {pr1646v2ATMFwPerOutPQsEntry 50659328}

pr1646v2ATMFwPerOutPQsPacketsViolateTx OBJECT-TYPE
   SYNTAX      Counter64
   MAX-ACCESS  read-only
   STATUS      current
   DESCRIPTION
      "Path: atm.performance.pvcTable.outPriorityQueues.packets.violateTx

       64 bit unsigned wrappable counter."
   ::= {pr1646v2ATMFwPerOutPQsEntry 50855936}

pr1646v2ATMFwPerOutPQsOctetsTotal OBJECT-TYPE
   SYNTAX      Counter64
   MAX-ACCESS  read-only
   STATUS      current
   DESCRIPTION
      "Path: atm.performance.pvcTable.outPriorityQueues.octets.total

       64 bit unsigned wrappable counter."
   ::= {pr1646v2ATMFwPerOutPQsEntry 67567616}

pr1646v2ATMFwPerOutPQsOctetsDirectTx OBJECT-TYPE
   SYNTAX      Counter64
   MAX-ACCESS  read-only
   STATUS      current
   DESCRIPTION
      "Path: atm.performance.pvcTable.outPriorityQueues.octets.directTx

       64 bit unsigned wrappable counter."
   ::= {pr1646v2ATMFwPerOutPQsEntry 67174400}

pr1646v2ATMFwPerOutPQsOctetsQueued OBJECT-TYPE
   SYNTAX      Counter64
   MAX-ACCESS  read-only
   STATUS      current
   DESCRIPTION
      "Path: atm.performance.pvcTable.outPriorityQueues.octets.queued

       64 bit unsigned wrappable counter."
   ::= {pr1646v2ATMFwPerOutPQsEntry 67239936}

pr1646v2ATMFwPerOutPQsOctetsDropped OBJECT-TYPE
   SYNTAX      Counter64
   MAX-ACCESS  read-only
   STATUS      current
   DESCRIPTION
      "Path: atm.performance.pvcTable.outPriorityQueues.octets.dropped

       64 bit unsigned wrappable counter."
   ::= {pr1646v2ATMFwPerOutPQsEntry 67305472}

pr1646v2ATMFwPerOutPQsOctetsRedDropped OBJECT-TYPE
   SYNTAX      Counter64
   MAX-ACCESS  read-only
   STATUS      current
   DESCRIPTION
      "Path: atm.performance.pvcTable.outPriorityQueues.octets.redDropped

       64 bit unsigned wrappable counter."
   ::= {pr1646v2ATMFwPerOutPQsEntry 67502080}

pr1646v2ATMFwPerOutPQsOctetsCirTx OBJECT-TYPE
   SYNTAX      Counter64
   MAX-ACCESS  read-only
   STATUS      current
   DESCRIPTION
      "Path: atm.performance.pvcTable.outPriorityQueues.octets.cirTx

       64 bit unsigned wrappable counter."
   ::= {pr1646v2ATMFwPerOutPQsEntry 67371008}

pr1646v2ATMFwPerOutPQsOctetsEirTx OBJECT-TYPE
   SYNTAX      Counter64
   MAX-ACCESS  read-only
   STATUS      current
   DESCRIPTION
      "Path: atm.performance.pvcTable.outPriorityQueues.octets.eirTx

       64 bit unsigned wrappable counter."
   ::= {pr1646v2ATMFwPerOutPQsEntry 67436544}

pr1646v2ATMFwPerOutPQsOctetsViolateTx OBJECT-TYPE
   SYNTAX      Counter64
   MAX-ACCESS  read-only
   STATUS      current
   DESCRIPTION
      "Path: atm.performance.pvcTable.outPriorityQueues.octets.violateTx

       64 bit unsigned wrappable counter."
   ::= {pr1646v2ATMFwPerOutPQsEntry 67633152}

pr1646v2ATMFwPerOutPQsOctetsBandwidth15sec OBJECT-TYPE
   SYNTAX      Integer32
   MAX-ACCESS  read-only
   STATUS      current
   DESCRIPTION
      "Path: atm.performance.pvcTable.outPriorityQueues.octets.bandwidth.15sec

       unit name = bps
       formula = 8 * ; 8 /"
   ::= {pr1646v2ATMFwPerOutPQsEntry 70386944}

pr1646v2ATMFwPerOutPQsOctetsBandwidth30sec OBJECT-TYPE
   SYNTAX      Integer32
   MAX-ACCESS  read-only
   STATUS      current
   DESCRIPTION
      "Path: atm.performance.pvcTable.outPriorityQueues.octets.bandwidth.30sec

       unit name = bps
       formula = 8 * ; 8 /"
   ::= {pr1646v2ATMFwPerOutPQsEntry 70388224}

pr1646v2ATMFwPerOutPQsOctetsBandwidth1min OBJECT-TYPE
   SYNTAX      Integer32
   MAX-ACCESS  read-only
   STATUS      current
   DESCRIPTION
      "Path: atm.performance.pvcTable.outPriorityQueues.octets.bandwidth.1min

       unit name = bps
       formula = 8 * ; 8 /"
   ::= {pr1646v2ATMFwPerOutPQsEntry 70390784}

pr1646v2ATMFwPerOutPQsOctetsBandwidth2min OBJECT-TYPE
   SYNTAX      Integer32
   MAX-ACCESS  read-only
   STATUS      current
   DESCRIPTION
      "Path: atm.performance.pvcTable.outPriorityQueues.octets.bandwidth.2min

       unit name = bps
       formula = 8 * ; 8 /"
   ::= {pr1646v2ATMFwPerOutPQsEntry 70395904}

pr1646v2ATMFwPerOutPQsOctetsBandwidth5min OBJECT-TYPE
   SYNTAX      Integer32
   MAX-ACCESS  read-only
   STATUS      current
   DESCRIPTION
      "Path: atm.performance.pvcTable.outPriorityQueues.octets.bandwidth.5min

       unit name = bps
       formula = 8 * ; 8 /"
   ::= {pr1646v2ATMFwPerOutPQsEntry 70411264}

pr1646v2ATMFwPerOutPQsH2Performance OBJECT-TYPE
   SYNTAX      SEQUENCE OF Pr1646v2ATMFwPerOutPQsH2PerformanceEntry
   MAX-ACCESS  not-accessible
   STATUS      current
   DESCRIPTION
      ""
   ::= {pr1646v2ATMFwPer 84213760}

pr1646v2ATMFwPerOutPQsH2PerformanceEntry OBJECT-TYPE
   SYNTAX      Pr1646v2ATMFwPerOutPQsH2PerformanceEntry
   MAX-ACCESS  not-accessible
   STATUS      current
   DESCRIPTION
      ""
   INDEX      { pr1646v2ATMFwPerOutPQsH2PerformanceGlobalIx,
                pr1646v2ATMFwPerTableIx,
                pr1646v2ATMFwPerOutPQsTableIx,
                pr1646v2ATMFwPerOutPQsH2PerformanceTableIx }
   ::= {pr1646v2ATMFwPerOutPQsH2Performance 1}

Pr1646v2ATMFwPerOutPQsH2PerformanceEntry ::=
   SEQUENCE
      {
      pr1646v2ATMFwPerOutPQsH2PerformanceGlobalIx
         GlobalIndex,
      pr1646v2ATMFwPerOutPQsH2PerformanceTableIx
         TableIndex,
      pr1646v2ATMFwPerOutPQsH2PerformanceSysUpTime
         TimeTicks,
      pr1646v2ATMFwPerOutPQsH2PerformanceTotPkts
         Counter64,
      pr1646v2ATMFwPerOutPQsH2PerformanceDirTxPkts
         Counter64,
      pr1646v2ATMFwPerOutPQsH2PerformanceQdPkts
         Counter64,
      pr1646v2ATMFwPerOutPQsH2PerformanceDropPkts
         Counter64,
      pr1646v2ATMFwPerOutPQsH2PerformanceRDropPkts
         Counter64,
      pr1646v2ATMFwPerOutPQsH2PerformanceCirTxPkts
         Counter64,
      pr1646v2ATMFwPerOutPQsH2PerformanceEirTxPkts
         Counter64,
      pr1646v2ATMFwPerOutPQsH2PerformanceViolTxPkts
         Counter64,
      pr1646v2ATMFwPerOutPQsH2PerformanceTotOcts
         Counter64,
      pr1646v2ATMFwPerOutPQsH2PerformanceDirTxOcts
         Counter64,
      pr1646v2ATMFwPerOutPQsH2PerformanceQdOcts
         Counter64,
      pr1646v2ATMFwPerOutPQsH2PerformanceDropOcts
         Counter64,
      pr1646v2ATMFwPerOutPQsH2PerformanceRDropOcts
         Counter64,
      pr1646v2ATMFwPerOutPQsH2PerformanceCirTxOcts
         Counter64,
      pr1646v2ATMFwPerOutPQsH2PerformanceEirTxOcts
         Counter64,
      pr1646v2ATMFwPerOutPQsH2PerformanceViolTxOcts
         Counter64,
      pr1646v2ATMFwPerOutPQsH2PerformanceBandwidth
         Integer32
      }

pr1646v2ATMFwPerOutPQsH2PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerOutPQsH2PerformanceEntry 10}

pr1646v2ATMFwPerOutPQsH2PerformanceTableIx OBJECT-TYPE
   SYNTAX      TableIndex
   MAX-ACCESS  not-accessible
   STATUS      current
   DESCRIPTION
      ""
   ::= {pr1646v2ATMFwPerOutPQsH2PerformanceEntry 11}

pr1646v2ATMFwPerOutPQsH2PerformanceSysUpTime OBJECT-TYPE
   SYNTAX      TimeTicks
   MAX-ACCESS  read-only
   STATUS      current
   DESCRIPTION
      "Path: atm.performance.pvcTable.outPriorityQueues.h2Performance.sysUpTime

       Time in centi-second."
   ::= {pr1646v2ATMFwPerOutPQsH2PerformanceEntry 16777216}

pr1646v2ATMFwPerOutPQsH2PerformanceTotPkts OBJECT-TYPE
   SYNTAX      Counter64
   MAX-ACCESS  read-only
   STATUS      current
   DESCRIPTION
      "Path: atm.performance.pvcTable.outPriorityQueues.h2Performance.totalPkts

       64 bit unsigned wrappable counter."
   ::= {pr1646v2ATMFwPerOutPQsH2PerformanceEntry 234881024}

pr1646v2ATMFwPerOutPQsH2PerformanceDirTxPkts OBJECT-TYPE
   SYNTAX      Counter64
   MAX-ACCESS  read-only
   STATUS      current
   DESCRIPTION
      "Path: atm.performance.pvcTable.outPriorityQueues.h2Performance.directTxPkts

       64 bit unsigned wrappable counter."
   ::= {pr1646v2ATMFwPerOutPQsH2PerformanceEntry 33554432}

pr1646v2ATMFwPerOutPQsH2PerformanceQdPkts OBJECT-TYPE
   SYNTAX      Counter64
   MAX-ACCESS  read-only
   STATUS      current
   DESCRIPTION
      "Path: atm.performance.pvcTable.outPriorityQueues.h2Performance.queuedPkts

       64 bit unsigned wrappable counter."
   ::= {pr1646v2ATMFwPerOutPQsH2PerformanceEntry 50331648}

pr1646v2ATMFwPerOutPQsH2PerformanceDropPkts OBJECT-TYPE
   SYNTAX      Counter64
   MAX-ACCESS  read-only
   STATUS      current
   DESCRIPTION
      "Path: atm.performance.pvcTable.outPriorityQueues.h2Performance.droppedPkts

       64 bit unsigned wrappable counter."
   ::= {pr1646v2ATMFwPerOutPQsH2PerformanceEntry 67108864}

pr1646v2ATMFwPerOutPQsH2PerformanceRDropPkts OBJECT-TYPE
   SYNTAX      Counter64
   MAX-ACCESS  read-only
   STATUS      current
   DESCRIPTION
      "Path: atm.performance.pvcTable.outPriorityQueues.h2Performance.redDroppedPkts

       64 bit unsigned wrappable counter."
   ::= {pr1646v2ATMFwPerOutPQsH2PerformanceEntry 201326592}

pr1646v2ATMFwPerOutPQsH2PerformanceCirTxPkts OBJECT-TYPE
   SYNTAX      Counter64
   MAX-ACCESS  read-only
   STATUS      current
   DESCRIPTION
      "Path: atm.performance.pvcTable.outPriorityQueues.h2Performance.cirTxPkts

       64 bit unsigned wrappable counter."
   ::= {pr1646v2ATMFwPerOutPQsH2PerformanceEntry 83886080}

pr1646v2ATMFwPerOutPQsH2PerformanceEirTxPkts OBJECT-TYPE
   SYNTAX      Counter64
   MAX-ACCESS  read-only
   STATUS      current
   DESCRIPTION
      "Path: atm.performance.pvcTable.outPriorityQueues.h2Performance.eirTxPkts

       64 bit unsigned wrappable counter."
   ::= {pr1646v2ATMFwPerOutPQsH2PerformanceEntry 100663296}

pr1646v2ATMFwPerOutPQsH2PerformanceViolTxPkts OBJECT-TYPE
   SYNTAX      Counter64
   MAX-ACCESS  read-only
   STATUS      current
   DESCRIPTION
      "Path: atm.performance.pvcTable.outPriorityQueues.h2Performance.violateTxPkts

       64 bit unsigned wrappable counter."
   ::= {pr1646v2ATMFwPerOutPQsH2PerformanceEntry 301989888}

pr1646v2ATMFwPerOutPQsH2PerformanceTotOcts OBJECT-TYPE
   SYNTAX      Counter64
   MAX-ACCESS  read-only
   STATUS      current
   DESCRIPTION
      "Path: atm.performance.pvcTable.outPriorityQueues.h2Performance.totalOctets

       64 bit unsigned wrappable counter."
   ::= {pr1646v2ATMFwPerOutPQsH2PerformanceEntry 251658240}

pr1646v2ATMFwPerOutPQsH2PerformanceDirTxOcts OBJECT-TYPE
   SYNTAX      Counter64
   MAX-ACCESS  read-only
   STATUS      current
   DESCRIPTION
      "Path: atm.performance.pvcTable.outPriorityQueues.h2Performance.directTxOctets

       64 bit unsigned wrappable counter."
   ::= {pr1646v2ATMFwPerOutPQsH2PerformanceEntry 117440512}

pr1646v2ATMFwPerOutPQsH2PerformanceQdOcts OBJECT-TYPE
   SYNTAX      Counter64
   MAX-ACCESS  read-only
   STATUS      current
   DESCRIPTION
      "Path: atm.performance.pvcTable.outPriorityQueues.h2Performance.queuedOctets

       64 bit unsigned wrappable counter."
   ::= {pr1646v2ATMFwPerOutPQsH2PerformanceEntry 134217728}

pr1646v2ATMFwPerOutPQsH2PerformanceDropOcts OBJECT-TYPE
   SYNTAX      Counter64
   MAX-ACCESS  read-only
   STATUS      current
   DESCRIPTION
      "Path: atm.performance.pvcTable.outPriorityQueues.h2Performance.droppedOctets

       64 bit unsigned wrappable counter."
   ::= {pr1646v2ATMFwPerOutPQsH2PerformanceEntry 150994944}

pr1646v2ATMFwPerOutPQsH2PerformanceRDropOcts OBJECT-TYPE
   SYNTAX      Counter64
   MAX-ACCESS  read-only
   STATUS      current
   DESCRIPTION
      "Path: atm.performance.pvcTable.outPriorityQueues.h2Performance.redDroppedOctets

       64 bit unsigned wrappable counter."
   ::= {pr1646v2ATMFwPerOutPQsH2PerformanceEntry 218103808}

pr1646v2ATMFwPerOutPQsH2PerformanceCirTxOcts OBJECT-TYPE
   SYNTAX      Counter64
   MAX-ACCESS  read-only
   STATUS      current
   DESCRIPTION
      "Path: atm.performance.pvcTable.outPriorityQueues.h2Performance.cirTxOctets

       64 bit unsigned wrappable counter."
   ::= {pr1646v2ATMFwPerOutPQsH2PerformanceEntry 167772160}

pr1646v2ATMFwPerOutPQsH2PerformanceEirTxOcts OBJECT-TYPE
   SYNTAX      Counter64
   MAX-ACCESS  read-only
   STATUS      current
   DESCRIPTION
      "Path: atm.performance.pvcTable.outPriorityQueues.h2Performance.eirTxOctets

       64 bit unsigned wrappable counter."
   ::= {pr1646v2ATMFwPerOutPQsH2PerformanceEntry 184549376}

pr1646v2ATMFwPerOutPQsH2PerformanceViolTxOcts OBJECT-TYPE
   SYNTAX      Counter64
   MAX-ACCESS  read-only
   STATUS      current
   DESCRIPTION
      "Path: atm.performance.pvcTable.outPriorityQueues.h2Performance.violateTxOctets

       64 bit unsigned wrappable counter."
   ::= {pr1646v2ATMFwPerOutPQsH2PerformanceEntry 318767104}

pr1646v2ATMFwPerOutPQsH2PerformanceBandwidth OBJECT-TYPE
   SYNTAX      Integer32
   MAX-ACCESS  read-only
   STATUS      current
   DESCRIPTION
      "Path: atm.performance.pvcTable.outPriorityQueues.h2Performance.bandwidth

       unit name = bps
       formula = 8 * ; 8 /"
   ::= {pr1646v2ATMFwPerOutPQsH2PerformanceEntry 268435456}

pr1646v2ATMFwPerOutPQsH24Performance OBJECT-TYPE
   SYNTAX      SEQUENCE OF Pr1646v2ATMFwPerOutPQsH24PerformanceEntry
   MAX-ACCESS  not-accessible
   STATUS      current
   DESCRIPTION
      ""
   ::= {pr1646v2ATMFwPer 84279296}

pr1646v2ATMFwPerOutPQsH24PerformanceEntry OBJECT-TYPE
   SYNTAX      Pr1646v2ATMFwPerOutPQsH24PerformanceEntry
   MAX-ACCESS  not-accessible
   STATUS      current
   DESCRIPTION
      ""
   INDEX      { pr1646v2ATMFwPerOutPQsH24PerformanceGlobalIx,
                pr1646v2ATMFwPerTableIx,
                pr1646v2ATMFwPerOutPQsTableIx,
                pr1646v2ATMFwPerOutPQsH24PerformanceTableIx }
   ::= {pr1646v2ATMFwPerOutPQsH24Performance 1}

Pr1646v2ATMFwPerOutPQsH24PerformanceEntry ::=
   SEQUENCE
      {
      pr1646v2ATMFwPerOutPQsH24PerformanceGlobalIx
         GlobalIndex,
      pr1646v2ATMFwPerOutPQsH24PerformanceTableIx
         TableIndex,
      pr1646v2ATMFwPerOutPQsH24PerformanceSysUpTime
         TimeTicks,
      pr1646v2ATMFwPerOutPQsH24PerformanceTotPkts
         Counter64,
      pr1646v2ATMFwPerOutPQsH24PerformanceDirTxPkts
         Counter64,
      pr1646v2ATMFwPerOutPQsH24PerformanceQdPkts
         Counter64,
      pr1646v2ATMFwPerOutPQsH24PerformanceDropPkts
         Counter64,
      pr1646v2ATMFwPerOutPQsH24PerformanceRDropPkts
         Counter64,
      pr1646v2ATMFwPerOutPQsH24PerformanceCirTxPkts
         Counter64,
      pr1646v2ATMFwPerOutPQsH24PerformanceEirTxPkts
         Counter64,
      pr1646v2ATMFwPerOutPQsH24PerformanceViolTxPkts
         Counter64,
      pr1646v2ATMFwPerOutPQsH24PerformanceTotOcts
         Counter64,
      pr1646v2ATMFwPerOutPQsH24PerformanceDirTxOcts
         Counter64,
      pr1646v2ATMFwPerOutPQsH24PerformanceQdOcts
         Counter64,
      pr1646v2ATMFwPerOutPQsH24PerformanceDropOcts
         Counter64,
      pr1646v2ATMFwPerOutPQsH24PerformanceRDropOcts
         Counter64,
      pr1646v2ATMFwPerOutPQsH24PerformanceCirTxOcts
         Counter64,
      pr1646v2ATMFwPerOutPQsH24PerformanceEirTxOcts
         Counter64,
      pr1646v2ATMFwPerOutPQsH24PerformanceViolTxOcts
         Counter64,
      pr1646v2ATMFwPerOutPQsH24PerformanceBandwidth
         Integer32
      }

pr1646v2ATMFwPerOutPQsH24PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerOutPQsH24PerformanceEntry 10}

pr1646v2ATMFwPerOutPQsH24PerformanceTableIx OBJECT-TYPE
   SYNTAX      TableIndex
   MAX-ACCESS  not-accessible
   STATUS      current
   DESCRIPTION
      ""
   ::= {pr1646v2ATMFwPerOutPQsH24PerformanceEntry 11}

pr1646v2ATMFwPerOutPQsH24PerformanceSysUpTime OBJECT-TYPE
   SYNTAX      TimeTicks
   MAX-ACCESS  read-only
   STATUS      current
   DESCRIPTION
      "Path: atm.performance.pvcTable.outPriorityQueues.h24Performance.sysUpTime

       Time in centi-second."
   ::= {pr1646v2ATMFwPerOutPQsH24PerformanceEntry 16777216}

pr1646v2ATMFwPerOutPQsH24PerformanceTotPkts OBJECT-TYPE
   SYNTAX      Counter64
   MAX-ACCESS  read-only
   STATUS      current
   DESCRIPTION
      "Path: atm.performance.pvcTable.outPriorityQueues.h24Performance.totalPkts

       64 bit unsigned wrappable counter."
   ::= {pr1646v2ATMFwPerOutPQsH24PerformanceEntry 234881024}

pr1646v2ATMFwPerOutPQsH24PerformanceDirTxPkts OBJECT-TYPE
   SYNTAX      Counter64
   MAX-ACCESS  read-only
   STATUS      current
   DESCRIPTION
      "Path: atm.performance.pvcTable.outPriorityQueues.h24Performance.directTxPkts

       64 bit unsigned wrappable counter."
   ::= {pr1646v2ATMFwPerOutPQsH24PerformanceEntry 33554432}

pr1646v2ATMFwPerOutPQsH24PerformanceQdPkts OBJECT-TYPE
   SYNTAX      Counter64
   MAX-ACCESS  read-only
   STATUS      current
   DESCRIPTION
      "Path: atm.performance.pvcTable.outPriorityQueues.h24Performance.queuedPkts

       64 bit unsigned wrappable counter."
   ::= {pr1646v2ATMFwPerOutPQsH24PerformanceEntry 50331648}

pr1646v2ATMFwPerOutPQsH24PerformanceDropPkts OBJECT-TYPE
   SYNTAX      Counter64
   MAX-ACCESS  read-only
   STATUS      current
   DESCRIPTION
      "Path: atm.performance.pvcTable.outPriorityQueues.h24Performance.droppedPkts

       64 bit unsigned wrappable counter."
   ::= {pr1646v2ATMFwPerOutPQsH24PerformanceEntry 67108864}

pr1646v2ATMFwPerOutPQsH24PerformanceRDropPkts OBJECT-TYPE
   SYNTAX      Counter64
   MAX-ACCESS  read-only
   STATUS      current
   DESCRIPTION
      "Path: atm.performance.pvcTable.outPriorityQueues.h24Performance.redDroppedPkts

       64 bit unsigned wrappable counter."
   ::= {pr1646v2ATMFwPerOutPQsH24PerformanceEntry 201326592}

pr1646v2ATMFwPerOutPQsH24PerformanceCirTxPkts OBJECT-TYPE
   SYNTAX      Counter64
   MAX-ACCESS  read-only
   STATUS      current
   DESCRIPTION
      "Path: atm.performance.pvcTable.outPriorityQueues.h24Performance.cirTxPkts

       64 bit unsigned wrappable counter."
   ::= {pr1646v2ATMFwPerOutPQsH24PerformanceEntry 83886080}

pr1646v2ATMFwPerOutPQsH24PerformanceEirTxPkts OBJECT-TYPE
   SYNTAX      Counter64
   MAX-ACCESS  read-only
   STATUS      current
   DESCRIPTION
      "Path: atm.performance.pvcTable.outPriorityQueues.h24Performance.eirTxPkts

       64 bit unsigned wrappable counter."
   ::= {pr1646v2ATMFwPerOutPQsH24PerformanceEntry 100663296}

pr1646v2ATMFwPerOutPQsH24PerformanceViolTxPkts OBJECT-TYPE
   SYNTAX      Counter64
   MAX-ACCESS  read-only
   STATUS      current
   DESCRIPTION
      "Path: atm.performance.pvcTable.outPriorityQueues.h24Performance.violateTxPkts

       64 bit unsigned wrappable counter."
   ::= {pr1646v2ATMFwPerOutPQsH24PerformanceEntry 301989888}

pr1646v2ATMFwPerOutPQsH24PerformanceTotOcts OBJECT-TYPE
   SYNTAX      Counter64
   MAX-ACCESS  read-only
   STATUS      current
   DESCRIPTION
      "Path: atm.performance.pvcTable.outPriorityQueues.h24Performance.totalOctets

       64 bit unsigned wrappable counter."
   ::= {pr1646v2ATMFwPerOutPQsH24PerformanceEntry 251658240}

pr1646v2ATMFwPerOutPQsH24PerformanceDirTxOcts OBJECT-TYPE
   SYNTAX      Counter64
   MAX-ACCESS  read-only
   STATUS      current
   DESCRIPTION
      "Path: atm.performance.pvcTable.outPriorityQueues.h24Performance.directTxOctets

       64 bit unsigned wrappable counter."
   ::= {pr1646v2ATMFwPerOutPQsH24PerformanceEntry 117440512}

pr1646v2ATMFwPerOutPQsH24PerformanceQdOcts OBJECT-TYPE
   SYNTAX      Counter64
   MAX-ACCESS  read-only
   STATUS      current
   DESCRIPTION
      "Path: atm.performance.pvcTable.outPriorityQueues.h24Performance.queuedOctets

       64 bit unsigned wrappable counter."
   ::= {pr1646v2ATMFwPerOutPQsH24PerformanceEntry 134217728}

pr1646v2ATMFwPerOutPQsH24PerformanceDropOcts OBJECT-TYPE
   SYNTAX      Counter64
   MAX-ACCESS  read-only
   STATUS      current
   DESCRIPTION
      "Path: atm.performance.pvcTable.outPriorityQueues.h24Performance.droppedOctets

       64 bit unsigned wrappable counter."
   ::= {pr1646v2ATMFwPerOutPQsH24PerformanceEntry 150994944}

pr1646v2ATMFwPerOutPQsH24PerformanceRDropOcts OBJECT-TYPE
   SYNTAX      Counter64
   MAX-ACCESS  read-only
   STATUS      current
   DESCRIPTION
      "Path: atm.performance.pvcTable.outPriorityQueues.h24Performance.redDroppedOctets

       64 bit unsigned wrappable counter."
   ::= {pr1646v2ATMFwPerOutPQsH24PerformanceEntry 218103808}

pr1646v2ATMFwPerOutPQsH24PerformanceCirTxOcts OBJECT-TYPE
   SYNTAX      Counter64
   MAX-ACCESS  read-only
   STATUS      current
   DESCRIPTION
      "Path: atm.performance.pvcTable.outPriorityQueues.h24Performance.cirTxOctets

       64 bit unsigned wrappable counter."
   ::= {pr1646v2ATMFwPerOutPQsH24PerformanceEntry 167772160}

pr1646v2ATMFwPerOutPQsH24PerformanceEirTxOcts OBJECT-TYPE
   SYNTAX      Counter64
   MAX-ACCESS  read-only
   STATUS      current
   DESCRIPTION
      "Path: atm.performance.pvcTable.outPriorityQueues.h24Performance.eirTxOctets

       64 bit unsigned wrappable counter."
   ::= {pr1646v2ATMFwPerOutPQsH24PerformanceEntry 184549376}

pr1646v2ATMFwPerOutPQsH24PerformanceViolTxOcts OBJECT-TYPE
   SYNTAX      Counter64
   MAX-ACCESS  read-only
   STATUS      current
   DESCRIPTION
      "Path: atm.performance.pvcTable.outPriorityQueues.h24Performance.violateTxOctets

       64 bit unsigned wrappable counter."
   ::= {pr1646v2ATMFwPerOutPQsH24PerformanceEntry 318767104}

pr1646v2ATMFwPerOutPQsH24PerformanceBandwidth OBJECT-TYPE
   SYNTAX      Integer32
   MAX-ACCESS  read-only
   STATUS      current
   DESCRIPTION
      "Path: atm.performance.pvcTable.outPriorityQueues.h24Performance.bandwidth

       unit name = bps
       formula = 8 * ; 8 /"
   ::= {pr1646v2ATMFwPerOutPQsH24PerformanceEntry 268435456}

pr1646v2ATMFwPerOutPQsD7Performance OBJECT-TYPE
   SYNTAX      SEQUENCE OF Pr1646v2ATMFwPerOutPQsD7PerformanceEntry
   MAX-ACCESS  not-accessible
   STATUS      current
   DESCRIPTION
      ""
   ::= {pr1646v2ATMFwPer 84344832}

pr1646v2ATMFwPerOutPQsD7PerformanceEntry OBJECT-TYPE
   SYNTAX      Pr1646v2ATMFwPerOutPQsD7PerformanceEntry
   MAX-ACCESS  not-accessible
   STATUS      current
   DESCRIPTION
      ""
   INDEX      { pr1646v2ATMFwPerOutPQsD7PerformanceGlobalIx,
                pr1646v2ATMFwPerTableIx,
                pr1646v2ATMFwPerOutPQsTableIx,
                pr1646v2ATMFwPerOutPQsD7PerformanceTableIx }
   ::= {pr1646v2ATMFwPerOutPQsD7Performance 1}

Pr1646v2ATMFwPerOutPQsD7PerformanceEntry ::=
   SEQUENCE
      {
      pr1646v2ATMFwPerOutPQsD7PerformanceGlobalIx
         GlobalIndex,
      pr1646v2ATMFwPerOutPQsD7PerformanceTableIx
         TableIndex,
      pr1646v2ATMFwPerOutPQsD7PerformanceSysUpTime
         TimeTicks,
      pr1646v2ATMFwPerOutPQsD7PerformanceTotPkts
         Counter64,
      pr1646v2ATMFwPerOutPQsD7PerformanceDirTxPkts
         Counter64,
      pr1646v2ATMFwPerOutPQsD7PerformanceQdPkts
         Counter64,
      pr1646v2ATMFwPerOutPQsD7PerformanceDropPkts
         Counter64,
      pr1646v2ATMFwPerOutPQsD7PerformanceRDropPkts
         Counter64,
      pr1646v2ATMFwPerOutPQsD7PerformanceCirTxPkts
         Counter64,
      pr1646v2ATMFwPerOutPQsD7PerformanceEirTxPkts
         Counter64,
      pr1646v2ATMFwPerOutPQsD7PerformanceViolTxPkts
         Counter64,
      pr1646v2ATMFwPerOutPQsD7PerformanceTotOcts
         Counter64,
      pr1646v2ATMFwPerOutPQsD7PerformanceDirTxOcts
         Counter64,
      pr1646v2ATMFwPerOutPQsD7PerformanceQdOcts
         Counter64,
      pr1646v2ATMFwPerOutPQsD7PerformanceDropOcts
         Counter64,
      pr1646v2ATMFwPerOutPQsD7PerformanceRDropOcts
         Counter64,
      pr1646v2ATMFwPerOutPQsD7PerformanceCirTxOcts
         Counter64,
      pr1646v2ATMFwPerOutPQsD7PerformanceEirTxOcts
         Counter64,
      pr1646v2ATMFwPerOutPQsD7PerformanceViolTxOcts
         Counter64,
      pr1646v2ATMFwPerOutPQsD7PerformanceBandwidth
         Integer32
      }

pr1646v2ATMFwPerOutPQsD7PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerOutPQsD7PerformanceEntry 10}

pr1646v2ATMFwPerOutPQsD7PerformanceTableIx OBJECT-TYPE
   SYNTAX      TableIndex
   MAX-ACCESS  not-accessible
   STATUS      current
   DESCRIPTION
      ""
   ::= {pr1646v2ATMFwPerOutPQsD7PerformanceEntry 11}

pr1646v2ATMFwPerOutPQsD7PerformanceSysUpTime OBJECT-TYPE
   SYNTAX      TimeTicks
   MAX-ACCESS  read-only
   STATUS      current
   DESCRIPTION
      "Path: atm.performance.pvcTable.outPriorityQueues.d7Performance.sysUpTime

       Time in centi-second."
   ::= {pr1646v2ATMFwPerOutPQsD7PerformanceEntry 16777216}

pr1646v2ATMFwPerOutPQsD7PerformanceTotPkts OBJECT-TYPE
   SYNTAX      Counter64
   MAX-ACCESS  read-only
   STATUS      current
   DESCRIPTION
      "Path: atm.performance.pvcTable.outPriorityQueues.d7Performance.totalPkts

       64 bit unsigned wrappable counter."
   ::= {pr1646v2ATMFwPerOutPQsD7PerformanceEntry 234881024}

pr1646v2ATMFwPerOutPQsD7PerformanceDirTxPkts OBJECT-TYPE
   SYNTAX      Counter64
   MAX-ACCESS  read-only
   STATUS      current
   DESCRIPTION
      "Path: atm.performance.pvcTable.outPriorityQueues.d7Performance.directTxPkts

       64 bit unsigned wrappable counter."
   ::= {pr1646v2ATMFwPerOutPQsD7PerformanceEntry 33554432}

pr1646v2ATMFwPerOutPQsD7PerformanceQdPkts OBJECT-TYPE
   SYNTAX      Counter64
   MAX-ACCESS  read-only
   STATUS      current
   DESCRIPTION
      "Path: atm.performance.pvcTable.outPriorityQueues.d7Performance.queuedPkts

       64 bit unsigned wrappable counter."
   ::= {pr1646v2ATMFwPerOutPQsD7PerformanceEntry 50331648}

pr1646v2ATMFwPerOutPQsD7PerformanceDropPkts OBJECT-TYPE
   SYNTAX      Counter64
   MAX-ACCESS  read-only
   STATUS      current
   DESCRIPTION
      "Path: atm.performance.pvcTable.outPriorityQueues.d7Performance.droppedPkts

       64 bit unsigned wrappable counter."
   ::= {pr1646v2ATMFwPerOutPQsD7PerformanceEntry 67108864}

pr1646v2ATMFwPerOutPQsD7PerformanceRDropPkts OBJECT-TYPE
   SYNTAX      Counter64
   MAX-ACCESS  read-only
   STATUS      current
   DESCRIPTION
      "Path: atm.performance.pvcTable.outPriorityQueues.d7Performance.redDroppedPkts

       64 bit unsigned wrappable counter."
   ::= {pr1646v2ATMFwPerOutPQsD7PerformanceEntry 201326592}

pr1646v2ATMFwPerOutPQsD7PerformanceCirTxPkts OBJECT-TYPE
   SYNTAX      Counter64
   MAX-ACCESS  read-only
   STATUS      current
   DESCRIPTION
      "Path: atm.performance.pvcTable.outPriorityQueues.d7Performance.cirTxPkts

       64 bit unsigned wrappable counter."
   ::= {pr1646v2ATMFwPerOutPQsD7PerformanceEntry 83886080}

pr1646v2ATMFwPerOutPQsD7PerformanceEirTxPkts OBJECT-TYPE
   SYNTAX      Counter64
   MAX-ACCESS  read-only
   STATUS      current
   DESCRIPTION
      "Path: atm.performance.pvcTable.outPriorityQueues.d7Performance.eirTxPkts

       64 bit unsigned wrappable counter."
   ::= {pr1646v2ATMFwPerOutPQsD7PerformanceEntry 100663296}

pr1646v2ATMFwPerOutPQsD7PerformanceViolTxPkts OBJECT-TYPE
   SYNTAX      Counter64
   MAX-ACCESS  read-only
   STATUS      current
   DESCRIPTION
      "Path: atm.performance.pvcTable.outPriorityQueues.d7Performance.violateTxPkts

       64 bit unsigned wrappable counter."
   ::= {pr1646v2ATMFwPerOutPQsD7PerformanceEntry 301989888}

pr1646v2ATMFwPerOutPQsD7PerformanceTotOcts OBJECT-TYPE
   SYNTAX      Counter64
   MAX-ACCESS  read-only
   STATUS      current
   DESCRIPTION
      "Path: atm.performance.pvcTable.outPriorityQueues.d7Performance.totalOctets

       64 bit unsigned wrappable counter."
   ::= {pr1646v2ATMFwPerOutPQsD7PerformanceEntry 251658240}

pr1646v2ATMFwPerOutPQsD7PerformanceDirTxOcts OBJECT-TYPE
   SYNTAX      Counter64
   MAX-ACCESS  read-only
   STATUS      current
   DESCRIPTION
      "Path: atm.performance.pvcTable.outPriorityQueues.d7Performance.directTxOctets

       64 bit unsigned wrappable counter."
   ::= {pr1646v2ATMFwPerOutPQsD7PerformanceEntry 117440512}

pr1646v2ATMFwPerOutPQsD7PerformanceQdOcts OBJECT-TYPE
   SYNTAX      Counter64
   MAX-ACCESS  read-only
   STATUS      current
   DESCRIPTION
      "Path: atm.performance.pvcTable.outPriorityQueues.d7Performance.queuedOctets

       64 bit unsigned wrappable counter."
   ::= {pr1646v2ATMFwPerOutPQsD7PerformanceEntry 134217728}

pr1646v2ATMFwPerOutPQsD7PerformanceDropOcts OBJECT-TYPE
   SYNTAX      Counter64
   MAX-ACCESS  read-only
   STATUS      current
   DESCRIPTION
      "Path: atm.performance.pvcTable.outPriorityQueues.d7Performance.droppedOctets

       64 bit unsigned wrappable counter."
   ::= {pr1646v2ATMFwPerOutPQsD7PerformanceEntry 150994944}

pr1646v2ATMFwPerOutPQsD7PerformanceRDropOcts OBJECT-TYPE
   SYNTAX      Counter64
   MAX-ACCESS  read-only
   STATUS      current
   DESCRIPTION
      "Path: atm.performance.pvcTable.outPriorityQueues.d7Performance.redDroppedOctets

       64 bit unsigned wrappable counter."
   ::= {pr1646v2ATMFwPerOutPQsD7PerformanceEntry 218103808}

pr1646v2ATMFwPerOutPQsD7PerformanceCirTxOcts OBJECT-TYPE
   SYNTAX      Counter64
   MAX-ACCESS  read-only
   STATUS      current
   DESCRIPTION
      "Path: atm.performance.pvcTable.outPriorityQueues.d7Performance.cirTxOctets

       64 bit unsigned wrappable counter."
   ::= {pr1646v2ATMFwPerOutPQsD7PerformanceEntry 167772160}

pr1646v2ATMFwPerOutPQsD7PerformanceEirTxOcts OBJECT-TYPE
   SYNTAX      Counter64
   MAX-ACCESS  read-only
   STATUS      current
   DESCRIPTION
      "Path: atm.performance.pvcTable.outPriorityQueues.d7Performance.eirTxOctets

       64 bit unsigned wrappable counter."
   ::= {pr1646v2ATMFwPerOutPQsD7PerformanceEntry 184549376}

pr1646v2ATMFwPerOutPQsD7PerformanceViolTxOcts OBJECT-TYPE
   SYNTAX      Counter64
   MAX-ACCESS  read-only
   STATUS      current
   DESCRIPTION
      "Path: atm.performance.pvcTable.outPriorityQueues.d7Performance.violateTxOctets

       64 bit unsigned wrappable counter."
   ::= {pr1646v2ATMFwPerOutPQsD7PerformanceEntry 318767104}

pr1646v2ATMFwPerOutPQsD7PerformanceBandwidth OBJECT-TYPE
   SYNTAX      Integer32
   MAX-ACCESS  read-only
   STATUS      current
   DESCRIPTION
      "Path: atm.performance.pvcTable.outPriorityQueues.d7Performance.bandwidth

       unit name = bps
       formula = 8 * ; 8 /"
   ::= {pr1646v2ATMFwPerOutPQsD7PerformanceEntry 268435456}

pr1646v2ATMFwPerFrDlci OBJECT-TYPE
   SYNTAX      SEQUENCE OF Pr1646v2ATMFwPerFrDlciEntry
   MAX-ACCESS  not-accessible
   STATUS      current
   DESCRIPTION
      ""
   ::= {pr1646v2ATMFwPer 503447552}

pr1646v2ATMFwPerFrDlciEntry OBJECT-TYPE
   SYNTAX      Pr1646v2ATMFwPerFrDlciEntry
   MAX-ACCESS  not-accessible
   STATUS      current
   DESCRIPTION
      ""
   INDEX      { pr1646v2ATMFwPerFrDlciGlobalIx,
                pr1646v2ATMFwPerTableIx,
                pr1646v2ATMFwPerFrDlciTableIx }
   ::= {pr1646v2ATMFwPerFrDlci 1}

Pr1646v2ATMFwPerFrDlciEntry ::=
   SEQUENCE
      {
      pr1646v2ATMFwPerFrDlciGlobalIx
         GlobalIndex,
      pr1646v2ATMFwPerFrDlciTableIx
         TableIndex,
      pr1646v2ATMFwPerFrDlciName
         DisplayString,
      pr1646v2ATMFwPerFrDlciMCInOctets
         Counter64,
      pr1646v2ATMFwPerFrDlciMCInUcast
         Counter64,
      pr1646v2ATMFwPerFrDlciMCInNUcastPkts
         Counter64,
      pr1646v2ATMFwPerFrDlciMCInBcastPkts
         Counter64,
      pr1646v2ATMFwPerFrDlciMCInMcastPkts
         Counter64,
      pr1646v2ATMFwPerFrDlciMCInDiscards
         Counter64,
      pr1646v2ATMFwPerFrDlciMCInErrors
         Counter64,
      pr1646v2ATMFwPerFrDlciMCInUnknownProtos
         Counter64,
      pr1646v2ATMFwPerFrDlciMCInDropEx
         Counter64,
      pr1646v2ATMFwPerFrDlciMCInDropNoMac
         Counter64,
      pr1646v2ATMFwPerFrDlciMCInDropNUCast
         Counter64,
      pr1646v2ATMFwPerFrDlciMCInDropFilter
         Counter64,
      pr1646v2ATMFwPerFrDlciMCInBandwidth15sec
         Integer32,
      pr1646v2ATMFwPerFrDlciMCInBandwidth30sec
         Integer32,
      pr1646v2ATMFwPerFrDlciMCInBandwidth1min
         Integer32,
      pr1646v2ATMFwPerFrDlciMCInBandwidth2min
         Integer32,
      pr1646v2ATMFwPerFrDlciMCInBandwidth5min
         Integer32,
      pr1646v2ATMFwPerFrDlciMCOutOctets
         Counter64,
      pr1646v2ATMFwPerFrDlciMCOutUcastPkts
         Counter64,
      pr1646v2ATMFwPerFrDlciMCOutNUcastPkts
         Counter64,
      pr1646v2ATMFwPerFrDlciMCOutBcastPkts
         Counter64,
      pr1646v2ATMFwPerFrDlciMCOutMcastPkts
         Counter64,
      pr1646v2ATMFwPerFrDlciMCOutDiscards
         Counter64,
      pr1646v2ATMFwPerFrDlciMCOutErrors
         Counter64,
      pr1646v2ATMFwPerFrDlciMCOutQLen
         Counter32,
      pr1646v2ATMFwPerFrDlciMCOutDropEx
         Counter64,
      pr1646v2ATMFwPerFrDlciMCOutDropNoArp
         Counter64,
      pr1646v2ATMFwPerFrDlciMCOutDropFilter
         Counter64,
      pr1646v2ATMFwPerFrDlciMCOutBandwidth15sec
         Integer32,
      pr1646v2ATMFwPerFrDlciMCOutBandwidth30sec
         Integer32,
      pr1646v2ATMFwPerFrDlciMCOutBandwidth1min
         Integer32,
      pr1646v2ATMFwPerFrDlciMCOutBandwidth2min
         Integer32,
      pr1646v2ATMFwPerFrDlciMCOutBandwidth5min
         Integer32,
      pr1646v2ATMFwPerFrDlciFrDlci
         Integer32,
      pr1646v2ATMFwPerFrDlciFrInFecn
         Counter32,
      pr1646v2ATMFwPerFrDlciFrInBecn
         Counter32,
      pr1646v2ATMFwPerFrDlciFrInDe
         Counter32,
      pr1646v2ATMFwPerFrDlciFrInOctets
         Counter32,
      pr1646v2ATMFwPerFrDlciFrInFrames
         Counter32,
      pr1646v2ATMFwPerFrDlciFrOutFecn
         Counter32,
      pr1646v2ATMFwPerFrDlciFrOutBecn
         Counter32,
      pr1646v2ATMFwPerFrDlciFrOutDe
         Counter32,
      pr1646v2ATMFwPerFrDlciFrOutOctets
         Counter32,
      pr1646v2ATMFwPerFrDlciFrOutFrames
         Counter32
      }

pr1646v2ATMFwPerFrDlciGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciEntry 10}

pr1646v2ATMFwPerFrDlciTableIx OBJECT-TYPE
   SYNTAX      TableIndex
   MAX-ACCESS  not-accessible
   STATUS      current
   DESCRIPTION
      ""
   ::= {pr1646v2ATMFwPerFrDlciEntry 11}

pr1646v2ATMFwPerFrDlciName OBJECT-TYPE
   SYNTAX      DisplayString
   MAX-ACCESS  read-only
   STATUS      current
   DESCRIPTION
      "Path: atm.performance.pvcTable.frameRelay.dlciTable.name"
   ::= {pr1646v2ATMFwPerFrDlciEntry 16777216}

pr1646v2ATMFwPerFrDlciMCInOctets OBJECT-TYPE
   SYNTAX      Counter64
   MAX-ACCESS  read-only
   STATUS      current
   DESCRIPTION
      "Path: atm.performance.pvcTable.frameRelay.dlciTable.mibCounters.ifInOctets

       64 bit unsigned wrappable counter."
   ::= {pr1646v2ATMFwPerFrDlciEntry 40697856}

pr1646v2ATMFwPerFrDlciMCInUcast OBJECT-TYPE
   SYNTAX      Counter64
   MAX-ACCESS  read-only
   STATUS      current
   DESCRIPTION
      "Path: atm.performance.pvcTable.frameRelay.dlciTable.mibCounters.ifInUcastPkts

       64 bit unsigned wrappable counter."
   ::= {pr1646v2ATMFwPerFrDlciEntry 40763392}

pr1646v2ATMFwPerFrDlciMCInNUcastPkts OBJECT-TYPE
   SYNTAX      Counter64
   MAX-ACCESS  read-only
   STATUS      current
   DESCRIPTION
      "Path: atm.performance.pvcTable.frameRelay.dlciTable.mibCounters.ifInNUcastPkts

       64 bit unsigned wrappable counter."
   ::= {pr1646v2ATMFwPerFrDlciEntry 40828928}

pr1646v2ATMFwPerFrDlciMCInBcastPkts OBJECT-TYPE
   SYNTAX      Counter64
   MAX-ACCESS  read-only
   STATUS      current
   DESCRIPTION
      "Path: atm.performance.pvcTable.frameRelay.dlciTable.mibCounters.ifInBcastPkts

       64 bit unsigned wrappable counter."
   ::= {pr1646v2ATMFwPerFrDlciEntry 47382528}

pr1646v2ATMFwPerFrDlciMCInMcastPkts OBJECT-TYPE
   SYNTAX      Counter64
   MAX-ACCESS  read-only
   STATUS      current
   DESCRIPTION
      "Path: atm.performance.pvcTable.frameRelay.dlciTable.mibCounters.ifInMcastPkts

       64 bit unsigned wrappable counter."
   ::= {pr1646v2ATMFwPerFrDlciEntry 48037888}

pr1646v2ATMFwPerFrDlciMCInDiscards OBJECT-TYPE
   SYNTAX      Counter64
   MAX-ACCESS  read-only
   STATUS      current
   DESCRIPTION
      "Path: atm.performance.pvcTable.frameRelay.dlciTable.mibCounters.ifInDiscards

       64 bit unsigned wrappable counter."
   ::= {pr1646v2ATMFwPerFrDlciEntry 40894464}

pr1646v2ATMFwPerFrDlciMCInErrors OBJECT-TYPE
   SYNTAX      Counter64
   MAX-ACCESS  read-only
   STATUS      current
   DESCRIPTION
      "Path: atm.performance.pvcTable.frameRelay.dlciTable.mibCounters.ifInErrors

       64 bit unsigned wrappable counter."
   ::= {pr1646v2ATMFwPerFrDlciEntry 40960000}

pr1646v2ATMFwPerFrDlciMCInUnknownProtos OBJECT-TYPE
   SYNTAX      Counter64
   MAX-ACCESS  read-only
   STATUS      current
   DESCRIPTION
      "Path: atm.performance.pvcTable.frameRelay.dlciTable.mibCounters.ifInUnknownProtos

       64 bit unsigned wrappable counter."
   ::= {pr1646v2ATMFwPerFrDlciEntry 41025536}

pr1646v2ATMFwPerFrDlciMCInDropEx OBJECT-TYPE
   SYNTAX      Counter64
   MAX-ACCESS  read-only
   STATUS      current
   DESCRIPTION
      "Path: atm.performance.pvcTable.frameRelay.dlciTable.mibCounters.ifInDropLevelExceeded

       64 bit unsigned wrappable counter."
   ::= {pr1646v2ATMFwPerFrDlciEntry 42074112}

pr1646v2ATMFwPerFrDlciMCInDropNoMac OBJECT-TYPE
   SYNTAX      Counter64
   MAX-ACCESS  read-only
   STATUS      current
   DESCRIPTION
      "Path: atm.performance.pvcTable.frameRelay.dlciTable.mibCounters.ifInDiscardsNoMacFit

       64 bit unsigned wrappable counter."
   ::= {pr1646v2ATMFwPerFrDlciEntry 42270720}

pr1646v2ATMFwPerFrDlciMCInDropNUCast OBJECT-TYPE
   SYNTAX      Counter64
   MAX-ACCESS  read-only
   STATUS      current
   DESCRIPTION
      "Path: atm.performance.pvcTable.frameRelay.dlciTable.mibCounters.ifInDiscardsNUCast

       64 bit unsigned wrappable counter."
   ::= {pr1646v2ATMFwPerFrDlciEntry 42467328}

pr1646v2ATMFwPerFrDlciMCInDropFilter OBJECT-TYPE
   SYNTAX      Counter64
   MAX-ACCESS  read-only
   STATUS      current
   DESCRIPTION
      "Path: atm.performance.pvcTable.frameRelay.dlciTable.mibCounters.ifInDiscardsFilter

       64 bit unsigned wrappable counter."
   ::= {pr1646v2ATMFwPerFrDlciEntry 42532864}

pr1646v2ATMFwPerFrDlciMCInBandwidth15sec OBJECT-TYPE
   SYNTAX      Integer32
   MAX-ACCESS  read-only
   STATUS      current
   DESCRIPTION
      "Path: atm.performance.pvcTable.frameRelay.dlciTable.mibCounters.ifInBandwidth.15sec

       unit name = bps
       formula = 8 * ; 8 /"
   ::= {pr1646v2ATMFwPerFrDlciEntry 45417728}

pr1646v2ATMFwPerFrDlciMCInBandwidth30sec OBJECT-TYPE
   SYNTAX      Integer32
   MAX-ACCESS  read-only
   STATUS      current
   DESCRIPTION
      "Path: atm.performance.pvcTable.frameRelay.dlciTable.mibCounters.ifInBandwidth.30sec

       unit name = bps
       formula = 8 * ; 8 /"
   ::= {pr1646v2ATMFwPerFrDlciEntry 45419008}

pr1646v2ATMFwPerFrDlciMCInBandwidth1min OBJECT-TYPE
   SYNTAX      Integer32
   MAX-ACCESS  read-only
   STATUS      current
   DESCRIPTION
      "Path: atm.performance.pvcTable.frameRelay.dlciTable.mibCounters.ifInBandwidth.1min

       unit name = bps
       formula = 8 * ; 8 /"
   ::= {pr1646v2ATMFwPerFrDlciEntry 45421568}

pr1646v2ATMFwPerFrDlciMCInBandwidth2min OBJECT-TYPE
   SYNTAX      Integer32
   MAX-ACCESS  read-only
   STATUS      current
   DESCRIPTION
      "Path: atm.performance.pvcTable.frameRelay.dlciTable.mibCounters.ifInBandwidth.2min

       unit name = bps
       formula = 8 * ; 8 /"
   ::= {pr1646v2ATMFwPerFrDlciEntry 45426688}

pr1646v2ATMFwPerFrDlciMCInBandwidth5min OBJECT-TYPE
   SYNTAX      Integer32
   MAX-ACCESS  read-only
   STATUS      current
   DESCRIPTION
      "Path: atm.performance.pvcTable.frameRelay.dlciTable.mibCounters.ifInBandwidth.5min

       unit name = bps
       formula = 8 * ; 8 /"
   ::= {pr1646v2ATMFwPerFrDlciEntry 45442048}

pr1646v2ATMFwPerFrDlciMCOutOctets OBJECT-TYPE
   SYNTAX      Counter64
   MAX-ACCESS  read-only
   STATUS      current
   DESCRIPTION
      "Path: atm.performance.pvcTable.frameRelay.dlciTable.mibCounters.ifOutOctets

       64 bit unsigned wrappable counter."
   ::= {pr1646v2ATMFwPerFrDlciEntry 41091072}

pr1646v2ATMFwPerFrDlciMCOutUcastPkts OBJECT-TYPE
   SYNTAX      Counter64
   MAX-ACCESS  read-only
   STATUS      current
   DESCRIPTION
      "Path: atm.performance.pvcTable.frameRelay.dlciTable.mibCounters.ifOutUcastPkts

       64 bit unsigned wrappable counter."
   ::= {pr1646v2ATMFwPerFrDlciEntry 41156608}

pr1646v2ATMFwPerFrDlciMCOutNUcastPkts OBJECT-TYPE
   SYNTAX      Counter64
   MAX-ACCESS  read-only
   STATUS      current
   DESCRIPTION
      "Path: atm.performance.pvcTable.frameRelay.dlciTable.mibCounters.ifOutNUcastPkts

       64 bit unsigned wrappable counter."
   ::= {pr1646v2ATMFwPerFrDlciEntry 41222144}

pr1646v2ATMFwPerFrDlciMCOutBcastPkts OBJECT-TYPE
   SYNTAX      Counter64
   MAX-ACCESS  read-only
   STATUS      current
   DESCRIPTION
      "Path: atm.performance.pvcTable.frameRelay.dlciTable.mibCounters.ifOutBcastPkts

       64 bit unsigned wrappable counter."
   ::= {pr1646v2ATMFwPerFrDlciEntry 47775744}

pr1646v2ATMFwPerFrDlciMCOutMcastPkts OBJECT-TYPE
   SYNTAX      Counter64
   MAX-ACCESS  read-only
   STATUS      current
   DESCRIPTION
      "Path: atm.performance.pvcTable.frameRelay.dlciTable.mibCounters.ifOutMcastPkts

       64 bit unsigned wrappable counter."
   ::= {pr1646v2ATMFwPerFrDlciEntry 48431104}

pr1646v2ATMFwPerFrDlciMCOutDiscards OBJECT-TYPE
   SYNTAX      Counter64
   MAX-ACCESS  read-only
   STATUS      current
   DESCRIPTION
      "Path: atm.performance.pvcTable.frameRelay.dlciTable.mibCounters.ifOutDiscards

       64 bit unsigned wrappable counter."
   ::= {pr1646v2ATMFwPerFrDlciEntry 41287680}

pr1646v2ATMFwPerFrDlciMCOutErrors OBJECT-TYPE
   SYNTAX      Counter64
   MAX-ACCESS  read-only
   STATUS      current
   DESCRIPTION
      "Path: atm.performance.pvcTable.frameRelay.dlciTable.mibCounters.ifOutErrors

       64 bit unsigned wrappable counter."
   ::= {pr1646v2ATMFwPerFrDlciEntry 41353216}

pr1646v2ATMFwPerFrDlciMCOutQLen OBJECT-TYPE
   SYNTAX      Counter32
   MAX-ACCESS  read-only
   STATUS      current
   DESCRIPTION
      "Path: atm.performance.pvcTable.frameRelay.dlciTable.mibCounters.ifOutQLen

       32 bit unsigned wrappable counter."
   ::= {pr1646v2ATMFwPerFrDlciEntry 41418752}

pr1646v2ATMFwPerFrDlciMCOutDropEx OBJECT-TYPE
   SYNTAX      Counter64
   MAX-ACCESS  read-only
   STATUS      current
   DESCRIPTION
      "Path: atm.performance.pvcTable.frameRelay.dlciTable.mibCounters.ifOutDropLevelExceeded

       64 bit unsigned wrappable counter."
   ::= {pr1646v2ATMFwPerFrDlciEntry 41484288}

pr1646v2ATMFwPerFrDlciMCOutDropNoArp OBJECT-TYPE
   SYNTAX      Counter64
   MAX-ACCESS  read-only
   STATUS      current
   DESCRIPTION
      "Path: atm.performance.pvcTable.frameRelay.dlciTable.mibCounters.ifOutDiscardsNoArp

       64 bit unsigned wrappable counter."
   ::= {pr1646v2ATMFwPerFrDlciEntry 42336256}

pr1646v2ATMFwPerFrDlciMCOutDropFilter OBJECT-TYPE
   SYNTAX      Counter64
   MAX-ACCESS  read-only
   STATUS      current
   DESCRIPTION
      "Path: atm.performance.pvcTable.frameRelay.dlciTable.mibCounters.ifOutDiscardsFilter

       64 bit unsigned wrappable counter."
   ::= {pr1646v2ATMFwPerFrDlciEntry 42598400}

pr1646v2ATMFwPerFrDlciMCOutBandwidth15sec OBJECT-TYPE
   SYNTAX      Integer32
   MAX-ACCESS  read-only
   STATUS      current
   DESCRIPTION
      "Path: atm.performance.pvcTable.frameRelay.dlciTable.mibCounters.ifOutBandwidth.15sec

       unit name = bps
       formula = 8 * ; 8 /"
   ::= {pr1646v2ATMFwPerFrDlciEntry 45483264}

pr1646v2ATMFwPerFrDlciMCOutBandwidth30sec OBJECT-TYPE
   SYNTAX      Integer32
   MAX-ACCESS  read-only
   STATUS      current
   DESCRIPTION
      "Path: atm.performance.pvcTable.frameRelay.dlciTable.mibCounters.ifOutBandwidth.30sec

       unit name = bps
       formula = 8 * ; 8 /"
   ::= {pr1646v2ATMFwPerFrDlciEntry 45484544}

pr1646v2ATMFwPerFrDlciMCOutBandwidth1min OBJECT-TYPE
   SYNTAX      Integer32
   MAX-ACCESS  read-only
   STATUS      current
   DESCRIPTION
      "Path: atm.performance.pvcTable.frameRelay.dlciTable.mibCounters.ifOutBandwidth.1min

       unit name = bps
       formula = 8 * ; 8 /"
   ::= {pr1646v2ATMFwPerFrDlciEntry 45487104}

pr1646v2ATMFwPerFrDlciMCOutBandwidth2min OBJECT-TYPE
   SYNTAX      Integer32
   MAX-ACCESS  read-only
   STATUS      current
   DESCRIPTION
      "Path: atm.performance.pvcTable.frameRelay.dlciTable.mibCounters.ifOutBandwidth.2min

       unit name = bps
       formula = 8 * ; 8 /"
   ::= {pr1646v2ATMFwPerFrDlciEntry 45492224}

pr1646v2ATMFwPerFrDlciMCOutBandwidth5min OBJECT-TYPE
   SYNTAX      Integer32
   MAX-ACCESS  read-only
   STATUS      current
   DESCRIPTION
      "Path: atm.performance.pvcTable.frameRelay.dlciTable.mibCounters.ifOutBandwidth.5min

       unit name = bps
       formula = 8 * ; 8 /"
   ::= {pr1646v2ATMFwPerFrDlciEntry 45507584}

pr1646v2ATMFwPerFrDlciFrDlci OBJECT-TYPE
   SYNTAX      Integer32
   MAX-ACCESS  read-only
   STATUS      current
   DESCRIPTION
      "Path: atm.performance.pvcTable.frameRelay.dlciTable.frameRelay.dlci"
   ::= {pr1646v2ATMFwPerFrDlciEntry 224657408}

pr1646v2ATMFwPerFrDlciFrInFecn OBJECT-TYPE
   SYNTAX      Counter32
   MAX-ACCESS  read-only
   STATUS      current
   DESCRIPTION
      "Path: atm.performance.pvcTable.frameRelay.dlciTable.frameRelay.inFecn

       32 bit unsigned wrappable counter."
   ::= {pr1646v2ATMFwPerFrDlciEntry 218169344}

pr1646v2ATMFwPerFrDlciFrInBecn OBJECT-TYPE
   SYNTAX      Counter32
   MAX-ACCESS  read-only
   STATUS      current
   DESCRIPTION
      "Path: atm.performance.pvcTable.frameRelay.dlciTable.frameRelay.inBecn

       32 bit unsigned wrappable counter."
   ::= {pr1646v2ATMFwPerFrDlciEntry 218234880}

pr1646v2ATMFwPerFrDlciFrInDe OBJECT-TYPE
   SYNTAX      Counter32
   MAX-ACCESS  read-only
   STATUS      current
   DESCRIPTION
      "Path: atm.performance.pvcTable.frameRelay.dlciTable.frameRelay.inDe

       32 bit unsigned wrappable counter."
   ::= {pr1646v2ATMFwPerFrDlciEntry 218300416}

pr1646v2ATMFwPerFrDlciFrInOctets OBJECT-TYPE
   SYNTAX      Counter32
   MAX-ACCESS  read-only
   STATUS      current
   DESCRIPTION
      "Path: atm.performance.pvcTable.frameRelay.dlciTable.frameRelay.inOctets

       32 bit unsigned wrappable counter."
   ::= {pr1646v2ATMFwPerFrDlciEntry 218365952}

pr1646v2ATMFwPerFrDlciFrInFrames OBJECT-TYPE
   SYNTAX      Counter32
   MAX-ACCESS  read-only
   STATUS      current
   DESCRIPTION
      "Path: atm.performance.pvcTable.frameRelay.dlciTable.frameRelay.inFrames

       32 bit unsigned wrappable counter."
   ::= {pr1646v2ATMFwPerFrDlciEntry 218431488}

pr1646v2ATMFwPerFrDlciFrOutFecn OBJECT-TYPE
   SYNTAX      Counter32
   MAX-ACCESS  read-only
   STATUS      current
   DESCRIPTION
      "Path: atm.performance.pvcTable.frameRelay.dlciTable.frameRelay.outFecn

       32 bit unsigned wrappable counter."
   ::= {pr1646v2ATMFwPerFrDlciEntry 226492416}

pr1646v2ATMFwPerFrDlciFrOutBecn OBJECT-TYPE
   SYNTAX      Counter32
   MAX-ACCESS  read-only
   STATUS      current
   DESCRIPTION
      "Path: atm.performance.pvcTable.frameRelay.dlciTable.frameRelay.outBecn

       32 bit unsigned wrappable counter."
   ::= {pr1646v2ATMFwPerFrDlciEntry 226557952}

pr1646v2ATMFwPerFrDlciFrOutDe OBJECT-TYPE
   SYNTAX      Counter32
   MAX-ACCESS  read-only
   STATUS      current
   DESCRIPTION
      "Path: atm.performance.pvcTable.frameRelay.dlciTable.frameRelay.outDe

       32 bit unsigned wrappable counter."
   ::= {pr1646v2ATMFwPerFrDlciEntry 226623488}

pr1646v2ATMFwPerFrDlciFrOutOctets OBJECT-TYPE
   SYNTAX      Counter32
   MAX-ACCESS  read-only
   STATUS      current
   DESCRIPTION
      "Path: atm.performance.pvcTable.frameRelay.dlciTable.frameRelay.outOctets

       32 bit unsigned wrappable counter."
   ::= {pr1646v2ATMFwPerFrDlciEntry 226689024}

pr1646v2ATMFwPerFrDlciFrOutFrames OBJECT-TYPE
   SYNTAX      Counter32
   MAX-ACCESS  read-only
   STATUS      current
   DESCRIPTION
      "Path: atm.performance.pvcTable.frameRelay.dlciTable.frameRelay.outFrames

       32 bit unsigned wrappable counter."
   ::= {pr1646v2ATMFwPerFrDlciEntry 226754560}

pr1646v2ATMFwPerFrDlciMCH2P OBJECT-TYPE
   SYNTAX      SEQUENCE OF Pr1646v2ATMFwPerFrDlciMCH2PEntry
   MAX-ACCESS  not-accessible
   STATUS      current
   DESCRIPTION
      ""
   ::= {pr1646v2ATMFwPer 503448186}

pr1646v2ATMFwPerFrDlciMCH2PEntry OBJECT-TYPE
   SYNTAX      Pr1646v2ATMFwPerFrDlciMCH2PEntry
   MAX-ACCESS  not-accessible
   STATUS      current
   DESCRIPTION
      ""
   INDEX      { pr1646v2ATMFwPerFrDlciMCH2PGlobalIx,
                pr1646v2ATMFwPerTableIx,
                pr1646v2ATMFwPerFrDlciTableIx,
                pr1646v2ATMFwPerFrDlciMCH2PTableIx }
   ::= {pr1646v2ATMFwPerFrDlciMCH2P 1}

Pr1646v2ATMFwPerFrDlciMCH2PEntry ::=
   SEQUENCE
      {
      pr1646v2ATMFwPerFrDlciMCH2PGlobalIx
         GlobalIndex,
      pr1646v2ATMFwPerFrDlciMCH2PTableIx
         TableIndex,
      pr1646v2ATMFwPerFrDlciMCH2PSysUpTime
         TimeTicks,
      pr1646v2ATMFwPerFrDlciMCH2PIfUpTime
         TimeTicks,
      pr1646v2ATMFwPerFrDlciMCH2PIfStatChanges
         Counter32,
      pr1646v2ATMFwPerFrDlciMCH2PIfInOctets
         Counter64,
      pr1646v2ATMFwPerFrDlciMCH2PIfInUCPkts
         Counter64,
      pr1646v2ATMFwPerFrDlciMCH2PIfInNUCPkts
         Counter64,
      pr1646v2ATMFwPerFrDlciMCH2PIfInBCPkts
         Counter64,
      pr1646v2ATMFwPerFrDlciMCH2PIfInMCPkts
         Counter64,
      pr1646v2ATMFwPerFrDlciMCH2PIfInDiscards
         Counter64,
      pr1646v2ATMFwPerFrDlciMCH2PIfInErrors
         Counter64,
      pr1646v2ATMFwPerFrDlciMCH2PIfInUnkwn
         Counter64,
      pr1646v2ATMFwPerFrDlciMCH2PInDropEx
         Counter64,
      pr1646v2ATMFwPerFrDlciMCH2PInDropNoMac
         Counter64,
      pr1646v2ATMFwPerFrDlciMCH2PInDropNUCast
         Counter64,
      pr1646v2ATMFwPerFrDlciMCH2PInDropFilter
         Counter64,
      pr1646v2ATMFwPerFrDlciMCH2PIfInBandwidth
         Integer32,
      pr1646v2ATMFwPerFrDlciMCH2PIfOutOctets
         Counter64,
      pr1646v2ATMFwPerFrDlciMCH2PIfOutUCPkts
         Counter64,
      pr1646v2ATMFwPerFrDlciMCH2PIfOutNUCPkts
         Counter64,
      pr1646v2ATMFwPerFrDlciMCH2PIfOutBCPkts
         Counter64,
      pr1646v2ATMFwPerFrDlciMCH2PIfOutMCPkts
         Counter64,
      pr1646v2ATMFwPerFrDlciMCH2PIfOutDiscards
         Counter64,
      pr1646v2ATMFwPerFrDlciMCH2PIfOutErrors
         Counter64,
      pr1646v2ATMFwPerFrDlciMCH2POutDropEx
         Counter64,
      pr1646v2ATMFwPerFrDlciMCH2POutDropNoArp
         Counter64,
      pr1646v2ATMFwPerFrDlciMCH2POutDropFilter
         Counter64,
      pr1646v2ATMFwPerFrDlciMCH2PIfOutBandwidth
         Integer32,
      pr1646v2ATMFwPerFrDlciMCH2PIfErrSec
         Counter32
      }

pr1646v2ATMFwPerFrDlciMCH2PGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciMCH2PEntry 10}

pr1646v2ATMFwPerFrDlciMCH2PTableIx OBJECT-TYPE
   SYNTAX      TableIndex
   MAX-ACCESS  not-accessible
   STATUS      current
   DESCRIPTION
      ""
   ::= {pr1646v2ATMFwPerFrDlciMCH2PEntry 11}

pr1646v2ATMFwPerFrDlciMCH2PSysUpTime OBJECT-TYPE
   SYNTAX      TimeTicks
   MAX-ACCESS  read-only
   STATUS      current
   DESCRIPTION
      "Path: atm.performance.pvcTable.frameRelay.dlciTable.mibCounters.h2Performance.sysUpTime

       Time in centi-second."
   ::= {pr1646v2ATMFwPerFrDlciMCH2PEntry 16777216}

pr1646v2ATMFwPerFrDlciMCH2PIfUpTime OBJECT-TYPE
   SYNTAX      TimeTicks
   MAX-ACCESS  read-only
   STATUS      current
   DESCRIPTION
      "Path: atm.performance.pvcTable.frameRelay.dlciTable.mibCounters.h2Performance.ifUpTime

       Time in centi-second."
   ::= {pr1646v2ATMFwPerFrDlciMCH2PEntry 33554432}

pr1646v2ATMFwPerFrDlciMCH2PIfStatChanges OBJECT-TYPE
   SYNTAX      Counter32
   MAX-ACCESS  read-only
   STATUS      current
   DESCRIPTION
      "Path: atm.performance.pvcTable.frameRelay.dlciTable.mibCounters.h2Performance.ifStatusChanges

       32 bit unsigned wrappable counter."
   ::= {pr1646v2ATMFwPerFrDlciMCH2PEntry 50331648}

pr1646v2ATMFwPerFrDlciMCH2PIfInOctets OBJECT-TYPE
   SYNTAX      Counter64
   MAX-ACCESS  read-only
   STATUS      current
   DESCRIPTION
      "Path: atm.performance.pvcTable.frameRelay.dlciTable.mibCounters.h2Performance.ifInOctets

       64 bit unsigned wrappable counter."
   ::= {pr1646v2ATMFwPerFrDlciMCH2PEntry 67108864}

pr1646v2ATMFwPerFrDlciMCH2PIfInUCPkts OBJECT-TYPE
   SYNTAX      Counter64
   MAX-ACCESS  read-only
   STATUS      current
   DESCRIPTION
      "Path: atm.performance.pvcTable.frameRelay.dlciTable.mibCounters.h2Performance.ifInUcastPkts

       64 bit unsigned wrappable counter."
   ::= {pr1646v2ATMFwPerFrDlciMCH2PEntry 83886080}

pr1646v2ATMFwPerFrDlciMCH2PIfInNUCPkts OBJECT-TYPE
   SYNTAX      Counter64
   MAX-ACCESS  read-only
   STATUS      current
   DESCRIPTION
      "Path: atm.performance.pvcTable.frameRelay.dlciTable.mibCounters.h2Performance.ifInNUcastPkts

       64 bit unsigned wrappable counter."
   ::= {pr1646v2ATMFwPerFrDlciMCH2PEntry 100663296}

pr1646v2ATMFwPerFrDlciMCH2PIfInBCPkts OBJECT-TYPE
   SYNTAX      Counter64
   MAX-ACCESS  read-only
   STATUS      current
   DESCRIPTION
      "Path: atm.performance.pvcTable.frameRelay.dlciTable.mibCounters.h2Performance.ifInBcastPkts

       64 bit unsigned wrappable counter."
   ::= {pr1646v2ATMFwPerFrDlciMCH2PEntry 419430400}

pr1646v2ATMFwPerFrDlciMCH2PIfInMCPkts OBJECT-TYPE
   SYNTAX      Counter64
   MAX-ACCESS  read-only
   STATUS      current
   DESCRIPTION
      "Path: atm.performance.pvcTable.frameRelay.dlciTable.mibCounters.h2Performance.ifInMcastPkts

       64 bit unsigned wrappable counter."
   ::= {pr1646v2ATMFwPerFrDlciMCH2PEntry 436207616}

pr1646v2ATMFwPerFrDlciMCH2PIfInDiscards OBJECT-TYPE
   SYNTAX      Counter64
   MAX-ACCESS  read-only
   STATUS      current
   DESCRIPTION
      "Path: atm.performance.pvcTable.frameRelay.dlciTable.mibCounters.h2Performance.ifInDiscards

       64 bit unsigned wrappable counter."
   ::= {pr1646v2ATMFwPerFrDlciMCH2PEntry 117440512}

pr1646v2ATMFwPerFrDlciMCH2PIfInErrors OBJECT-TYPE
   SYNTAX      Counter64
   MAX-ACCESS  read-only
   STATUS      current
   DESCRIPTION
      "Path: atm.performance.pvcTable.frameRelay.dlciTable.mibCounters.h2Performance.ifInErrors

       64 bit unsigned wrappable counter."
   ::= {pr1646v2ATMFwPerFrDlciMCH2PEntry 134217728}

pr1646v2ATMFwPerFrDlciMCH2PIfInUnkwn OBJECT-TYPE
   SYNTAX      Counter64
   MAX-ACCESS  read-only
   STATUS      current
   DESCRIPTION
      "Path: atm.performance.pvcTable.frameRelay.dlciTable.mibCounters.h2Performance.ifInUnknownProtos

       64 bit unsigned wrappable counter."
   ::= {pr1646v2ATMFwPerFrDlciMCH2PEntry 150994944}

pr1646v2ATMFwPerFrDlciMCH2PInDropEx OBJECT-TYPE
   SYNTAX      Counter64
   MAX-ACCESS  read-only
   STATUS      current
   DESCRIPTION
      "Path: atm.performance.pvcTable.frameRelay.dlciTable.mibCounters.h2Performance.ifInDropLevelExceeded

       64 bit unsigned wrappable counter."
   ::= {pr1646v2ATMFwPerFrDlciMCH2PEntry 335544320}

pr1646v2ATMFwPerFrDlciMCH2PInDropNoMac OBJECT-TYPE
   SYNTAX      Counter64
   MAX-ACCESS  read-only
   STATUS      current
   DESCRIPTION
      "Path: atm.performance.pvcTable.frameRelay.dlciTable.mibCounters.h2Performance.fInDiscardsNoMacFit

       64 bit unsigned wrappable counter."
   ::= {pr1646v2ATMFwPerFrDlciMCH2PEntry 301989888}

pr1646v2ATMFwPerFrDlciMCH2PInDropNUCast OBJECT-TYPE
   SYNTAX      Counter64
   MAX-ACCESS  read-only
   STATUS      current
   DESCRIPTION
      "Path: atm.performance.pvcTable.frameRelay.dlciTable.mibCounters.h2Performance.fInDiscardsNUCast

       64 bit unsigned wrappable counter."
   ::= {pr1646v2ATMFwPerFrDlciMCH2PEntry 318767104}

pr1646v2ATMFwPerFrDlciMCH2PInDropFilter OBJECT-TYPE
   SYNTAX      Counter64
   MAX-ACCESS  read-only
   STATUS      current
   DESCRIPTION
      "Path: atm.performance.pvcTable.frameRelay.dlciTable.mibCounters.h2Performance.fInDiscardsFilter

       64 bit unsigned wrappable counter."
   ::= {pr1646v2ATMFwPerFrDlciMCH2PEntry 385875968}

pr1646v2ATMFwPerFrDlciMCH2PIfInBandwidth OBJECT-TYPE
   SYNTAX      Integer32
   MAX-ACCESS  read-only
   STATUS      current
   DESCRIPTION
      "Path: atm.performance.pvcTable.frameRelay.dlciTable.mibCounters.h2Performance.ifInBandwidth

       unit name = bps
       formula = 8 * ; 8 /"
   ::= {pr1646v2ATMFwPerFrDlciMCH2PEntry 268435456}

pr1646v2ATMFwPerFrDlciMCH2PIfOutOctets OBJECT-TYPE
   SYNTAX      Counter64
   MAX-ACCESS  read-only
   STATUS      current
   DESCRIPTION
      "Path: atm.performance.pvcTable.frameRelay.dlciTable.mibCounters.h2Performance.ifOutOctets

       64 bit unsigned wrappable counter."
   ::= {pr1646v2ATMFwPerFrDlciMCH2PEntry 167772160}

pr1646v2ATMFwPerFrDlciMCH2PIfOutUCPkts OBJECT-TYPE
   SYNTAX      Counter64
   MAX-ACCESS  read-only
   STATUS      current
   DESCRIPTION
      "Path: atm.performance.pvcTable.frameRelay.dlciTable.mibCounters.h2Performance.ifOutUcastPkts

       64 bit unsigned wrappable counter."
   ::= {pr1646v2ATMFwPerFrDlciMCH2PEntry 184549376}

pr1646v2ATMFwPerFrDlciMCH2PIfOutNUCPkts OBJECT-TYPE
   SYNTAX      Counter64
   MAX-ACCESS  read-only
   STATUS      current
   DESCRIPTION
      "Path: atm.performance.pvcTable.frameRelay.dlciTable.mibCounters.h2Performance.ifOutNUcastPkts

       64 bit unsigned wrappable counter."
   ::= {pr1646v2ATMFwPerFrDlciMCH2PEntry 201326592}

pr1646v2ATMFwPerFrDlciMCH2PIfOutBCPkts OBJECT-TYPE
   SYNTAX      Counter64
   MAX-ACCESS  read-only
   STATUS      current
   DESCRIPTION
      "Path: atm.performance.pvcTable.frameRelay.dlciTable.mibCounters.h2Performance.ifOutBcastPkts

       64 bit unsigned wrappable counter."
   ::= {pr1646v2ATMFwPerFrDlciMCH2PEntry 452984832}

pr1646v2ATMFwPerFrDlciMCH2PIfOutMCPkts OBJECT-TYPE
   SYNTAX      Counter64
   MAX-ACCESS  read-only
   STATUS      current
   DESCRIPTION
      "Path: atm.performance.pvcTable.frameRelay.dlciTable.mibCounters.h2Performance.ifOutMcastPkts

       64 bit unsigned wrappable counter."
   ::= {pr1646v2ATMFwPerFrDlciMCH2PEntry 469762048}

pr1646v2ATMFwPerFrDlciMCH2PIfOutDiscards OBJECT-TYPE
   SYNTAX      Counter64
   MAX-ACCESS  read-only
   STATUS      current
   DESCRIPTION
      "Path: atm.performance.pvcTable.frameRelay.dlciTable.mibCounters.h2Performance.ifOutDiscards

       64 bit unsigned wrappable counter."
   ::= {pr1646v2ATMFwPerFrDlciMCH2PEntry 218103808}

pr1646v2ATMFwPerFrDlciMCH2PIfOutErrors OBJECT-TYPE
   SYNTAX      Counter64
   MAX-ACCESS  read-only
   STATUS      current
   DESCRIPTION
      "Path: atm.performance.pvcTable.frameRelay.dlciTable.mibCounters.h2Performance.ifOutErrors

       64 bit unsigned wrappable counter."
   ::= {pr1646v2ATMFwPerFrDlciMCH2PEntry 234881024}

pr1646v2ATMFwPerFrDlciMCH2POutDropEx OBJECT-TYPE
   SYNTAX      Counter64
   MAX-ACCESS  read-only
   STATUS      current
   DESCRIPTION
      "Path: atm.performance.pvcTable.frameRelay.dlciTable.mibCounters.h2Performance.ifOutDropLevelExceeded

       64 bit unsigned wrappable counter."
   ::= {pr1646v2ATMFwPerFrDlciMCH2PEntry 352321536}

pr1646v2ATMFwPerFrDlciMCH2POutDropNoArp OBJECT-TYPE
   SYNTAX      Counter64
   MAX-ACCESS  read-only
   STATUS      current
   DESCRIPTION
      "Path: atm.performance.pvcTable.frameRelay.dlciTable.mibCounters.h2Performance.ifOutDiscardsNoArp

       64 bit unsigned wrappable counter."
   ::= {pr1646v2ATMFwPerFrDlciMCH2PEntry 369098752}

pr1646v2ATMFwPerFrDlciMCH2POutDropFilter OBJECT-TYPE
   SYNTAX      Counter64
   MAX-ACCESS  read-only
   STATUS      current
   DESCRIPTION
      "Path: atm.performance.pvcTable.frameRelay.dlciTable.mibCounters.h2Performance.ifOutDiscardsFilter

       64 bit unsigned wrappable counter."
   ::= {pr1646v2ATMFwPerFrDlciMCH2PEntry 402653184}

pr1646v2ATMFwPerFrDlciMCH2PIfOutBandwidth OBJECT-TYPE
   SYNTAX      Integer32
   MAX-ACCESS  read-only
   STATUS      current
   DESCRIPTION
      "Path: atm.performance.pvcTable.frameRelay.dlciTable.mibCounters.h2Performance.ifOutBandwidth

       unit name = bps
       formula = 8 * ; 8 /"
   ::= {pr1646v2ATMFwPerFrDlciMCH2PEntry 285212672}

pr1646v2ATMFwPerFrDlciMCH2PIfErrSec OBJECT-TYPE
   SYNTAX      Counter32
   MAX-ACCESS  read-only
   STATUS      current
   DESCRIPTION
      "Path: atm.performance.pvcTable.frameRelay.dlciTable.mibCounters.h2Performance.ifErrSec

       32 bit unsigned wrappable counter."
   ::= {pr1646v2ATMFwPerFrDlciMCH2PEntry 251658240}

pr1646v2ATMFwPerFrDlciMCH24P OBJECT-TYPE
   SYNTAX      SEQUENCE OF Pr1646v2ATMFwPerFrDlciMCH24PEntry
   MAX-ACCESS  not-accessible
   STATUS      current
   DESCRIPTION
      ""
   ::= {pr1646v2ATMFwPer 503448187}

pr1646v2ATMFwPerFrDlciMCH24PEntry OBJECT-TYPE
   SYNTAX      Pr1646v2ATMFwPerFrDlciMCH24PEntry
   MAX-ACCESS  not-accessible
   STATUS      current
   DESCRIPTION
      ""
   INDEX      { pr1646v2ATMFwPerFrDlciMCH24PGlobalIx,
                pr1646v2ATMFwPerTableIx,
                pr1646v2ATMFwPerFrDlciTableIx,
                pr1646v2ATMFwPerFrDlciMCH24PTableIx }
   ::= {pr1646v2ATMFwPerFrDlciMCH24P 1}

Pr1646v2ATMFwPerFrDlciMCH24PEntry ::=
   SEQUENCE
      {
      pr1646v2ATMFwPerFrDlciMCH24PGlobalIx
         GlobalIndex,
      pr1646v2ATMFwPerFrDlciMCH24PTableIx
         TableIndex,
      pr1646v2ATMFwPerFrDlciMCH24PSysUpTime
         TimeTicks,
      pr1646v2ATMFwPerFrDlciMCH24PIfUpTime
         TimeTicks,
      pr1646v2ATMFwPerFrDlciMCH24PIfStatChanges
         Counter32,
      pr1646v2ATMFwPerFrDlciMCH24PIfInOctets
         Counter64,
      pr1646v2ATMFwPerFrDlciMCH24PIfInUCPkts
         Counter64,
      pr1646v2ATMFwPerFrDlciMCH24PIfInNUCPkts
         Counter64,
      pr1646v2ATMFwPerFrDlciMCH24PIfInBCPkts
         Counter64,
      pr1646v2ATMFwPerFrDlciMCH24PIfInMCPkts
         Counter64,
      pr1646v2ATMFwPerFrDlciMCH24PIfInDiscards
         Counter64,
      pr1646v2ATMFwPerFrDlciMCH24PIfInErrors
         Counter64,
      pr1646v2ATMFwPerFrDlciMCH24PIfInUnkwn
         Counter64,
      pr1646v2ATMFwPerFrDlciMCH24PInDropEx
         Counter64,
      pr1646v2ATMFwPerFrDlciMCH24PInDropNoMac
         Counter64,
      pr1646v2ATMFwPerFrDlciMCH24PInDropNUCast
         Counter64,
      pr1646v2ATMFwPerFrDlciMCH24PInDropFilter
         Counter64,
      pr1646v2ATMFwPerFrDlciMCH24PIfInBandwidth
         Integer32,
      pr1646v2ATMFwPerFrDlciMCH24PIfOutOctets
         Counter64,
      pr1646v2ATMFwPerFrDlciMCH24PIfOutUCPkts
         Counter64,
      pr1646v2ATMFwPerFrDlciMCH24PIfOutNUCPkts
         Counter64,
      pr1646v2ATMFwPerFrDlciMCH24PIfOutBCPkts
         Counter64,
      pr1646v2ATMFwPerFrDlciMCH24PIfOutMCPkts
         Counter64,
      pr1646v2ATMFwPerFrDlciMCH24PIfOutDiscards
         Counter64,
      pr1646v2ATMFwPerFrDlciMCH24PIfOutErrors
         Counter64,
      pr1646v2ATMFwPerFrDlciMCH24POutDropEx
         Counter64,
      pr1646v2ATMFwPerFrDlciMCH24POutDropNoArp
         Counter64,
      pr1646v2ATMFwPerFrDlciMCH24POutDropFilter
         Counter64,
      pr1646v2ATMFwPerFrDlciMCH24PIfOutBandwidth
         Integer32,
      pr1646v2ATMFwPerFrDlciMCH24PIfErrSec
         Counter32
      }

pr1646v2ATMFwPerFrDlciMCH24PGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciMCH24PEntry 10}

pr1646v2ATMFwPerFrDlciMCH24PTableIx OBJECT-TYPE
   SYNTAX      TableIndex
   MAX-ACCESS  not-accessible
   STATUS      current
   DESCRIPTION
      ""
   ::= {pr1646v2ATMFwPerFrDlciMCH24PEntry 11}

pr1646v2ATMFwPerFrDlciMCH24PSysUpTime OBJECT-TYPE
   SYNTAX      TimeTicks
   MAX-ACCESS  read-only
   STATUS      current
   DESCRIPTION
      "Path: atm.performance.pvcTable.frameRelay.dlciTable.mibCounters.h24Performance.sysUpTime

       Time in centi-second."
   ::= {pr1646v2ATMFwPerFrDlciMCH24PEntry 16777216}

pr1646v2ATMFwPerFrDlciMCH24PIfUpTime OBJECT-TYPE
   SYNTAX      TimeTicks
   MAX-ACCESS  read-only
   STATUS      current
   DESCRIPTION
      "Path: atm.performance.pvcTable.frameRelay.dlciTable.mibCounters.h24Performance.ifUpTime

       Time in centi-second."
   ::= {pr1646v2ATMFwPerFrDlciMCH24PEntry 33554432}

pr1646v2ATMFwPerFrDlciMCH24PIfStatChanges OBJECT-TYPE
   SYNTAX      Counter32
   MAX-ACCESS  read-only
   STATUS      current
   DESCRIPTION
      "Path: atm.performance.pvcTable.frameRelay.dlciTable.mibCounters.h24Performance.ifStatusChanges

       32 bit unsigned wrappable counter."
   ::= {pr1646v2ATMFwPerFrDlciMCH24PEntry 50331648}

pr1646v2ATMFwPerFrDlciMCH24PIfInOctets OBJECT-TYPE
   SYNTAX      Counter64
   MAX-ACCESS  read-only
   STATUS      current
   DESCRIPTION
      "Path: atm.performance.pvcTable.frameRelay.dlciTable.mibCounters.h24Performance.ifInOctets

       64 bit unsigned wrappable counter."
   ::= {pr1646v2ATMFwPerFrDlciMCH24PEntry 67108864}

pr1646v2ATMFwPerFrDlciMCH24PIfInUCPkts OBJECT-TYPE
   SYNTAX      Counter64
   MAX-ACCESS  read-only
   STATUS      current
   DESCRIPTION
      "Path: atm.performance.pvcTable.frameRelay.dlciTable.mibCounters.h24Performance.ifInUcastPkts

       64 bit unsigned wrappable counter."
   ::= {pr1646v2ATMFwPerFrDlciMCH24PEntry 83886080}

pr1646v2ATMFwPerFrDlciMCH24PIfInNUCPkts OBJECT-TYPE
   SYNTAX      Counter64
   MAX-ACCESS  read-only
   STATUS      current
   DESCRIPTION
      "Path: atm.performance.pvcTable.frameRelay.dlciTable.mibCounters.h24Performance.ifInNUcastPkts

       64 bit unsigned wrappable counter."
   ::= {pr1646v2ATMFwPerFrDlciMCH24PEntry 100663296}

pr1646v2ATMFwPerFrDlciMCH24PIfInBCPkts OBJECT-TYPE
   SYNTAX      Counter64
   MAX-ACCESS  read-only
   STATUS      current
   DESCRIPTION
      "Path: atm.performance.pvcTable.frameRelay.dlciTable.mibCounters.h24Performance.ifInBcastPkts

       64 bit unsigned wrappable counter."
   ::= {pr1646v2ATMFwPerFrDlciMCH24PEntry 419430400}

pr1646v2ATMFwPerFrDlciMCH24PIfInMCPkts OBJECT-TYPE
   SYNTAX      Counter64
   MAX-ACCESS  read-only
   STATUS      current
   DESCRIPTION
      "Path: atm.performance.pvcTable.frameRelay.dlciTable.mibCounters.h24Performance.ifInMcastPkts

       64 bit unsigned wrappable counter."
   ::= {pr1646v2ATMFwPerFrDlciMCH24PEntry 436207616}

pr1646v2ATMFwPerFrDlciMCH24PIfInDiscards OBJECT-TYPE
   SYNTAX      Counter64
   MAX-ACCESS  read-only
   STATUS      current
   DESCRIPTION
      "Path: atm.performance.pvcTable.frameRelay.dlciTable.mibCounters.h24Performance.ifInDiscards

       64 bit unsigned wrappable counter."
   ::= {pr1646v2ATMFwPerFrDlciMCH24PEntry 117440512}

pr1646v2ATMFwPerFrDlciMCH24PIfInErrors OBJECT-TYPE
   SYNTAX      Counter64
   MAX-ACCESS  read-only
   STATUS      current
   DESCRIPTION
      "Path: atm.performance.pvcTable.frameRelay.dlciTable.mibCounters.h24Performance.ifInErrors

       64 bit unsigned wrappable counter."
   ::= {pr1646v2ATMFwPerFrDlciMCH24PEntry 134217728}

pr1646v2ATMFwPerFrDlciMCH24PIfInUnkwn OBJECT-TYPE
   SYNTAX      Counter64
   MAX-ACCESS  read-only
   STATUS      current
   DESCRIPTION
      "Path: atm.performance.pvcTable.frameRelay.dlciTable.mibCounters.h24Performance.ifInUnknownProtos

       64 bit unsigned wrappable counter."
   ::= {pr1646v2ATMFwPerFrDlciMCH24PEntry 150994944}

pr1646v2ATMFwPerFrDlciMCH24PInDropEx OBJECT-TYPE
   SYNTAX      Counter64
   MAX-ACCESS  read-only
   STATUS      current
   DESCRIPTION
      "Path: atm.performance.pvcTable.frameRelay.dlciTable.mibCounters.h24Performance.ifInDropLevelExceeded

       64 bit unsigned wrappable counter."
   ::= {pr1646v2ATMFwPerFrDlciMCH24PEntry 335544320}

pr1646v2ATMFwPerFrDlciMCH24PInDropNoMac OBJECT-TYPE
   SYNTAX      Counter64
   MAX-ACCESS  read-only
   STATUS      current
   DESCRIPTION
      "Path: atm.performance.pvcTable.frameRelay.dlciTable.mibCounters.h24Performance.fInDiscardsNoMacFit

       64 bit unsigned wrappable counter."
   ::= {pr1646v2ATMFwPerFrDlciMCH24PEntry 301989888}

pr1646v2ATMFwPerFrDlciMCH24PInDropNUCast OBJECT-TYPE
   SYNTAX      Counter64
   MAX-ACCESS  read-only
   STATUS      current
   DESCRIPTION
      "Path: atm.performance.pvcTable.frameRelay.dlciTable.mibCounters.h24Performance.fInDiscardsNUCast

       64 bit unsigned wrappable counter."
   ::= {pr1646v2ATMFwPerFrDlciMCH24PEntry 318767104}

pr1646v2ATMFwPerFrDlciMCH24PInDropFilter OBJECT-TYPE
   SYNTAX      Counter64
   MAX-ACCESS  read-only
   STATUS      current
   DESCRIPTION
      "Path: atm.performance.pvcTable.frameRelay.dlciTable.mibCounters.h24Performance.fInDiscardsFilter

       64 bit unsigned wrappable counter."
   ::= {pr1646v2ATMFwPerFrDlciMCH24PEntry 385875968}

pr1646v2ATMFwPerFrDlciMCH24PIfInBandwidth OBJECT-TYPE
   SYNTAX      Integer32
   MAX-ACCESS  read-only
   STATUS      current
   DESCRIPTION
      "Path: atm.performance.pvcTable.frameRelay.dlciTable.mibCounters.h24Performance.ifInBandwidth

       unit name = bps
       formula = 8 * ; 8 /"
   ::= {pr1646v2ATMFwPerFrDlciMCH24PEntry 268435456}

pr1646v2ATMFwPerFrDlciMCH24PIfOutOctets OBJECT-TYPE
   SYNTAX      Counter64
   MAX-ACCESS  read-only
   STATUS      current
   DESCRIPTION
      "Path: atm.performance.pvcTable.frameRelay.dlciTable.mibCounters.h24Performance.ifOutOctets

       64 bit unsigned wrappable counter."
   ::= {pr1646v2ATMFwPerFrDlciMCH24PEntry 167772160}

pr1646v2ATMFwPerFrDlciMCH24PIfOutUCPkts OBJECT-TYPE
   SYNTAX      Counter64
   MAX-ACCESS  read-only
   STATUS      current
   DESCRIPTION
      "Path: atm.performance.pvcTable.frameRelay.dlciTable.mibCounters.h24Performance.ifOutUcastPkts

       64 bit unsigned wrappable counter."
   ::= {pr1646v2ATMFwPerFrDlciMCH24PEntry 184549376}

pr1646v2ATMFwPerFrDlciMCH24PIfOutNUCPkts OBJECT-TYPE
   SYNTAX      Counter64
   MAX-ACCESS  read-only
   STATUS      current
   DESCRIPTION
      "Path: atm.performance.pvcTable.frameRelay.dlciTable.mibCounters.h24Performance.ifOutNUcastPkts

       64 bit unsigned wrappable counter."
   ::= {pr1646v2ATMFwPerFrDlciMCH24PEntry 201326592}

pr1646v2ATMFwPerFrDlciMCH24PIfOutBCPkts OBJECT-TYPE
   SYNTAX      Counter64
   MAX-ACCESS  read-only
   STATUS      current
   DESCRIPTION
      "Path: atm.performance.pvcTable.frameRelay.dlciTable.mibCounters.h24Performance.ifOutBcastPkts

       64 bit unsigned wrappable counter."
   ::= {pr1646v2ATMFwPerFrDlciMCH24PEntry 452984832}

pr1646v2ATMFwPerFrDlciMCH24PIfOutMCPkts OBJECT-TYPE
   SYNTAX      Counter64
   MAX-ACCESS  read-only
   STATUS      current
   DESCRIPTION
      "Path: atm.performance.pvcTable.frameRelay.dlciTable.mibCounters.h24Performance.ifOutMcastPkts

       64 bit unsigned wrappable counter."
   ::= {pr1646v2ATMFwPerFrDlciMCH24PEntry 469762048}

pr1646v2ATMFwPerFrDlciMCH24PIfOutDiscards OBJECT-TYPE
   SYNTAX      Counter64
   MAX-ACCESS  read-only
   STATUS      current
   DESCRIPTION
      "Path: atm.performance.pvcTable.frameRelay.dlciTable.mibCounters.h24Performance.ifOutDiscards

       64 bit unsigned wrappable counter."
   ::= {pr1646v2ATMFwPerFrDlciMCH24PEntry 218103808}

pr1646v2ATMFwPerFrDlciMCH24PIfOutErrors OBJECT-TYPE
   SYNTAX      Counter64
   MAX-ACCESS  read-only
   STATUS      current
   DESCRIPTION
      "Path: atm.performance.pvcTable.frameRelay.dlciTable.mibCounters.h24Performance.ifOutErrors

       64 bit unsigned wrappable counter."
   ::= {pr1646v2ATMFwPerFrDlciMCH24PEntry 234881024}

pr1646v2ATMFwPerFrDlciMCH24POutDropEx OBJECT-TYPE
   SYNTAX      Counter64
   MAX-ACCESS  read-only
   STATUS      current
   DESCRIPTION
      "Path: atm.performance.pvcTable.frameRelay.dlciTable.mibCounters.h24Performance.ifOutDropLevelExceeded

       64 bit unsigned wrappable counter."
   ::= {pr1646v2ATMFwPerFrDlciMCH24PEntry 352321536}

pr1646v2ATMFwPerFrDlciMCH24POutDropNoArp OBJECT-TYPE
   SYNTAX      Counter64
   MAX-ACCESS  read-only
   STATUS      current
   DESCRIPTION
      "Path: atm.performance.pvcTable.frameRelay.dlciTable.mibCounters.h24Performance.ifOutDiscardsNoArp

       64 bit unsigned wrappable counter."
   ::= {pr1646v2ATMFwPerFrDlciMCH24PEntry 369098752}

pr1646v2ATMFwPerFrDlciMCH24POutDropFilter OBJECT-TYPE
   SYNTAX      Counter64
   MAX-ACCESS  read-only
   STATUS      current
   DESCRIPTION
      "Path: atm.performance.pvcTable.frameRelay.dlciTable.mibCounters.h24Performance.ifOutDiscardsFilter

       64 bit unsigned wrappable counter."
   ::= {pr1646v2ATMFwPerFrDlciMCH24PEntry 402653184}

pr1646v2ATMFwPerFrDlciMCH24PIfOutBandwidth OBJECT-TYPE
   SYNTAX      Integer32
   MAX-ACCESS  read-only
   STATUS      current
   DESCRIPTION
      "Path: atm.performance.pvcTable.frameRelay.dlciTable.mibCounters.h24Performance.ifOutBandwidth

       unit name = bps
       formula = 8 * ; 8 /"
   ::= {pr1646v2ATMFwPerFrDlciMCH24PEntry 285212672}

pr1646v2ATMFwPerFrDlciMCH24PIfErrSec OBJECT-TYPE
   SYNTAX      Counter32
   MAX-ACCESS  read-only
   STATUS      current
   DESCRIPTION
      "Path: atm.performance.pvcTable.frameRelay.dlciTable.mibCounters.h24Performance.ifErrSec

       32 bit unsigned wrappable counter."
   ::= {pr1646v2ATMFwPerFrDlciMCH24PEntry 251658240}

pr1646v2ATMFwPerFrDlciMCD7P OBJECT-TYPE
   SYNTAX      SEQUENCE OF Pr1646v2ATMFwPerFrDlciMCD7PEntry
   MAX-ACCESS  not-accessible
   STATUS      current
   DESCRIPTION
      ""
   ::= {pr1646v2ATMFwPer 503448188}

pr1646v2ATMFwPerFrDlciMCD7PEntry OBJECT-TYPE
   SYNTAX      Pr1646v2ATMFwPerFrDlciMCD7PEntry
   MAX-ACCESS  not-accessible
   STATUS      current
   DESCRIPTION
      ""
   INDEX      { pr1646v2ATMFwPerFrDlciMCD7PGlobalIx,
                pr1646v2ATMFwPerTableIx,
                pr1646v2ATMFwPerFrDlciTableIx,
                pr1646v2ATMFwPerFrDlciMCD7PTableIx }
   ::= {pr1646v2ATMFwPerFrDlciMCD7P 1}

Pr1646v2ATMFwPerFrDlciMCD7PEntry ::=
   SEQUENCE
      {
      pr1646v2ATMFwPerFrDlciMCD7PGlobalIx
         GlobalIndex,
      pr1646v2ATMFwPerFrDlciMCD7PTableIx
         TableIndex,
      pr1646v2ATMFwPerFrDlciMCD7PSysUpTime
         TimeTicks,
      pr1646v2ATMFwPerFrDlciMCD7PIfUpTime
         TimeTicks,
      pr1646v2ATMFwPerFrDlciMCD7PIfStatChanges
         Counter32,
      pr1646v2ATMFwPerFrDlciMCD7PIfInOctets
         Counter64,
      pr1646v2ATMFwPerFrDlciMCD7PIfInUCPkts
         Counter64,
      pr1646v2ATMFwPerFrDlciMCD7PIfInNUCPkts
         Counter64,
      pr1646v2ATMFwPerFrDlciMCD7PIfInBCPkts
         Counter64,
      pr1646v2ATMFwPerFrDlciMCD7PIfInMCPkts
         Counter64,
      pr1646v2ATMFwPerFrDlciMCD7PIfInDiscards
         Counter64,
      pr1646v2ATMFwPerFrDlciMCD7PIfInErrors
         Counter64,
      pr1646v2ATMFwPerFrDlciMCD7PIfInUnkwn
         Counter64,
      pr1646v2ATMFwPerFrDlciMCD7PInDropEx
         Counter64,
      pr1646v2ATMFwPerFrDlciMCD7PInDropNoMac
         Counter64,
      pr1646v2ATMFwPerFrDlciMCD7PInDropNUCast
         Counter64,
      pr1646v2ATMFwPerFrDlciMCD7PInDropFilter
         Counter64,
      pr1646v2ATMFwPerFrDlciMCD7PIfInBandwidth
         Integer32,
      pr1646v2ATMFwPerFrDlciMCD7PIfOutOctets
         Counter64,
      pr1646v2ATMFwPerFrDlciMCD7PIfOutUCPkts
         Counter64,
      pr1646v2ATMFwPerFrDlciMCD7PIfOutNUCPkts
         Counter64,
      pr1646v2ATMFwPerFrDlciMCD7PIfOutBCPkts
         Counter64,
      pr1646v2ATMFwPerFrDlciMCD7PIfOutMCPkts
         Counter64,
      pr1646v2ATMFwPerFrDlciMCD7PIfOutDiscards
         Counter64,
      pr1646v2ATMFwPerFrDlciMCD7PIfOutErrors
         Counter64,
      pr1646v2ATMFwPerFrDlciMCD7POutDropEx
         Counter64,
      pr1646v2ATMFwPerFrDlciMCD7POutDropNoArp
         Counter64,
      pr1646v2ATMFwPerFrDlciMCD7POutDropFilter
         Counter64,
      pr1646v2ATMFwPerFrDlciMCD7PIfOutBandwidth
         Integer32,
      pr1646v2ATMFwPerFrDlciMCD7PIfErrSec
         Counter32
      }

pr1646v2ATMFwPerFrDlciMCD7PGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciMCD7PEntry 10}

pr1646v2ATMFwPerFrDlciMCD7PTableIx OBJECT-TYPE
   SYNTAX      TableIndex
   MAX-ACCESS  not-accessible
   STATUS      current
   DESCRIPTION
      ""
   ::= {pr1646v2ATMFwPerFrDlciMCD7PEntry 11}

pr1646v2ATMFwPerFrDlciMCD7PSysUpTime OBJECT-TYPE
   SYNTAX      TimeTicks
   MAX-ACCESS  read-only
   STATUS      current
   DESCRIPTION
      "Path: atm.performance.pvcTable.frameRelay.dlciTable.mibCounters.d7Performance.sysUpTime

       Time in centi-second."
   ::= {pr1646v2ATMFwPerFrDlciMCD7PEntry 16777216}

pr1646v2ATMFwPerFrDlciMCD7PIfUpTime OBJECT-TYPE
   SYNTAX      TimeTicks
   MAX-ACCESS  read-only
   STATUS      current
   DESCRIPTION
      "Path: atm.performance.pvcTable.frameRelay.dlciTable.mibCounters.d7Performance.ifUpTime

       Time in centi-second."
   ::= {pr1646v2ATMFwPerFrDlciMCD7PEntry 33554432}

pr1646v2ATMFwPerFrDlciMCD7PIfStatChanges OBJECT-TYPE
   SYNTAX      Counter32
   MAX-ACCESS  read-only
   STATUS      current
   DESCRIPTION
      "Path: atm.performance.pvcTable.frameRelay.dlciTable.mibCounters.d7Performance.ifStatusChanges

       32 bit unsigned wrappable counter."
   ::= {pr1646v2ATMFwPerFrDlciMCD7PEntry 50331648}

pr1646v2ATMFwPerFrDlciMCD7PIfInOctets OBJECT-TYPE
   SYNTAX      Counter64
   MAX-ACCESS  read-only
   STATUS      current
   DESCRIPTION
      "Path: atm.performance.pvcTable.frameRelay.dlciTable.mibCounters.d7Performance.ifInOctets

       64 bit unsigned wrappable counter."
   ::= {pr1646v2ATMFwPerFrDlciMCD7PEntry 67108864}

pr1646v2ATMFwPerFrDlciMCD7PIfInUCPkts OBJECT-TYPE
   SYNTAX      Counter64
   MAX-ACCESS  read-only
   STATUS      current
   DESCRIPTION
      "Path: atm.performance.pvcTable.frameRelay.dlciTable.mibCounters.d7Performance.ifInUcastPkts

       64 bit unsigned wrappable counter."
   ::= {pr1646v2ATMFwPerFrDlciMCD7PEntry 83886080}

pr1646v2ATMFwPerFrDlciMCD7PIfInNUCPkts OBJECT-TYPE
   SYNTAX      Counter64
   MAX-ACCESS  read-only
   STATUS      current
   DESCRIPTION
      "Path: atm.performance.pvcTable.frameRelay.dlciTable.mibCounters.d7Performance.ifInNUcastPkts

       64 bit unsigned wrappable counter."
   ::= {pr1646v2ATMFwPerFrDlciMCD7PEntry 100663296}

pr1646v2ATMFwPerFrDlciMCD7PIfInBCPkts OBJECT-TYPE
   SYNTAX      Counter64
   MAX-ACCESS  read-only
   STATUS      current
   DESCRIPTION
      "Path: atm.performance.pvcTable.frameRelay.dlciTable.mibCounters.d7Performance.ifInBcastPkts

       64 bit unsigned wrappable counter."
   ::= {pr1646v2ATMFwPerFrDlciMCD7PEntry 419430400}

pr1646v2ATMFwPerFrDlciMCD7PIfInMCPkts OBJECT-TYPE
   SYNTAX      Counter64
   MAX-ACCESS  read-only
   STATUS      current
   DESCRIPTION
      "Path: atm.performance.pvcTable.frameRelay.dlciTable.mibCounters.d7Performance.ifInMcastPkts

       64 bit unsigned wrappable counter."
   ::= {pr1646v2ATMFwPerFrDlciMCD7PEntry 436207616}

pr1646v2ATMFwPerFrDlciMCD7PIfInDiscards OBJECT-TYPE
   SYNTAX      Counter64
   MAX-ACCESS  read-only
   STATUS      current
   DESCRIPTION
      "Path: atm.performance.pvcTable.frameRelay.dlciTable.mibCounters.d7Performance.ifInDiscards

       64 bit unsigned wrappable counter."
   ::= {pr1646v2ATMFwPerFrDlciMCD7PEntry 117440512}

pr1646v2ATMFwPerFrDlciMCD7PIfInErrors OBJECT-TYPE
   SYNTAX      Counter64
   MAX-ACCESS  read-only
   STATUS      current
   DESCRIPTION
      "Path: atm.performance.pvcTable.frameRelay.dlciTable.mibCounters.d7Performance.ifInErrors

       64 bit unsigned wrappable counter."
   ::= {pr1646v2ATMFwPerFrDlciMCD7PEntry 134217728}

pr1646v2ATMFwPerFrDlciMCD7PIfInUnkwn OBJECT-TYPE
   SYNTAX      Counter64
   MAX-ACCESS  read-only
   STATUS      current
   DESCRIPTION
      "Path: atm.performance.pvcTable.frameRelay.dlciTable.mibCounters.d7Performance.ifInUnknownProtos

       64 bit unsigned wrappable counter."
   ::= {pr1646v2ATMFwPerFrDlciMCD7PEntry 150994944}

pr1646v2ATMFwPerFrDlciMCD7PInDropEx OBJECT-TYPE
   SYNTAX      Counter64
   MAX-ACCESS  read-only
   STATUS      current
   DESCRIPTION
      "Path: atm.performance.pvcTable.frameRelay.dlciTable.mibCounters.d7Performance.ifInDropLevelExceeded

       64 bit unsigned wrappable counter."
   ::= {pr1646v2ATMFwPerFrDlciMCD7PEntry 335544320}

pr1646v2ATMFwPerFrDlciMCD7PInDropNoMac OBJECT-TYPE
   SYNTAX      Counter64
   MAX-ACCESS  read-only
   STATUS      current
   DESCRIPTION
      "Path: atm.performance.pvcTable.frameRelay.dlciTable.mibCounters.d7Performance.fInDiscardsNoMacFit

       64 bit unsigned wrappable counter."
   ::= {pr1646v2ATMFwPerFrDlciMCD7PEntry 301989888}

pr1646v2ATMFwPerFrDlciMCD7PInDropNUCast OBJECT-TYPE
   SYNTAX      Counter64
   MAX-ACCESS  read-only
   STATUS      current
   DESCRIPTION
      "Path: atm.performance.pvcTable.frameRelay.dlciTable.mibCounters.d7Performance.fInDiscardsNUCast

       64 bit unsigned wrappable counter."
   ::= {pr1646v2ATMFwPerFrDlciMCD7PEntry 318767104}

pr1646v2ATMFwPerFrDlciMCD7PInDropFilter OBJECT-TYPE
   SYNTAX      Counter64
   MAX-ACCESS  read-only
   STATUS      current
   DESCRIPTION
      "Path: atm.performance.pvcTable.frameRelay.dlciTable.mibCounters.d7Performance.fInDiscardsFilter

       64 bit unsigned wrappable counter."
   ::= {pr1646v2ATMFwPerFrDlciMCD7PEntry 385875968}

pr1646v2ATMFwPerFrDlciMCD7PIfInBandwidth OBJECT-TYPE
   SYNTAX      Integer32
   MAX-ACCESS  read-only
   STATUS      current
   DESCRIPTION
      "Path: atm.performance.pvcTable.frameRelay.dlciTable.mibCounters.d7Performance.ifInBandwidth

       unit name = bps
       formula = 8 * ; 8 /"
   ::= {pr1646v2ATMFwPerFrDlciMCD7PEntry 268435456}

pr1646v2ATMFwPerFrDlciMCD7PIfOutOctets OBJECT-TYPE
   SYNTAX      Counter64
   MAX-ACCESS  read-only
   STATUS      current
   DESCRIPTION
      "Path: atm.performance.pvcTable.frameRelay.dlciTable.mibCounters.d7Performance.ifOutOctets

       64 bit unsigned wrappable counter."
   ::= {pr1646v2ATMFwPerFrDlciMCD7PEntry 167772160}

pr1646v2ATMFwPerFrDlciMCD7PIfOutUCPkts OBJECT-TYPE
   SYNTAX      Counter64
   MAX-ACCESS  read-only
   STATUS      current
   DESCRIPTION
      "Path: atm.performance.pvcTable.frameRelay.dlciTable.mibCounters.d7Performance.ifOutUcastPkts

       64 bit unsigned wrappable counter."
   ::= {pr1646v2ATMFwPerFrDlciMCD7PEntry 184549376}

pr1646v2ATMFwPerFrDlciMCD7PIfOutNUCPkts OBJECT-TYPE
   SYNTAX      Counter64
   MAX-ACCESS  read-only
   STATUS      current
   DESCRIPTION
      "Path: atm.performance.pvcTable.frameRelay.dlciTable.mibCounters.d7Performance.ifOutNUcastPkts

       64 bit unsigned wrappable counter."
   ::= {pr1646v2ATMFwPerFrDlciMCD7PEntry 201326592}

pr1646v2ATMFwPerFrDlciMCD7PIfOutBCPkts OBJECT-TYPE
   SYNTAX      Counter64
   MAX-ACCESS  read-only
   STATUS      current
   DESCRIPTION
      "Path: atm.performance.pvcTable.frameRelay.dlciTable.mibCounters.d7Performance.ifOutBcastPkts

       64 bit unsigned wrappable counter."
   ::= {pr1646v2ATMFwPerFrDlciMCD7PEntry 452984832}

pr1646v2ATMFwPerFrDlciMCD7PIfOutMCPkts OBJECT-TYPE
   SYNTAX      Counter64
   MAX-ACCESS  read-only
   STATUS      current
   DESCRIPTION
      "Path: atm.performance.pvcTable.frameRelay.dlciTable.mibCounters.d7Performance.ifOutMcastPkts

       64 bit unsigned wrappable counter."
   ::= {pr1646v2ATMFwPerFrDlciMCD7PEntry 469762048}

pr1646v2ATMFwPerFrDlciMCD7PIfOutDiscards OBJECT-TYPE
   SYNTAX      Counter64
   MAX-ACCESS  read-only
   STATUS      current
   DESCRIPTION
      "Path: atm.performance.pvcTable.frameRelay.dlciTable.mibCounters.d7Performance.ifOutDiscards

       64 bit unsigned wrappable counter."
   ::= {pr1646v2ATMFwPerFrDlciMCD7PEntry 218103808}

pr1646v2ATMFwPerFrDlciMCD7PIfOutErrors OBJECT-TYPE
   SYNTAX      Counter64
   MAX-ACCESS  read-only
   STATUS      current
   DESCRIPTION
      "Path: atm.performance.pvcTable.frameRelay.dlciTable.mibCounters.d7Performance.ifOutErrors

       64 bit unsigned wrappable counter."
   ::= {pr1646v2ATMFwPerFrDlciMCD7PEntry 234881024}

pr1646v2ATMFwPerFrDlciMCD7POutDropEx OBJECT-TYPE
   SYNTAX      Counter64
   MAX-ACCESS  read-only
   STATUS      current
   DESCRIPTION
      "Path: atm.performance.pvcTable.frameRelay.dlciTable.mibCounters.d7Performance.ifOutDropLevelExceeded

       64 bit unsigned wrappable counter."
   ::= {pr1646v2ATMFwPerFrDlciMCD7PEntry 352321536}

pr1646v2ATMFwPerFrDlciMCD7POutDropNoArp OBJECT-TYPE
   SYNTAX      Counter64
   MAX-ACCESS  read-only
   STATUS      current
   DESCRIPTION
      "Path: atm.performance.pvcTable.frameRelay.dlciTable.mibCounters.d7Performance.ifOutDiscardsNoArp

       64 bit unsigned wrappable counter."
   ::= {pr1646v2ATMFwPerFrDlciMCD7PEntry 369098752}

pr1646v2ATMFwPerFrDlciMCD7POutDropFilter OBJECT-TYPE
   SYNTAX      Counter64
   MAX-ACCESS  read-only
   STATUS      current
   DESCRIPTION
      "Path: atm.performance.pvcTable.frameRelay.dlciTable.mibCounters.d7Performance.ifOutDiscardsFilter

       64 bit unsigned wrappable counter."
   ::= {pr1646v2ATMFwPerFrDlciMCD7PEntry 402653184}

pr1646v2ATMFwPerFrDlciMCD7PIfOutBandwidth OBJECT-TYPE
   SYNTAX      Integer32
   MAX-ACCESS  read-only
   STATUS      current
   DESCRIPTION
      "Path: atm.performance.pvcTable.frameRelay.dlciTable.mibCounters.d7Performance.ifOutBandwidth

       unit name = bps
       formula = 8 * ; 8 /"
   ::= {pr1646v2ATMFwPerFrDlciMCD7PEntry 285212672}

pr1646v2ATMFwPerFrDlciMCD7PIfErrSec OBJECT-TYPE
   SYNTAX      Counter32
   MAX-ACCESS  read-only
   STATUS      current
   DESCRIPTION
      "Path: atm.performance.pvcTable.frameRelay.dlciTable.mibCounters.d7Performance.ifErrSec

       32 bit unsigned wrappable counter."
   ::= {pr1646v2ATMFwPerFrDlciMCD7PEntry 251658240}

pr1646v2ATMFwPerFrDlciInPQs OBJECT-TYPE
   SYNTAX      SEQUENCE OF Pr1646v2ATMFwPerFrDlciInPQsEntry
   MAX-ACCESS  not-accessible
   STATUS      current
   DESCRIPTION
      ""
   ::= {pr1646v2ATMFwPer 503449088}

pr1646v2ATMFwPerFrDlciInPQsEntry OBJECT-TYPE
   SYNTAX      Pr1646v2ATMFwPerFrDlciInPQsEntry
   MAX-ACCESS  not-accessible
   STATUS      current
   DESCRIPTION
      ""
   INDEX      { pr1646v2ATMFwPerFrDlciInPQsGlobalIx,
                pr1646v2ATMFwPerTableIx,
                pr1646v2ATMFwPerFrDlciTableIx,
                pr1646v2ATMFwPerFrDlciInPQsTableIx }
   ::= {pr1646v2ATMFwPerFrDlciInPQs 1}

Pr1646v2ATMFwPerFrDlciInPQsEntry ::=
   SEQUENCE
      {
      pr1646v2ATMFwPerFrDlciInPQsGlobalIx
         GlobalIndex,
      pr1646v2ATMFwPerFrDlciInPQsTableIx
         TableIndex,
      pr1646v2ATMFwPerFrDlciInPQsName
         INTEGER,
      pr1646v2ATMFwPerFrDlciInPQsLength
         Integer32,
      pr1646v2ATMFwPerFrDlciInPQsOctetLength
         Integer32,
      pr1646v2ATMFwPerFrDlciInPQsRedLength
         Integer32,
      pr1646v2ATMFwPerFrDlciInPQsPacketsTotal
         Counter64,
      pr1646v2ATMFwPerFrDlciInPQsPacketsDirectTx
         Counter64,
      pr1646v2ATMFwPerFrDlciInPQsPacketsQueued
         Counter64,
      pr1646v2ATMFwPerFrDlciInPQsPacketsDropped
         Counter64,
      pr1646v2ATMFwPerFrDlciInPQsPacketsRedDropped
         Counter64,
      pr1646v2ATMFwPerFrDlciInPQsPacketsCirTx
         Counter64,
      pr1646v2ATMFwPerFrDlciInPQsPacketsEirTx
         Counter64,
      pr1646v2ATMFwPerFrDlciInPQsPacketsViolateTx
         Counter64,
      pr1646v2ATMFwPerFrDlciInPQsOctetsTotal
         Counter64,
      pr1646v2ATMFwPerFrDlciInPQsOctetsDirectTx
         Counter64,
      pr1646v2ATMFwPerFrDlciInPQsOctetsQueued
         Counter64,
      pr1646v2ATMFwPerFrDlciInPQsOctetsDropped
         Counter64,
      pr1646v2ATMFwPerFrDlciInPQsOctetsRedDropped
         Counter64,
      pr1646v2ATMFwPerFrDlciInPQsOctetsCirTx
         Counter64,
      pr1646v2ATMFwPerFrDlciInPQsOctetsEirTx
         Counter64,
      pr1646v2ATMFwPerFrDlciInPQsOctetsViolateTx
         Counter64,
      pr1646v2ATMFwPerFrDlciInPQsOctetsBandwidth15sec
         Integer32,
      pr1646v2ATMFwPerFrDlciInPQsOctetsBandwidth30sec
         Integer32,
      pr1646v2ATMFwPerFrDlciInPQsOctetsBandwidth1min
         Integer32,
      pr1646v2ATMFwPerFrDlciInPQsOctetsBandwidth2min
         Integer32,
      pr1646v2ATMFwPerFrDlciInPQsOctetsBandwidth5min
         Integer32
      }

pr1646v2ATMFwPerFrDlciInPQsGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciInPQsEntry 10}

pr1646v2ATMFwPerFrDlciInPQsTableIx OBJECT-TYPE
   SYNTAX      TableIndex
   MAX-ACCESS  not-accessible
   STATUS      current
   DESCRIPTION
      ""
   ::= {pr1646v2ATMFwPerFrDlciInPQsEntry 11}

pr1646v2ATMFwPerFrDlciInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.frameRelay.dlciTable.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2ATMFwPerFrDlciInPQsEntry 16777216}

pr1646v2ATMFwPerFrDlciInPQsLength OBJECT-TYPE
   SYNTAX      Integer32
   MAX-ACCESS  read-only
   STATUS      current
   DESCRIPTION
      "Path: atm.performance.pvcTable.frameRelay.dlciTable.inPriorityQueues.length"
   ::= {pr1646v2ATMFwPerFrDlciInPQsEntry 33554432}

pr1646v2ATMFwPerFrDlciInPQsOctetLength OBJECT-TYPE
   SYNTAX      Integer32
   MAX-ACCESS  read-only
   STATUS      current
   DESCRIPTION
      "Path: atm.performance.pvcTable.frameRelay.dlciTable.inPriorityQueues.octetLength"
   ::= {pr1646v2ATMFwPerFrDlciInPQsEntry 150994944}

pr1646v2ATMFwPerFrDlciInPQsRedLength OBJECT-TYPE
   SYNTAX      Integer32
   MAX-ACCESS  read-only
   STATUS      current
   DESCRIPTION
      "Path: atm.performance.pvcTable.frameRelay.dlciTable.inPriorityQueues.redLength"
   ::= {pr1646v2ATMFwPerFrDlciInPQsEntry 134217728}

pr1646v2ATMFwPerFrDlciInPQsPacketsTotal OBJECT-TYPE
   SYNTAX      Counter64
   MAX-ACCESS  read-only
   STATUS      current
   DESCRIPTION
      "Path: atm.performance.pvcTable.frameRelay.dlciTable.inPriorityQueues.packets.total

       64 bit unsigned wrappable counter."
   ::= {pr1646v2ATMFwPerFrDlciInPQsEntry 50790400}

pr1646v2ATMFwPerFrDlciInPQsPacketsDirectTx OBJECT-TYPE
   SYNTAX      Counter64
   MAX-ACCESS  read-only
   STATUS      current
   DESCRIPTION
      "Path: atm.performance.pvcTable.frameRelay.dlciTable.inPriorityQueues.packets.directTx

       64 bit unsigned wrappable counter."
   ::= {pr1646v2ATMFwPerFrDlciInPQsEntry 50397184}

pr1646v2ATMFwPerFrDlciInPQsPacketsQueued OBJECT-TYPE
   SYNTAX      Counter64
   MAX-ACCESS  read-only
   STATUS      current
   DESCRIPTION
      "Path: atm.performance.pvcTable.frameRelay.dlciTable.inPriorityQueues.packets.queued

       64 bit unsigned wrappable counter."
   ::= {pr1646v2ATMFwPerFrDlciInPQsEntry 50462720}

pr1646v2ATMFwPerFrDlciInPQsPacketsDropped OBJECT-TYPE
   SYNTAX      Counter64
   MAX-ACCESS  read-only
   STATUS      current
   DESCRIPTION
      "Path: atm.performance.pvcTable.frameRelay.dlciTable.inPriorityQueues.packets.dropped

       64 bit unsigned wrappable counter."
   ::= {pr1646v2ATMFwPerFrDlciInPQsEntry 50528256}

pr1646v2ATMFwPerFrDlciInPQsPacketsRedDropped OBJECT-TYPE
   SYNTAX      Counter64
   MAX-ACCESS  read-only
   STATUS      current
   DESCRIPTION
      "Path: atm.performance.pvcTable.frameRelay.dlciTable.inPriorityQueues.packets.redDropped

       64 bit unsigned wrappable counter."
   ::= {pr1646v2ATMFwPerFrDlciInPQsEntry 50724864}

pr1646v2ATMFwPerFrDlciInPQsPacketsCirTx OBJECT-TYPE
   SYNTAX      Counter64
   MAX-ACCESS  read-only
   STATUS      current
   DESCRIPTION
      "Path: atm.performance.pvcTable.frameRelay.dlciTable.inPriorityQueues.packets.cirTx

       64 bit unsigned wrappable counter."
   ::= {pr1646v2ATMFwPerFrDlciInPQsEntry 50593792}

pr1646v2ATMFwPerFrDlciInPQsPacketsEirTx OBJECT-TYPE
   SYNTAX      Counter64
   MAX-ACCESS  read-only
   STATUS      current
   DESCRIPTION
      "Path: atm.performance.pvcTable.frameRelay.dlciTable.inPriorityQueues.packets.eirTx

       64 bit unsigned wrappable counter."
   ::= {pr1646v2ATMFwPerFrDlciInPQsEntry 50659328}

pr1646v2ATMFwPerFrDlciInPQsPacketsViolateTx OBJECT-TYPE
   SYNTAX      Counter64
   MAX-ACCESS  read-only
   STATUS      current
   DESCRIPTION
      "Path: atm.performance.pvcTable.frameRelay.dlciTable.inPriorityQueues.packets.violateTx

       64 bit unsigned wrappable counter."
   ::= {pr1646v2ATMFwPerFrDlciInPQsEntry 50855936}

pr1646v2ATMFwPerFrDlciInPQsOctetsTotal OBJECT-TYPE
   SYNTAX      Counter64
   MAX-ACCESS  read-only
   STATUS      current
   DESCRIPTION
      "Path: atm.performance.pvcTable.frameRelay.dlciTable.inPriorityQueues.octets.total

       64 bit unsigned wrappable counter."
   ::= {pr1646v2ATMFwPerFrDlciInPQsEntry 67567616}

pr1646v2ATMFwPerFrDlciInPQsOctetsDirectTx OBJECT-TYPE
   SYNTAX      Counter64
   MAX-ACCESS  read-only
   STATUS      current
   DESCRIPTION
      "Path: atm.performance.pvcTable.frameRelay.dlciTable.inPriorityQueues.octets.directTx

       64 bit unsigned wrappable counter."
   ::= {pr1646v2ATMFwPerFrDlciInPQsEntry 67174400}

pr1646v2ATMFwPerFrDlciInPQsOctetsQueued OBJECT-TYPE
   SYNTAX      Counter64
   MAX-ACCESS  read-only
   STATUS      current
   DESCRIPTION
      "Path: atm.performance.pvcTable.frameRelay.dlciTable.inPriorityQueues.octets.queued

       64 bit unsigned wrappable counter."
   ::= {pr1646v2ATMFwPerFrDlciInPQsEntry 67239936}

pr1646v2ATMFwPerFrDlciInPQsOctetsDropped OBJECT-TYPE
   SYNTAX      Counter64
   MAX-ACCESS  read-only
   STATUS      current
   DESCRIPTION
      "Path: atm.performance.pvcTable.frameRelay.dlciTable.inPriorityQueues.octets.dropped

       64 bit unsigned wrappable counter."
   ::= {pr1646v2ATMFwPerFrDlciInPQsEntry 67305472}

pr1646v2ATMFwPerFrDlciInPQsOctetsRedDropped OBJECT-TYPE
   SYNTAX      Counter64
   MAX-ACCESS  read-only
   STATUS      current
   DESCRIPTION
      "Path: atm.performance.pvcTable.frameRelay.dlciTable.inPriorityQueues.octets.redDropped

       64 bit unsigned wrappable counter."
   ::= {pr1646v2ATMFwPerFrDlciInPQsEntry 67502080}

pr1646v2ATMFwPerFrDlciInPQsOctetsCirTx OBJECT-TYPE
   SYNTAX      Counter64
   MAX-ACCESS  read-only
   STATUS      current
   DESCRIPTION
      "Path: atm.performance.pvcTable.frameRelay.dlciTable.inPriorityQueues.octets.cirTx

       64 bit unsigned wrappable counter."
   ::= {pr1646v2ATMFwPerFrDlciInPQsEntry 67371008}

pr1646v2ATMFwPerFrDlciInPQsOctetsEirTx OBJECT-TYPE
   SYNTAX      Counter64
   MAX-ACCESS  read-only
   STATUS      current
   DESCRIPTION
      "Path: atm.performance.pvcTable.frameRelay.dlciTable.inPriorityQueues.octets.eirTx

       64 bit unsigned wrappable counter."
   ::= {pr1646v2ATMFwPerFrDlciInPQsEntry 67436544}

pr1646v2ATMFwPerFrDlciInPQsOctetsViolateTx OBJECT-TYPE
   SYNTAX      Counter64
   MAX-ACCESS  read-only
   STATUS      current
   DESCRIPTION
      "Path: atm.performance.pvcTable.frameRelay.dlciTable.inPriorityQueues.octets.violateTx

       64 bit unsigned wrappable counter."
   ::= {pr1646v2ATMFwPerFrDlciInPQsEntry 67633152}

pr1646v2ATMFwPerFrDlciInPQsOctetsBandwidth15sec OBJECT-TYPE
   SYNTAX      Integer32
   MAX-ACCESS  read-only
   STATUS      current
   DESCRIPTION
      "Path: atm.performance.pvcTable.frameRelay.dlciTable.inPriorityQueues.octets.bandwidth.15sec

       unit name = bps
       formula = 8 * ; 8 /"
   ::= {pr1646v2ATMFwPerFrDlciInPQsEntry 70386944}

pr1646v2ATMFwPerFrDlciInPQsOctetsBandwidth30sec OBJECT-TYPE
   SYNTAX      Integer32
   MAX-ACCESS  read-only
   STATUS      current
   DESCRIPTION
      "Path: atm.performance.pvcTable.frameRelay.dlciTable.inPriorityQueues.octets.bandwidth.30sec

       unit name = bps
       formula = 8 * ; 8 /"
   ::= {pr1646v2ATMFwPerFrDlciInPQsEntry 70388224}

pr1646v2ATMFwPerFrDlciInPQsOctetsBandwidth1min OBJECT-TYPE
   SYNTAX      Integer32
   MAX-ACCESS  read-only
   STATUS      current
   DESCRIPTION
      "Path: atm.performance.pvcTable.frameRelay.dlciTable.inPriorityQueues.octets.bandwidth.1min

       unit name = bps
       formula = 8 * ; 8 /"
   ::= {pr1646v2ATMFwPerFrDlciInPQsEntry 70390784}

pr1646v2ATMFwPerFrDlciInPQsOctetsBandwidth2min OBJECT-TYPE
   SYNTAX      Integer32
   MAX-ACCESS  read-only
   STATUS      current
   DESCRIPTION
      "Path: atm.performance.pvcTable.frameRelay.dlciTable.inPriorityQueues.octets.bandwidth.2min

       unit name = bps
       formula = 8 * ; 8 /"
   ::= {pr1646v2ATMFwPerFrDlciInPQsEntry 70395904}

pr1646v2ATMFwPerFrDlciInPQsOctetsBandwidth5min OBJECT-TYPE
   SYNTAX      Integer32
   MAX-ACCESS  read-only
   STATUS      current
   DESCRIPTION
      "Path: atm.performance.pvcTable.frameRelay.dlciTable.inPriorityQueues.octets.bandwidth.5min

       unit name = bps
       formula = 8 * ; 8 /"
   ::= {pr1646v2ATMFwPerFrDlciInPQsEntry 70411264}

pr1646v2ATMFwPerFrDlciInPQsH2Performance OBJECT-TYPE
   SYNTAX      SEQUENCE OF Pr1646v2ATMFwPerFrDlciInPQsH2PerformanceEntry
   MAX-ACCESS  not-accessible
   STATUS      current
   DESCRIPTION
      ""
   ::= {pr1646v2ATMFwPer 503449093}

pr1646v2ATMFwPerFrDlciInPQsH2PerformanceEntry OBJECT-TYPE
   SYNTAX      Pr1646v2ATMFwPerFrDlciInPQsH2PerformanceEntry
   MAX-ACCESS  not-accessible
   STATUS      current
   DESCRIPTION
      ""
   INDEX      { pr1646v2ATMFwPerFrDlciInPQsH2PerformanceGlobalIx,
                pr1646v2ATMFwPerTableIx,
                pr1646v2ATMFwPerFrDlciTableIx,
                pr1646v2ATMFwPerFrDlciInPQsTableIx,
                pr1646v2ATMFwPerFrDlciInPQsH2PerformanceTableIx }
   ::= {pr1646v2ATMFwPerFrDlciInPQsH2Performance 1}

Pr1646v2ATMFwPerFrDlciInPQsH2PerformanceEntry ::=
   SEQUENCE
      {
      pr1646v2ATMFwPerFrDlciInPQsH2PerformanceGlobalIx
         GlobalIndex,
      pr1646v2ATMFwPerFrDlciInPQsH2PerformanceTableIx
         TableIndex,
      pr1646v2ATMFwPerFrDlciInPQsH2PerformanceSysUpTime
         TimeTicks,
      pr1646v2ATMFwPerFrDlciInPQsH2PerformanceTotPkts
         Counter64,
      pr1646v2ATMFwPerFrDlciInPQsH2PerformanceDirTxPkts
         Counter64,
      pr1646v2ATMFwPerFrDlciInPQsH2PerformanceQdPkts
         Counter64,
      pr1646v2ATMFwPerFrDlciInPQsH2PerformanceDropPkts
         Counter64,
      pr1646v2ATMFwPerFrDlciInPQsH2PerformanceRDropPkts
         Counter64,
      pr1646v2ATMFwPerFrDlciInPQsH2PerformanceCirTxPkts
         Counter64,
      pr1646v2ATMFwPerFrDlciInPQsH2PerformanceEirTxPkts
         Counter64,
      pr1646v2ATMFwPerFrDlciInPQsH2PerformanceViolTxPkts
         Counter64,
      pr1646v2ATMFwPerFrDlciInPQsH2PerformanceTotOcts
         Counter64,
      pr1646v2ATMFwPerFrDlciInPQsH2PerformanceDirTxOcts
         Counter64,
      pr1646v2ATMFwPerFrDlciInPQsH2PerformanceQdOcts
         Counter64,
      pr1646v2ATMFwPerFrDlciInPQsH2PerformanceDropOcts
         Counter64,
      pr1646v2ATMFwPerFrDlciInPQsH2PerformanceRDropOcts
         Counter64,
      pr1646v2ATMFwPerFrDlciInPQsH2PerformanceCirTxOcts
         Counter64,
      pr1646v2ATMFwPerFrDlciInPQsH2PerformanceEirTxOcts
         Counter64,
      pr1646v2ATMFwPerFrDlciInPQsH2PerformanceViolTxOcts
         Counter64,
      pr1646v2ATMFwPerFrDlciInPQsH2PerformanceBandwidth
         Integer32
      }

pr1646v2ATMFwPerFrDlciInPQsH2PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciInPQsH2PerformanceEntry 10}

pr1646v2ATMFwPerFrDlciInPQsH2PerformanceTableIx OBJECT-TYPE
   SYNTAX      TableIndex
   MAX-ACCESS  not-accessible
   STATUS      current
   DESCRIPTION
      ""
   ::= {pr1646v2ATMFwPerFrDlciInPQsH2PerformanceEntry 11}

pr1646v2ATMFwPerFrDlciInPQsH2PerformanceSysUpTime OBJECT-TYPE
   SYNTAX      TimeTicks
   MAX-ACCESS  read-only
   STATUS      current
   DESCRIPTION
      "Path: atm.performance.pvcTable.frameRelay.dlciTable.inPriorityQueues.h2Performance.sysUpTime

       Time in centi-second."
   ::= {pr1646v2ATMFwPerFrDlciInPQsH2PerformanceEntry 16777216}

pr1646v2ATMFwPerFrDlciInPQsH2PerformanceTotPkts OBJECT-TYPE
   SYNTAX      Counter64
   MAX-ACCESS  read-only
   STATUS      current
   DESCRIPTION
      "Path: atm.performance.pvcTable.frameRelay.dlciTable.inPriorityQueues.h2Performance.totalPkts

       64 bit unsigned wrappable counter."
   ::= {pr1646v2ATMFwPerFrDlciInPQsH2PerformanceEntry 234881024}

pr1646v2ATMFwPerFrDlciInPQsH2PerformanceDirTxPkts OBJECT-TYPE
   SYNTAX      Counter64
   MAX-ACCESS  read-only
   STATUS      current
   DESCRIPTION
      "Path: atm.performance.pvcTable.frameRelay.dlciTable.inPriorityQueues.h2Performance.directTxPkts

       64 bit unsigned wrappable counter."
   ::= {pr1646v2ATMFwPerFrDlciInPQsH2PerformanceEntry 33554432}

pr1646v2ATMFwPerFrDlciInPQsH2PerformanceQdPkts OBJECT-TYPE
   SYNTAX      Counter64
   MAX-ACCESS  read-only
   STATUS      current
   DESCRIPTION
      "Path: atm.performance.pvcTable.frameRelay.dlciTable.inPriorityQueues.h2Performance.queuedPkts

       64 bit unsigned wrappable counter."
   ::= {pr1646v2ATMFwPerFrDlciInPQsH2PerformanceEntry 50331648}

pr1646v2ATMFwPerFrDlciInPQsH2PerformanceDropPkts OBJECT-TYPE
   SYNTAX      Counter64
   MAX-ACCESS  read-only
   STATUS      current
   DESCRIPTION
      "Path: atm.performance.pvcTable.frameRelay.dlciTable.inPriorityQueues.h2Performance.droppedPkts

       64 bit unsigned wrappable counter."
   ::= {pr1646v2ATMFwPerFrDlciInPQsH2PerformanceEntry 67108864}

pr1646v2ATMFwPerFrDlciInPQsH2PerformanceRDropPkts OBJECT-TYPE
   SYNTAX      Counter64
   MAX-ACCESS  read-only
   STATUS      current
   DESCRIPTION
      "Path: atm.performance.pvcTable.frameRelay.dlciTable.inPriorityQueues.h2Performance.redDroppedPkts

       64 bit unsigned wrappable counter."
   ::= {pr1646v2ATMFwPerFrDlciInPQsH2PerformanceEntry 201326592}

pr1646v2ATMFwPerFrDlciInPQsH2PerformanceCirTxPkts OBJECT-TYPE
   SYNTAX      Counter64
   MAX-ACCESS  read-only
   STATUS      current
   DESCRIPTION
      "Path: atm.performance.pvcTable.frameRelay.dlciTable.inPriorityQueues.h2Performance.cirTxPkts

       64 bit unsigned wrappable counter."
   ::= {pr1646v2ATMFwPerFrDlciInPQsH2PerformanceEntry 83886080}

pr1646v2ATMFwPerFrDlciInPQsH2PerformanceEirTxPkts OBJECT-TYPE
   SYNTAX      Counter64
   MAX-ACCESS  read-only
   STATUS      current
   DESCRIPTION
      "Path: atm.performance.pvcTable.frameRelay.dlciTable.inPriorityQueues.h2Performance.eirTxPkts

       64 bit unsigned wrappable counter."
   ::= {pr1646v2ATMFwPerFrDlciInPQsH2PerformanceEntry 100663296}

pr1646v2ATMFwPerFrDlciInPQsH2PerformanceViolTxPkts OBJECT-TYPE
   SYNTAX      Counter64
   MAX-ACCESS  read-only
   STATUS      current
   DESCRIPTION
      "Path: atm.performance.pvcTable.frameRelay.dlciTable.inPriorityQueues.h2Performance.violateTxPkts

       64 bit unsigned wrappable counter."
   ::= {pr1646v2ATMFwPerFrDlciInPQsH2PerformanceEntry 301989888}

pr1646v2ATMFwPerFrDlciInPQsH2PerformanceTotOcts OBJECT-TYPE
   SYNTAX      Counter64
   MAX-ACCESS  read-only
   STATUS      current
   DESCRIPTION
      "Path: atm.performance.pvcTable.frameRelay.dlciTable.inPriorityQueues.h2Performance.totalOctets

       64 bit unsigned wrappable counter."
   ::= {pr1646v2ATMFwPerFrDlciInPQsH2PerformanceEntry 251658240}

pr1646v2ATMFwPerFrDlciInPQsH2PerformanceDirTxOcts OBJECT-TYPE
   SYNTAX      Counter64
   MAX-ACCESS  read-only
   STATUS      current
   DESCRIPTION
      "Path: atm.performance.pvcTable.frameRelay.dlciTable.inPriorityQueues.h2Performance.directTxOctets

       64 bit unsigned wrappable counter."
   ::= {pr1646v2ATMFwPerFrDlciInPQsH2PerformanceEntry 117440512}

pr1646v2ATMFwPerFrDlciInPQsH2PerformanceQdOcts OBJECT-TYPE
   SYNTAX      Counter64
   MAX-ACCESS  read-only
   STATUS      current
   DESCRIPTION
      "Path: atm.performance.pvcTable.frameRelay.dlciTable.inPriorityQueues.h2Performance.queuedOctets

       64 bit unsigned wrappable counter."
   ::= {pr1646v2ATMFwPerFrDlciInPQsH2PerformanceEntry 134217728}

pr1646v2ATMFwPerFrDlciInPQsH2PerformanceDropOcts OBJECT-TYPE
   SYNTAX      Counter64
   MAX-ACCESS  read-only
   STATUS      current
   DESCRIPTION
      "Path: atm.performance.pvcTable.frameRelay.dlciTable.inPriorityQueues.h2Performance.droppedOctets

       64 bit unsigned wrappable counter."
   ::= {pr1646v2ATMFwPerFrDlciInPQsH2PerformanceEntry 150994944}

pr1646v2ATMFwPerFrDlciInPQsH2PerformanceRDropOcts OBJECT-TYPE
   SYNTAX      Counter64
   MAX-ACCESS  read-only
   STATUS      current
   DESCRIPTION
      "Path: atm.performance.pvcTable.frameRelay.dlciTable.inPriorityQueues.h2Performance.redDroppedOctets

       64 bit unsigned wrappable counter."
   ::= {pr1646v2ATMFwPerFrDlciInPQsH2PerformanceEntry 218103808}

pr1646v2ATMFwPerFrDlciInPQsH2PerformanceCirTxOcts OBJECT-TYPE
   SYNTAX      Counter64
   MAX-ACCESS  read-only
   STATUS      current
   DESCRIPTION
      "Path: atm.performance.pvcTable.frameRelay.dlciTable.inPriorityQueues.h2Performance.cirTxOctets

       64 bit unsigned wrappable counter."
   ::= {pr1646v2ATMFwPerFrDlciInPQsH2PerformanceEntry 167772160}

pr1646v2ATMFwPerFrDlciInPQsH2PerformanceEirTxOcts OBJECT-TYPE
   SYNTAX      Counter64
   MAX-ACCESS  read-only
   STATUS      current
   DESCRIPTION
      "Path: atm.performance.pvcTable.frameRelay.dlciTable.inPriorityQueues.h2Performance.eirTxOctets

       64 bit unsigned wrappable counter."
   ::= {pr1646v2ATMFwPerFrDlciInPQsH2PerformanceEntry 184549376}

pr1646v2ATMFwPerFrDlciInPQsH2PerformanceViolTxOcts OBJECT-TYPE
   SYNTAX      Counter64
   MAX-ACCESS  read-only
   STATUS      current
   DESCRIPTION
      "Path: atm.performance.pvcTable.frameRelay.dlciTable.inPriorityQueues.h2Performance.violateTxOctets

       64 bit unsigned wrappable counter."
   ::= {pr1646v2ATMFwPerFrDlciInPQsH2PerformanceEntry 318767104}

pr1646v2ATMFwPerFrDlciInPQsH2PerformanceBandwidth OBJECT-TYPE
   SYNTAX      Integer32
   MAX-ACCESS  read-only
   STATUS      current
   DESCRIPTION
      "Path: atm.performance.pvcTable.frameRelay.dlciTable.inPriorityQueues.h2Performance.bandwidth

       unit name = bps
       formula = 8 * ; 8 /"
   ::= {pr1646v2ATMFwPerFrDlciInPQsH2PerformanceEntry 268435456}

pr1646v2ATMFwPerFrDlciInPQsH24Performance OBJECT-TYPE
   SYNTAX      SEQUENCE OF Pr1646v2ATMFwPerFrDlciInPQsH24PerformanceEntry
   MAX-ACCESS  not-accessible
   STATUS      current
   DESCRIPTION
      ""
   ::= {pr1646v2ATMFwPer 503449094}

pr1646v2ATMFwPerFrDlciInPQsH24PerformanceEntry OBJECT-TYPE
   SYNTAX      Pr1646v2ATMFwPerFrDlciInPQsH24PerformanceEntry
   MAX-ACCESS  not-accessible
   STATUS      current
   DESCRIPTION
      ""
   INDEX      { pr1646v2ATMFwPerFrDlciInPQsH24PerformanceGlobalIx,
                pr1646v2ATMFwPerTableIx,
                pr1646v2ATMFwPerFrDlciTableIx,
                pr1646v2ATMFwPerFrDlciInPQsTableIx,
                pr1646v2ATMFwPerFrDlciInPQsH24PerformanceTableIx }
   ::= {pr1646v2ATMFwPerFrDlciInPQsH24Performance 1}

Pr1646v2ATMFwPerFrDlciInPQsH24PerformanceEntry ::=
   SEQUENCE
      {
      pr1646v2ATMFwPerFrDlciInPQsH24PerformanceGlobalIx
         GlobalIndex,
      pr1646v2ATMFwPerFrDlciInPQsH24PerformanceTableIx
         TableIndex,
      pr1646v2ATMFwPerFrDlciInPQsH24PerformanceSysUpTime
         TimeTicks,
      pr1646v2ATMFwPerFrDlciInPQsH24PerformanceTotPkts
         Counter64,
      pr1646v2ATMFwPerFrDlciInPQsH24PerformanceDirTxPkts
         Counter64,
      pr1646v2ATMFwPerFrDlciInPQsH24PerformanceQdPkts
         Counter64,
      pr1646v2ATMFwPerFrDlciInPQsH24PerformanceDropPkts
         Counter64,
      pr1646v2ATMFwPerFrDlciInPQsH24PerformanceRDropPkts
         Counter64,
      pr1646v2ATMFwPerFrDlciInPQsH24PerformanceCirTxPkts
         Counter64,
      pr1646v2ATMFwPerFrDlciInPQsH24PerformanceEirTxPkts
         Counter64,
      pr1646v2ATMFwPerFrDlciInPQsH24PerformanceViolTxPkts
         Counter64,
      pr1646v2ATMFwPerFrDlciInPQsH24PerformanceTotOcts
         Counter64,
      pr1646v2ATMFwPerFrDlciInPQsH24PerformanceDirTxOcts
         Counter64,
      pr1646v2ATMFwPerFrDlciInPQsH24PerformanceQdOcts
         Counter64,
      pr1646v2ATMFwPerFrDlciInPQsH24PerformanceDropOcts
         Counter64,
      pr1646v2ATMFwPerFrDlciInPQsH24PerformanceRDropOcts
         Counter64,
      pr1646v2ATMFwPerFrDlciInPQsH24PerformanceCirTxOcts
         Counter64,
      pr1646v2ATMFwPerFrDlciInPQsH24PerformanceEirTxOcts
         Counter64,
      pr1646v2ATMFwPerFrDlciInPQsH24PerformanceViolTxOcts
         Counter64,
      pr1646v2ATMFwPerFrDlciInPQsH24PerformanceBandwidth
         Integer32
      }

pr1646v2ATMFwPerFrDlciInPQsH24PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciInPQsH24PerformanceEntry 10}

pr1646v2ATMFwPerFrDlciInPQsH24PerformanceTableIx OBJECT-TYPE
   SYNTAX      TableIndex
   MAX-ACCESS  not-accessible
   STATUS      current
   DESCRIPTION
      ""
   ::= {pr1646v2ATMFwPerFrDlciInPQsH24PerformanceEntry 11}

pr1646v2ATMFwPerFrDlciInPQsH24PerformanceSysUpTime OBJECT-TYPE
   SYNTAX      TimeTicks
   MAX-ACCESS  read-only
   STATUS      current
   DESCRIPTION
      "Path: atm.performance.pvcTable.frameRelay.dlciTable.inPriorityQueues.h24Performance.sysUpTime

       Time in centi-second."
   ::= {pr1646v2ATMFwPerFrDlciInPQsH24PerformanceEntry 16777216}

pr1646v2ATMFwPerFrDlciInPQsH24PerformanceTotPkts OBJECT-TYPE
   SYNTAX      Counter64
   MAX-ACCESS  read-only
   STATUS      current
   DESCRIPTION
      "Path: atm.performance.pvcTable.frameRelay.dlciTable.inPriorityQueues.h24Performance.totalPkts

       64 bit unsigned wrappable counter."
   ::= {pr1646v2ATMFwPerFrDlciInPQsH24PerformanceEntry 234881024}

pr1646v2ATMFwPerFrDlciInPQsH24PerformanceDirTxPkts OBJECT-TYPE
   SYNTAX      Counter64
   MAX-ACCESS  read-only
   STATUS      current
   DESCRIPTION
      "Path: atm.performance.pvcTable.frameRelay.dlciTable.inPriorityQueues.h24Performance.directTxPkts

       64 bit unsigned wrappable counter."
   ::= {pr1646v2ATMFwPerFrDlciInPQsH24PerformanceEntry 33554432}

pr1646v2ATMFwPerFrDlciInPQsH24PerformanceQdPkts OBJECT-TYPE
   SYNTAX      Counter64
   MAX-ACCESS  read-only
   STATUS      current
   DESCRIPTION
      "Path: atm.performance.pvcTable.frameRelay.dlciTable.inPriorityQueues.h24Performance.queuedPkts

       64 bit unsigned wrappable counter."
   ::= {pr1646v2ATMFwPerFrDlciInPQsH24PerformanceEntry 50331648}

pr1646v2ATMFwPerFrDlciInPQsH24PerformanceDropPkts OBJECT-TYPE
   SYNTAX      Counter64
   MAX-ACCESS  read-only
   STATUS      current
   DESCRIPTION
      "Path: atm.performance.pvcTable.frameRelay.dlciTable.inPriorityQueues.h24Performance.droppedPkts

       64 bit unsigned wrappable counter."
   ::= {pr1646v2ATMFwPerFrDlciInPQsH24PerformanceEntry 67108864}

pr1646v2ATMFwPerFrDlciInPQsH24PerformanceRDropPkts OBJECT-TYPE
   SYNTAX      Counter64
   MAX-ACCESS  read-only
   STATUS      current
   DESCRIPTION
      "Path: atm.performance.pvcTable.frameRelay.dlciTable.inPriorityQueues.h24Performance.redDroppedPkts

       64 bit unsigned wrappable counter."
   ::= {pr1646v2ATMFwPerFrDlciInPQsH24PerformanceEntry 201326592}

pr1646v2ATMFwPerFrDlciInPQsH24PerformanceCirTxPkts OBJECT-TYPE
   SYNTAX      Counter64
   MAX-ACCESS  read-only
   STATUS      current
   DESCRIPTION
      "Path: atm.performance.pvcTable.frameRelay.dlciTable.inPriorityQueues.h24Performance.cirTxPkts

       64 bit unsigned wrappable counter."
   ::= {pr1646v2ATMFwPerFrDlciInPQsH24PerformanceEntry 83886080}

pr1646v2ATMFwPerFrDlciInPQsH24PerformanceEirTxPkts OBJECT-TYPE
   SYNTAX      Counter64
   MAX-ACCESS  read-only
   STATUS      current
   DESCRIPTION
      "Path: atm.performance.pvcTable.frameRelay.dlciTable.inPriorityQueues.h24Performance.eirTxPkts

       64 bit unsigned wrappable counter."
   ::= {pr1646v2ATMFwPerFrDlciInPQsH24PerformanceEntry 100663296}

pr1646v2ATMFwPerFrDlciInPQsH24PerformanceViolTxPkts OBJECT-TYPE
   SYNTAX      Counter64
   MAX-ACCESS  read-only
   STATUS      current
   DESCRIPTION
      "Path: atm.performance.pvcTable.frameRelay.dlciTable.inPriorityQueues.h24Performance.violateTxPkts

       64 bit unsigned wrappable counter."
   ::= {pr1646v2ATMFwPerFrDlciInPQsH24PerformanceEntry 301989888}

pr1646v2ATMFwPerFrDlciInPQsH24PerformanceTotOcts OBJECT-TYPE
   SYNTAX      Counter64
   MAX-ACCESS  read-only
   STATUS      current
   DESCRIPTION
      "Path: atm.performance.pvcTable.frameRelay.dlciTable.inPriorityQueues.h24Performance.totalOctets

       64 bit unsigned wrappable counter."
   ::= {pr1646v2ATMFwPerFrDlciInPQsH24PerformanceEntry 251658240}

pr1646v2ATMFwPerFrDlciInPQsH24PerformanceDirTxOcts OBJECT-TYPE
   SYNTAX      Counter64
   MAX-ACCESS  read-only
   STATUS      current
   DESCRIPTION
      "Path: atm.performance.pvcTable.frameRelay.dlciTable.inPriorityQueues.h24Performance.directTxOctets

       64 bit unsigned wrappable counter."
   ::= {pr1646v2ATMFwPerFrDlciInPQsH24PerformanceEntry 117440512}

pr1646v2ATMFwPerFrDlciInPQsH24PerformanceQdOcts OBJECT-TYPE
   SYNTAX      Counter64
   MAX-ACCESS  read-only
   STATUS      current
   DESCRIPTION
      "Path: atm.performance.pvcTable.frameRelay.dlciTable.inPriorityQueues.h24Performance.queuedOctets

       64 bit unsigned wrappable counter."
   ::= {pr1646v2ATMFwPerFrDlciInPQsH24PerformanceEntry 134217728}

pr1646v2ATMFwPerFrDlciInPQsH24PerformanceDropOcts OBJECT-TYPE
   SYNTAX      Counter64
   MAX-ACCESS  read-only
   STATUS      current
   DESCRIPTION
      "Path: atm.performance.pvcTable.frameRelay.dlciTable.inPriorityQueues.h24Performance.droppedOctets

       64 bit unsigned wrappable counter."
   ::= {pr1646v2ATMFwPerFrDlciInPQsH24PerformanceEntry 150994944}

pr1646v2ATMFwPerFrDlciInPQsH24PerformanceRDropOcts OBJECT-TYPE
   SYNTAX      Counter64
   MAX-ACCESS  read-only
   STATUS      current
   DESCRIPTION
      "Path: atm.performance.pvcTable.frameRelay.dlciTable.inPriorityQueues.h24Performance.redDroppedOctets

       64 bit unsigned wrappable counter."
   ::= {pr1646v2ATMFwPerFrDlciInPQsH24PerformanceEntry 218103808}

pr1646v2ATMFwPerFrDlciInPQsH24PerformanceCirTxOcts OBJECT-TYPE
   SYNTAX      Counter64
   MAX-ACCESS  read-only
   STATUS      current
   DESCRIPTION
      "Path: atm.performance.pvcTable.frameRelay.dlciTable.inPriorityQueues.h24Performance.cirTxOctets

       64 bit unsigned wrappable counter."
   ::= {pr1646v2ATMFwPerFrDlciInPQsH24PerformanceEntry 167772160}

pr1646v2ATMFwPerFrDlciInPQsH24PerformanceEirTxOcts OBJECT-TYPE
   SYNTAX      Counter64
   MAX-ACCESS  read-only
   STATUS      current
   DESCRIPTION
      "Path: atm.performance.pvcTable.frameRelay.dlciTable.inPriorityQueues.h24Performance.eirTxOctets

       64 bit unsigned wrappable counter."
   ::= {pr1646v2ATMFwPerFrDlciInPQsH24PerformanceEntry 184549376}

pr1646v2ATMFwPerFrDlciInPQsH24PerformanceViolTxOcts OBJECT-TYPE
   SYNTAX      Counter64
   MAX-ACCESS  read-only
   STATUS      current
   DESCRIPTION
      "Path: atm.performance.pvcTable.frameRelay.dlciTable.inPriorityQueues.h24Performance.violateTxOctets

       64 bit unsigned wrappable counter."
   ::= {pr1646v2ATMFwPerFrDlciInPQsH24PerformanceEntry 318767104}

pr1646v2ATMFwPerFrDlciInPQsH24PerformanceBandwidth OBJECT-TYPE
   SYNTAX      Integer32
   MAX-ACCESS  read-only
   STATUS      current
   DESCRIPTION
      "Path: atm.performance.pvcTable.frameRelay.dlciTable.inPriorityQueues.h24Performance.bandwidth

       unit name = bps
       formula = 8 * ; 8 /"
   ::= {pr1646v2ATMFwPerFrDlciInPQsH24PerformanceEntry 268435456}

pr1646v2ATMFwPerFrDlciInPQsD7Performance OBJECT-TYPE
   SYNTAX      SEQUENCE OF Pr1646v2ATMFwPerFrDlciInPQsD7PerformanceEntry
   MAX-ACCESS  not-accessible
   STATUS      current
   DESCRIPTION
      ""
   ::= {pr1646v2ATMFwPer 503449095}

pr1646v2ATMFwPerFrDlciInPQsD7PerformanceEntry OBJECT-TYPE
   SYNTAX      Pr1646v2ATMFwPerFrDlciInPQsD7PerformanceEntry
   MAX-ACCESS  not-accessible
   STATUS      current
   DESCRIPTION
      ""
   INDEX      { pr1646v2ATMFwPerFrDlciInPQsD7PerformanceGlobalIx,
                pr1646v2ATMFwPerTableIx,
                pr1646v2ATMFwPerFrDlciTableIx,
                pr1646v2ATMFwPerFrDlciInPQsTableIx,
                pr1646v2ATMFwPerFrDlciInPQsD7PerformanceTableIx }
   ::= {pr1646v2ATMFwPerFrDlciInPQsD7Performance 1}

Pr1646v2ATMFwPerFrDlciInPQsD7PerformanceEntry ::=
   SEQUENCE
      {
      pr1646v2ATMFwPerFrDlciInPQsD7PerformanceGlobalIx
         GlobalIndex,
      pr1646v2ATMFwPerFrDlciInPQsD7PerformanceTableIx
         TableIndex,
      pr1646v2ATMFwPerFrDlciInPQsD7PerformanceSysUpTime
         TimeTicks,
      pr1646v2ATMFwPerFrDlciInPQsD7PerformanceTotPkts
         Counter64,
      pr1646v2ATMFwPerFrDlciInPQsD7PerformanceDirTxPkts
         Counter64,
      pr1646v2ATMFwPerFrDlciInPQsD7PerformanceQdPkts
         Counter64,
      pr1646v2ATMFwPerFrDlciInPQsD7PerformanceDropPkts
         Counter64,
      pr1646v2ATMFwPerFrDlciInPQsD7PerformanceRDropPkts
         Counter64,
      pr1646v2ATMFwPerFrDlciInPQsD7PerformanceCirTxPkts
         Counter64,
      pr1646v2ATMFwPerFrDlciInPQsD7PerformanceEirTxPkts
         Counter64,
      pr1646v2ATMFwPerFrDlciInPQsD7PerformanceViolTxPkts
         Counter64,
      pr1646v2ATMFwPerFrDlciInPQsD7PerformanceTotOcts
         Counter64,
      pr1646v2ATMFwPerFrDlciInPQsD7PerformanceDirTxOcts
         Counter64,
      pr1646v2ATMFwPerFrDlciInPQsD7PerformanceQdOcts
         Counter64,
      pr1646v2ATMFwPerFrDlciInPQsD7PerformanceDropOcts
         Counter64,
      pr1646v2ATMFwPerFrDlciInPQsD7PerformanceRDropOcts
         Counter64,
      pr1646v2ATMFwPerFrDlciInPQsD7PerformanceCirTxOcts
         Counter64,
      pr1646v2ATMFwPerFrDlciInPQsD7PerformanceEirTxOcts
         Counter64,
      pr1646v2ATMFwPerFrDlciInPQsD7PerformanceViolTxOcts
         Counter64,
      pr1646v2ATMFwPerFrDlciInPQsD7PerformanceBandwidth
         Integer32
      }

pr1646v2ATMFwPerFrDlciInPQsD7PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciInPQsD7PerformanceEntry 10}

pr1646v2ATMFwPerFrDlciInPQsD7PerformanceTableIx OBJECT-TYPE
   SYNTAX      TableIndex
   MAX-ACCESS  not-accessible
   STATUS      current
   DESCRIPTION
      ""
   ::= {pr1646v2ATMFwPerFrDlciInPQsD7PerformanceEntry 11}

pr1646v2ATMFwPerFrDlciInPQsD7PerformanceSysUpTime OBJECT-TYPE
   SYNTAX      TimeTicks
   MAX-ACCESS  read-only
   STATUS      current
   DESCRIPTION
      "Path: atm.performance.pvcTable.frameRelay.dlciTable.inPriorityQueues.d7Performance.sysUpTime

       Time in centi-second."
   ::= {pr1646v2ATMFwPerFrDlciInPQsD7PerformanceEntry 16777216}

pr1646v2ATMFwPerFrDlciInPQsD7PerformanceTotPkts OBJECT-TYPE
   SYNTAX      Counter64
   MAX-ACCESS  read-only
   STATUS      current
   DESCRIPTION
      "Path: atm.performance.pvcTable.frameRelay.dlciTable.inPriorityQueues.d7Performance.totalPkts

       64 bit unsigned wrappable counter."
   ::= {pr1646v2ATMFwPerFrDlciInPQsD7PerformanceEntry 234881024}

pr1646v2ATMFwPerFrDlciInPQsD7PerformanceDirTxPkts OBJECT-TYPE
   SYNTAX      Counter64
   MAX-ACCESS  read-only
   STATUS      current
   DESCRIPTION
      "Path: atm.performance.pvcTable.frameRelay.dlciTable.inPriorityQueues.d7Performance.directTxPkts

       64 bit unsigned wrappable counter."
   ::= {pr1646v2ATMFwPerFrDlciInPQsD7PerformanceEntry 33554432}

pr1646v2ATMFwPerFrDlciInPQsD7PerformanceQdPkts OBJECT-TYPE
   SYNTAX      Counter64
   MAX-ACCESS  read-only
   STATUS      current
   DESCRIPTION
      "Path: atm.performance.pvcTable.frameRelay.dlciTable.inPriorityQueues.d7Performance.queuedPkts

       64 bit unsigned wrappable counter."
   ::= {pr1646v2ATMFwPerFrDlciInPQsD7PerformanceEntry 50331648}

pr1646v2ATMFwPerFrDlciInPQsD7PerformanceDropPkts OBJECT-TYPE
   SYNTAX      Counter64
   MAX-ACCESS  read-only
   STATUS      current
   DESCRIPTION
      "Path: atm.performance.pvcTable.frameRelay.dlciTable.inPriorityQueues.d7Performance.droppedPkts

       64 bit unsigned wrappable counter."
   ::= {pr1646v2ATMFwPerFrDlciInPQsD7PerformanceEntry 67108864}

pr1646v2ATMFwPerFrDlciInPQsD7PerformanceRDropPkts OBJECT-TYPE
   SYNTAX      Counter64
   MAX-ACCESS  read-only
   STATUS      current
   DESCRIPTION
      "Path: atm.performance.pvcTable.frameRelay.dlciTable.inPriorityQueues.d7Performance.redDroppedPkts

       64 bit unsigned wrappable counter."
   ::= {pr1646v2ATMFwPerFrDlciInPQsD7PerformanceEntry 201326592}

pr1646v2ATMFwPerFrDlciInPQsD7PerformanceCirTxPkts OBJECT-TYPE
   SYNTAX      Counter64
   MAX-ACCESS  read-only
   STATUS      current
   DESCRIPTION
      "Path: atm.performance.pvcTable.frameRelay.dlciTable.inPriorityQueues.d7Performance.cirTxPkts

       64 bit unsigned wrappable counter."
   ::= {pr1646v2ATMFwPerFrDlciInPQsD7PerformanceEntry 83886080}

pr1646v2ATMFwPerFrDlciInPQsD7PerformanceEirTxPkts OBJECT-TYPE
   SYNTAX      Counter64
   MAX-ACCESS  read-only
   STATUS      current
   DESCRIPTION
      "Path: atm.performance.pvcTable.frameRelay.dlciTable.inPriorityQueues.d7Performance.eirTxPkts

       64 bit unsigned wrappable counter."
   ::= {pr1646v2ATMFwPerFrDlciInPQsD7PerformanceEntry 100663296}

pr1646v2ATMFwPerFrDlciInPQsD7PerformanceViolTxPkts OBJECT-TYPE
   SYNTAX      Counter64
   MAX-ACCESS  read-only
   STATUS      current
   DESCRIPTION
      "Path: atm.performance.pvcTable.frameRelay.dlciTable.inPriorityQueues.d7Performance.violateTxPkts

       64 bit unsigned wrappable counter."
   ::= {pr1646v2ATMFwPerFrDlciInPQsD7PerformanceEntry 301989888}

pr1646v2ATMFwPerFrDlciInPQsD7PerformanceTotOcts OBJECT-TYPE
   SYNTAX      Counter64
   MAX-ACCESS  read-only
   STATUS      current
   DESCRIPTION
      "Path: atm.performance.pvcTable.frameRelay.dlciTable.inPriorityQueues.d7Performance.totalOctets

       64 bit unsigned wrappable counter."
   ::= {pr1646v2ATMFwPerFrDlciInPQsD7PerformanceEntry 251658240}

pr1646v2ATMFwPerFrDlciInPQsD7PerformanceDirTxOcts OBJECT-TYPE
   SYNTAX      Counter64
   MAX-ACCESS  read-only
   STATUS      current
   DESCRIPTION
      "Path: atm.performance.pvcTable.frameRelay.dlciTable.inPriorityQueues.d7Performance.directTxOctets

       64 bit unsigned wrappable counter."
   ::= {pr1646v2ATMFwPerFrDlciInPQsD7PerformanceEntry 117440512}

pr1646v2ATMFwPerFrDlciInPQsD7PerformanceQdOcts OBJECT-TYPE
   SYNTAX      Counter64
   MAX-ACCESS  read-only
   STATUS      current
   DESCRIPTION
      "Path: atm.performance.pvcTable.frameRelay.dlciTable.inPriorityQueues.d7Performance.queuedOctets

       64 bit unsigned wrappable counter."
   ::= {pr1646v2ATMFwPerFrDlciInPQsD7PerformanceEntry 134217728}

pr1646v2ATMFwPerFrDlciInPQsD7PerformanceDropOcts OBJECT-TYPE
   SYNTAX      Counter64
   MAX-ACCESS  read-only
   STATUS      current
   DESCRIPTION
      "Path: atm.performance.pvcTable.frameRelay.dlciTable.inPriorityQueues.d7Performance.droppedOctets

       64 bit unsigned wrappable counter."
   ::= {pr1646v2ATMFwPerFrDlciInPQsD7PerformanceEntry 150994944}

pr1646v2ATMFwPerFrDlciInPQsD7PerformanceRDropOcts OBJECT-TYPE
   SYNTAX      Counter64
   MAX-ACCESS  read-only
   STATUS      current
   DESCRIPTION
      "Path: atm.performance.pvcTable.frameRelay.dlciTable.inPriorityQueues.d7Performance.redDroppedOctets

       64 bit unsigned wrappable counter."
   ::= {pr1646v2ATMFwPerFrDlciInPQsD7PerformanceEntry 218103808}

pr1646v2ATMFwPerFrDlciInPQsD7PerformanceCirTxOcts OBJECT-TYPE
   SYNTAX      Counter64
   MAX-ACCESS  read-only
   STATUS      current
   DESCRIPTION
      "Path: atm.performance.pvcTable.frameRelay.dlciTable.inPriorityQueues.d7Performance.cirTxOctets

       64 bit unsigned wrappable counter."
   ::= {pr1646v2ATMFwPerFrDlciInPQsD7PerformanceEntry 167772160}

pr1646v2ATMFwPerFrDlciInPQsD7PerformanceEirTxOcts OBJECT-TYPE
   SYNTAX      Counter64
   MAX-ACCESS  read-only
   STATUS      current
   DESCRIPTION
      "Path: atm.performance.pvcTable.frameRelay.dlciTable.inPriorityQueues.d7Performance.eirTxOctets

       64 bit unsigned wrappable counter."
   ::= {pr1646v2ATMFwPerFrDlciInPQsD7PerformanceEntry 184549376}

pr1646v2ATMFwPerFrDlciInPQsD7PerformanceViolTxOcts OBJECT-TYPE
   SYNTAX      Counter64
   MAX-ACCESS  read-only
   STATUS      current
   DESCRIPTION
      "Path: atm.performance.pvcTable.frameRelay.dlciTable.inPriorityQueues.d7Performance.violateTxOctets

       64 bit unsigned wrappable counter."
   ::= {pr1646v2ATMFwPerFrDlciInPQsD7PerformanceEntry 318767104}

pr1646v2ATMFwPerFrDlciInPQsD7PerformanceBandwidth OBJECT-TYPE
   SYNTAX      Integer32
   MAX-ACCESS  read-only
   STATUS      current
   DESCRIPTION
      "Path: atm.performance.pvcTable.frameRelay.dlciTable.inPriorityQueues.d7Performance.bandwidth

       unit name = bps
       formula = 8 * ; 8 /"
   ::= {pr1646v2ATMFwPerFrDlciInPQsD7PerformanceEntry 268435456}

pr1646v2ATMFwPerFrDlciOutPQs OBJECT-TYPE
   SYNTAX      SEQUENCE OF Pr1646v2ATMFwPerFrDlciOutPQsEntry
   MAX-ACCESS  not-accessible
   STATUS      current
   DESCRIPTION
      ""
   ::= {pr1646v2ATMFwPer 503448832}

pr1646v2ATMFwPerFrDlciOutPQsEntry OBJECT-TYPE
   SYNTAX      Pr1646v2ATMFwPerFrDlciOutPQsEntry
   MAX-ACCESS  not-accessible
   STATUS      current
   DESCRIPTION
      ""
   INDEX      { pr1646v2ATMFwPerFrDlciOutPQsGlobalIx,
                pr1646v2ATMFwPerTableIx,
                pr1646v2ATMFwPerFrDlciTableIx,
                pr1646v2ATMFwPerFrDlciOutPQsTableIx }
   ::= {pr1646v2ATMFwPerFrDlciOutPQs 1}

Pr1646v2ATMFwPerFrDlciOutPQsEntry ::=
   SEQUENCE
      {
      pr1646v2ATMFwPerFrDlciOutPQsGlobalIx
         GlobalIndex,
      pr1646v2ATMFwPerFrDlciOutPQsTableIx
         TableIndex,
      pr1646v2ATMFwPerFrDlciOutPQsName
         INTEGER,
      pr1646v2ATMFwPerFrDlciOutPQsLength
         Integer32,
      pr1646v2ATMFwPerFrDlciOutPQsOctetLength
         Integer32,
      pr1646v2ATMFwPerFrDlciOutPQsRedLength
         Integer32,
      pr1646v2ATMFwPerFrDlciOutPQsPacketsTotal
         Counter64,
      pr1646v2ATMFwPerFrDlciOutPQsPacketsDirectTx
         Counter64,
      pr1646v2ATMFwPerFrDlciOutPQsPacketsQueued
         Counter64,
      pr1646v2ATMFwPerFrDlciOutPQsPacketsDropped
         Counter64,
      pr1646v2ATMFwPerFrDlciOutPQsPacketsRedDropped
         Counter64,
      pr1646v2ATMFwPerFrDlciOutPQsPacketsCirTx
         Counter64,
      pr1646v2ATMFwPerFrDlciOutPQsPacketsEirTx
         Counter64,
      pr1646v2ATMFwPerFrDlciOutPQsPacketsViolateTx
         Counter64,
      pr1646v2ATMFwPerFrDlciOutPQsOctetsTotal
         Counter64,
      pr1646v2ATMFwPerFrDlciOutPQsOctetsDirectTx
         Counter64,
      pr1646v2ATMFwPerFrDlciOutPQsOctetsQueued
         Counter64,
      pr1646v2ATMFwPerFrDlciOutPQsOctetsDropped
         Counter64,
      pr1646v2ATMFwPerFrDlciOutPQsOctetsRedDropped
         Counter64,
      pr1646v2ATMFwPerFrDlciOutPQsOctetsCirTx
         Counter64,
      pr1646v2ATMFwPerFrDlciOutPQsOctetsEirTx
         Counter64,
      pr1646v2ATMFwPerFrDlciOutPQsOctetsViolateTx
         Counter64,
      pr1646v2ATMFwPerFrDlciOutPQsOctetsBandwidth15sec
         Integer32,
      pr1646v2ATMFwPerFrDlciOutPQsOctetsBandwidth30sec
         Integer32,
      pr1646v2ATMFwPerFrDlciOutPQsOctetsBandwidth1min
         Integer32,
      pr1646v2ATMFwPerFrDlciOutPQsOctetsBandwidth2min
         Integer32,
      pr1646v2ATMFwPerFrDlciOutPQsOctetsBandwidth5min
         Integer32
      }

pr1646v2ATMFwPerFrDlciOutPQsGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciOutPQsEntry 10}

pr1646v2ATMFwPerFrDlciOutPQsTableIx OBJECT-TYPE
   SYNTAX      TableIndex
   MAX-ACCESS  not-accessible
   STATUS      current
   DESCRIPTION
      ""
   ::= {pr1646v2ATMFwPerFrDlciOutPQsEntry 11}

pr1646v2ATMFwPerFrDlciOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.frameRelay.dlciTable.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2ATMFwPerFrDlciOutPQsEntry 16777216}

pr1646v2ATMFwPerFrDlciOutPQsLength OBJECT-TYPE
   SYNTAX      Integer32
   MAX-ACCESS  read-only
   STATUS      current
   DESCRIPTION
      "Path: atm.performance.pvcTable.frameRelay.dlciTable.outPriorityQueues.length"
   ::= {pr1646v2ATMFwPerFrDlciOutPQsEntry 33554432}

pr1646v2ATMFwPerFrDlciOutPQsOctetLength OBJECT-TYPE
   SYNTAX      Integer32
   MAX-ACCESS  read-only
   STATUS      current
   DESCRIPTION
      "Path: atm.performance.pvcTable.frameRelay.dlciTable.outPriorityQueues.octetLength"
   ::= {pr1646v2ATMFwPerFrDlciOutPQsEntry 150994944}

pr1646v2ATMFwPerFrDlciOutPQsRedLength OBJECT-TYPE
   SYNTAX      Integer32
   MAX-ACCESS  read-only
   STATUS      current
   DESCRIPTION
      "Path: atm.performance.pvcTable.frameRelay.dlciTable.outPriorityQueues.redLength"
   ::= {pr1646v2ATMFwPerFrDlciOutPQsEntry 134217728}

pr1646v2ATMFwPerFrDlciOutPQsPacketsTotal OBJECT-TYPE
   SYNTAX      Counter64
   MAX-ACCESS  read-only
   STATUS      current
   DESCRIPTION
      "Path: atm.performance.pvcTable.frameRelay.dlciTable.outPriorityQueues.packets.total

       64 bit unsigned wrappable counter."
   ::= {pr1646v2ATMFwPerFrDlciOutPQsEntry 50790400}

pr1646v2ATMFwPerFrDlciOutPQsPacketsDirectTx OBJECT-TYPE
   SYNTAX      Counter64
   MAX-ACCESS  read-only
   STATUS      current
   DESCRIPTION
      "Path: atm.performance.pvcTable.frameRelay.dlciTable.outPriorityQueues.packets.directTx

       64 bit unsigned wrappable counter."
   ::= {pr1646v2ATMFwPerFrDlciOutPQsEntry 50397184}

pr1646v2ATMFwPerFrDlciOutPQsPacketsQueued OBJECT-TYPE
   SYNTAX      Counter64
   MAX-ACCESS  read-only
   STATUS      current
   DESCRIPTION
      "Path: atm.performance.pvcTable.frameRelay.dlciTable.outPriorityQueues.packets.queued

       64 bit unsigned wrappable counter."
   ::= {pr1646v2ATMFwPerFrDlciOutPQsEntry 50462720}

pr1646v2ATMFwPerFrDlciOutPQsPacketsDropped OBJECT-TYPE
   SYNTAX      Counter64
   MAX-ACCESS  read-only
   STATUS      current
   DESCRIPTION
      "Path: atm.performance.pvcTable.frameRelay.dlciTable.outPriorityQueues.packets.dropped

       64 bit unsigned wrappable counter."
   ::= {pr1646v2ATMFwPerFrDlciOutPQsEntry 50528256}

pr1646v2ATMFwPerFrDlciOutPQsPacketsRedDropped OBJECT-TYPE
   SYNTAX      Counter64
   MAX-ACCESS  read-only
   STATUS      current
   DESCRIPTION
      "Path: atm.performance.pvcTable.frameRelay.dlciTable.outPriorityQueues.packets.redDropped

       64 bit unsigned wrappable counter."
   ::= {pr1646v2ATMFwPerFrDlciOutPQsEntry 50724864}

pr1646v2ATMFwPerFrDlciOutPQsPacketsCirTx OBJECT-TYPE
   SYNTAX      Counter64
   MAX-ACCESS  read-only
   STATUS      current
   DESCRIPTION
      "Path: atm.performance.pvcTable.frameRelay.dlciTable.outPriorityQueues.packets.cirTx

       64 bit unsigned wrappable counter."
   ::= {pr1646v2ATMFwPerFrDlciOutPQsEntry 50593792}

pr1646v2ATMFwPerFrDlciOutPQsPacketsEirTx OBJECT-TYPE
   SYNTAX      Counter64
   MAX-ACCESS  read-only
   STATUS      current
   DESCRIPTION
      "Path: atm.performance.pvcTable.frameRelay.dlciTable.outPriorityQueues.packets.eirTx

       64 bit unsigned wrappable counter."
   ::= {pr1646v2ATMFwPerFrDlciOutPQsEntry 50659328}

pr1646v2ATMFwPerFrDlciOutPQsPacketsViolateTx OBJECT-TYPE
   SYNTAX      Counter64
   MAX-ACCESS  read-only
   STATUS      current
   DESCRIPTION
      "Path: atm.performance.pvcTable.frameRelay.dlciTable.outPriorityQueues.packets.violateTx

       64 bit unsigned wrappable counter."
   ::= {pr1646v2ATMFwPerFrDlciOutPQsEntry 50855936}

pr1646v2ATMFwPerFrDlciOutPQsOctetsTotal OBJECT-TYPE
   SYNTAX      Counter64
   MAX-ACCESS  read-only
   STATUS      current
   DESCRIPTION
      "Path: atm.performance.pvcTable.frameRelay.dlciTable.outPriorityQueues.octets.total

       64 bit unsigned wrappable counter."
   ::= {pr1646v2ATMFwPerFrDlciOutPQsEntry 67567616}

pr1646v2ATMFwPerFrDlciOutPQsOctetsDirectTx OBJECT-TYPE
   SYNTAX      Counter64
   MAX-ACCESS  read-only
   STATUS      current
   DESCRIPTION
      "Path: atm.performance.pvcTable.frameRelay.dlciTable.outPriorityQueues.octets.directTx

       64 bit unsigned wrappable counter."
   ::= {pr1646v2ATMFwPerFrDlciOutPQsEntry 67174400}

pr1646v2ATMFwPerFrDlciOutPQsOctetsQueued OBJECT-TYPE
   SYNTAX      Counter64
   MAX-ACCESS  read-only
   STATUS      current
   DESCRIPTION
      "Path: atm.performance.pvcTable.frameRelay.dlciTable.outPriorityQueues.octets.queued

       64 bit unsigned wrappable counter."
   ::= {pr1646v2ATMFwPerFrDlciOutPQsEntry 67239936}

pr1646v2ATMFwPerFrDlciOutPQsOctetsDropped OBJECT-TYPE
   SYNTAX      Counter64
   MAX-ACCESS  read-only
   STATUS      current
   DESCRIPTION
      "Path: atm.performance.pvcTable.frameRelay.dlciTable.outPriorityQueues.octets.dropped

       64 bit unsigned wrappable counter."
   ::= {pr1646v2ATMFwPerFrDlciOutPQsEntry 67305472}

pr1646v2ATMFwPerFrDlciOutPQsOctetsRedDropped OBJECT-TYPE
   SYNTAX      Counter64
   MAX-ACCESS  read-only
   STATUS      current
   DESCRIPTION
      "Path: atm.performance.pvcTable.frameRelay.dlciTable.outPriorityQueues.octets.redDropped

       64 bit unsigned wrappable counter."
   ::= {pr1646v2ATMFwPerFrDlciOutPQsEntry 67502080}

pr1646v2ATMFwPerFrDlciOutPQsOctetsCirTx OBJECT-TYPE
   SYNTAX      Counter64
   MAX-ACCESS  read-only
   STATUS      current
   DESCRIPTION
      "Path: atm.performance.pvcTable.frameRelay.dlciTable.outPriorityQueues.octets.cirTx

       64 bit unsigned wrappable counter."
   ::= {pr1646v2ATMFwPerFrDlciOutPQsEntry 67371008}

pr1646v2ATMFwPerFrDlciOutPQsOctetsEirTx OBJECT-TYPE
   SYNTAX      Counter64
   MAX-ACCESS  read-only
   STATUS      current
   DESCRIPTION
      "Path: atm.performance.pvcTable.frameRelay.dlciTable.outPriorityQueues.octets.eirTx

       64 bit unsigned wrappable counter."
   ::= {pr1646v2ATMFwPerFrDlciOutPQsEntry 67436544}

pr1646v2ATMFwPerFrDlciOutPQsOctetsViolateTx OBJECT-TYPE
   SYNTAX      Counter64
   MAX-ACCESS  read-only
   STATUS      current
   DESCRIPTION
      "Path: atm.performance.pvcTable.frameRelay.dlciTable.outPriorityQueues.octets.violateTx

       64 bit unsigned wrappable counter."
   ::= {pr1646v2ATMFwPerFrDlciOutPQsEntry 67633152}

pr1646v2ATMFwPerFrDlciOutPQsOctetsBandwidth15sec OBJECT-TYPE
   SYNTAX      Integer32
   MAX-ACCESS  read-only
   STATUS      current
   DESCRIPTION
      "Path: atm.performance.pvcTable.frameRelay.dlciTable.outPriorityQueues.octets.bandwidth.15sec

       unit name = bps
       formula = 8 * ; 8 /"
   ::= {pr1646v2ATMFwPerFrDlciOutPQsEntry 70386944}

pr1646v2ATMFwPerFrDlciOutPQsOctetsBandwidth30sec OBJECT-TYPE
   SYNTAX      Integer32
   MAX-ACCESS  read-only
   STATUS      current
   DESCRIPTION
      "Path: atm.performance.pvcTable.frameRelay.dlciTable.outPriorityQueues.octets.bandwidth.30sec

       unit name = bps
       formula = 8 * ; 8 /"
   ::= {pr1646v2ATMFwPerFrDlciOutPQsEntry 70388224}

pr1646v2ATMFwPerFrDlciOutPQsOctetsBandwidth1min OBJECT-TYPE
   SYNTAX      Integer32
   MAX-ACCESS  read-only
   STATUS      current
   DESCRIPTION
      "Path: atm.performance.pvcTable.frameRelay.dlciTable.outPriorityQueues.octets.bandwidth.1min

       unit name = bps
       formula = 8 * ; 8 /"
   ::= {pr1646v2ATMFwPerFrDlciOutPQsEntry 70390784}

pr1646v2ATMFwPerFrDlciOutPQsOctetsBandwidth2min OBJECT-TYPE
   SYNTAX      Integer32
   MAX-ACCESS  read-only
   STATUS      current
   DESCRIPTION
      "Path: atm.performance.pvcTable.frameRelay.dlciTable.outPriorityQueues.octets.bandwidth.2min

       unit name = bps
       formula = 8 * ; 8 /"
   ::= {pr1646v2ATMFwPerFrDlciOutPQsEntry 70395904}

pr1646v2ATMFwPerFrDlciOutPQsOctetsBandwidth5min OBJECT-TYPE
   SYNTAX      Integer32
   MAX-ACCESS  read-only
   STATUS      current
   DESCRIPTION
      "Path: atm.performance.pvcTable.frameRelay.dlciTable.outPriorityQueues.octets.bandwidth.5min

       unit name = bps
       formula = 8 * ; 8 /"
   ::= {pr1646v2ATMFwPerFrDlciOutPQsEntry 70411264}

pr1646v2ATMFwPerFrDlciOutPQsH2Performance OBJECT-TYPE
   SYNTAX      SEQUENCE OF Pr1646v2ATMFwPerFrDlciOutPQsH2PerformanceEntry
   MAX-ACCESS  not-accessible
   STATUS      current
   DESCRIPTION
      ""
   ::= {pr1646v2ATMFwPer 503448837}

pr1646v2ATMFwPerFrDlciOutPQsH2PerformanceEntry OBJECT-TYPE
   SYNTAX      Pr1646v2ATMFwPerFrDlciOutPQsH2PerformanceEntry
   MAX-ACCESS  not-accessible
   STATUS      current
   DESCRIPTION
      ""
   INDEX      { pr1646v2ATMFwPerFrDlciOutPQsH2PerformanceGlobalIx,
                pr1646v2ATMFwPerTableIx,
                pr1646v2ATMFwPerFrDlciTableIx,
                pr1646v2ATMFwPerFrDlciOutPQsTableIx,
                pr1646v2ATMFwPerFrDlciOutPQsH2PerformanceTableIx }
   ::= {pr1646v2ATMFwPerFrDlciOutPQsH2Performance 1}

Pr1646v2ATMFwPerFrDlciOutPQsH2PerformanceEntry ::=
   SEQUENCE
      {
      pr1646v2ATMFwPerFrDlciOutPQsH2PerformanceGlobalIx
         GlobalIndex,
      pr1646v2ATMFwPerFrDlciOutPQsH2PerformanceTableIx
         TableIndex,
      pr1646v2ATMFwPerFrDlciOutPQsH2PerformanceSysUpTime
         TimeTicks,
      pr1646v2ATMFwPerFrDlciOutPQsH2PerformanceTotPkts
         Counter64,
      pr1646v2ATMFwPerFrDlciOutPQsH2PerformanceDirTxPkts
         Counter64,
      pr1646v2ATMFwPerFrDlciOutPQsH2PerformanceQdPkts
         Counter64,
      pr1646v2ATMFwPerFrDlciOutPQsH2PerformanceDropPkts
         Counter64,
      pr1646v2ATMFwPerFrDlciOutPQsH2PerformanceRDropPkts
         Counter64,
      pr1646v2ATMFwPerFrDlciOutPQsH2PerformanceCirTxPkts
         Counter64,
      pr1646v2ATMFwPerFrDlciOutPQsH2PerformanceEirTxPkts
         Counter64,
      pr1646v2ATMFwPerFrDlciOutPQsH2PerformanceViolTxPkts
         Counter64,
      pr1646v2ATMFwPerFrDlciOutPQsH2PerformanceTotOcts
         Counter64,
      pr1646v2ATMFwPerFrDlciOutPQsH2PerformanceDirTxOcts
         Counter64,
      pr1646v2ATMFwPerFrDlciOutPQsH2PerformanceQdOcts
         Counter64,
      pr1646v2ATMFwPerFrDlciOutPQsH2PerformanceDropOcts
         Counter64,
      pr1646v2ATMFwPerFrDlciOutPQsH2PerformanceRDropOcts
         Counter64,
      pr1646v2ATMFwPerFrDlciOutPQsH2PerformanceCirTxOcts
         Counter64,
      pr1646v2ATMFwPerFrDlciOutPQsH2PerformanceEirTxOcts
         Counter64,
      pr1646v2ATMFwPerFrDlciOutPQsH2PerformanceViolTxOcts
         Counter64,
      pr1646v2ATMFwPerFrDlciOutPQsH2PerformanceBandwidth
         Integer32
      }

pr1646v2ATMFwPerFrDlciOutPQsH2PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciOutPQsH2PerformanceEntry 10}

pr1646v2ATMFwPerFrDlciOutPQsH2PerformanceTableIx OBJECT-TYPE
   SYNTAX      TableIndex
   MAX-ACCESS  not-accessible
   STATUS      current
   DESCRIPTION
      ""
   ::= {pr1646v2ATMFwPerFrDlciOutPQsH2PerformanceEntry 11}

pr1646v2ATMFwPerFrDlciOutPQsH2PerformanceSysUpTime OBJECT-TYPE
   SYNTAX      TimeTicks
   MAX-ACCESS  read-only
   STATUS      current
   DESCRIPTION
      "Path: atm.performance.pvcTable.frameRelay.dlciTable.outPriorityQueues.h2Performance.sysUpTime

       Time in centi-second."
   ::= {pr1646v2ATMFwPerFrDlciOutPQsH2PerformanceEntry 16777216}

pr1646v2ATMFwPerFrDlciOutPQsH2PerformanceTotPkts OBJECT-TYPE
   SYNTAX      Counter64
   MAX-ACCESS  read-only
   STATUS      current
   DESCRIPTION
      "Path: atm.performance.pvcTable.frameRelay.dlciTable.outPriorityQueues.h2Performance.totalPkts

       64 bit unsigned wrappable counter."
   ::= {pr1646v2ATMFwPerFrDlciOutPQsH2PerformanceEntry 234881024}

pr1646v2ATMFwPerFrDlciOutPQsH2PerformanceDirTxPkts OBJECT-TYPE
   SYNTAX      Counter64
   MAX-ACCESS  read-only
   STATUS      current
   DESCRIPTION
      "Path: atm.performance.pvcTable.frameRelay.dlciTable.outPriorityQueues.h2Performance.directTxPkts

       64 bit unsigned wrappable counter."
   ::= {pr1646v2ATMFwPerFrDlciOutPQsH2PerformanceEntry 33554432}

pr1646v2ATMFwPerFrDlciOutPQsH2PerformanceQdPkts OBJECT-TYPE
   SYNTAX      Counter64
   MAX-ACCESS  read-only
   STATUS      current
   DESCRIPTION
      "Path: atm.performance.pvcTable.frameRelay.dlciTable.outPriorityQueues.h2Performance.queuedPkts

       64 bit unsigned wrappable counter."
   ::= {pr1646v2ATMFwPerFrDlciOutPQsH2PerformanceEntry 50331648}

pr1646v2ATMFwPerFrDlciOutPQsH2PerformanceDropPkts OBJECT-TYPE
   SYNTAX      Counter64
   MAX-ACCESS  read-only
   STATUS      current
   DESCRIPTION
      "Path: atm.performance.pvcTable.frameRelay.dlciTable.outPriorityQueues.h2Performance.droppedPkts

       64 bit unsigned wrappable counter."
   ::= {pr1646v2ATMFwPerFrDlciOutPQsH2PerformanceEntry 67108864}

pr1646v2ATMFwPerFrDlciOutPQsH2PerformanceRDropPkts OBJECT-TYPE
   SYNTAX      Counter64
   MAX-ACCESS  read-only
   STATUS      current
   DESCRIPTION
      "Path: atm.performance.pvcTable.frameRelay.dlciTable.outPriorityQueues.h2Performance.redDroppedPkts

       64 bit unsigned wrappable counter."
   ::= {pr1646v2ATMFwPerFrDlciOutPQsH2PerformanceEntry 201326592}

pr1646v2ATMFwPerFrDlciOutPQsH2PerformanceCirTxPkts OBJECT-TYPE
   SYNTAX      Counter64
   MAX-ACCESS  read-only
   STATUS      current
   DESCRIPTION
      "Path: atm.performance.pvcTable.frameRelay.dlciTable.outPriorityQueues.h2Performance.cirTxPkts

       64 bit unsigned wrappable counter."
   ::= {pr1646v2ATMFwPerFrDlciOutPQsH2PerformanceEntry 83886080}

pr1646v2ATMFwPerFrDlciOutPQsH2PerformanceEirTxPkts OBJECT-TYPE
   SYNTAX      Counter64
   MAX-ACCESS  read-only
   STATUS      current
   DESCRIPTION
      "Path: atm.performance.pvcTable.frameRelay.dlciTable.outPriorityQueues.h2Performance.eirTxPkts

       64 bit unsigned wrappable counter."
   ::= {pr1646v2ATMFwPerFrDlciOutPQsH2PerformanceEntry 100663296}

pr1646v2ATMFwPerFrDlciOutPQsH2PerformanceViolTxPkts OBJECT-TYPE
   SYNTAX      Counter64
   MAX-ACCESS  read-only
   STATUS      current
   DESCRIPTION
      "Path: atm.performance.pvcTable.frameRelay.dlciTable.outPriorityQueues.h2Performance.violateTxPkts

       64 bit unsigned wrappable counter."
   ::= {pr1646v2ATMFwPerFrDlciOutPQsH2PerformanceEntry 301989888}

pr1646v2ATMFwPerFrDlciOutPQsH2PerformanceTotOcts OBJECT-TYPE
   SYNTAX      Counter64
   MAX-ACCESS  read-only
   STATUS      current
   DESCRIPTION
      "Path: atm.performance.pvcTable.frameRelay.dlciTable.outPriorityQueues.h2Performance.totalOctets

       64 bit unsigned wrappable counter."
   ::= {pr1646v2ATMFwPerFrDlciOutPQsH2PerformanceEntry 251658240}

pr1646v2ATMFwPerFrDlciOutPQsH2PerformanceDirTxOcts OBJECT-TYPE
   SYNTAX      Counter64
   MAX-ACCESS  read-only
   STATUS      current
   DESCRIPTION
      "Path: atm.performance.pvcTable.frameRelay.dlciTable.outPriorityQueues.h2Performance.directTxOctets

       64 bit unsigned wrappable counter."
   ::= {pr1646v2ATMFwPerFrDlciOutPQsH2PerformanceEntry 117440512}

pr1646v2ATMFwPerFrDlciOutPQsH2PerformanceQdOcts OBJECT-TYPE
   SYNTAX      Counter64
   MAX-ACCESS  read-only
   STATUS      current
   DESCRIPTION
      "Path: atm.performance.pvcTable.frameRelay.dlciTable.outPriorityQueues.h2Performance.queuedOctets

       64 bit unsigned wrappable counter."
   ::= {pr1646v2ATMFwPerFrDlciOutPQsH2PerformanceEntry 134217728}

pr1646v2ATMFwPerFrDlciOutPQsH2PerformanceDropOcts OBJECT-TYPE
   SYNTAX      Counter64
   MAX-ACCESS  read-only
   STATUS      current
   DESCRIPTION
      "Path: atm.performance.pvcTable.frameRelay.dlciTable.outPriorityQueues.h2Performance.droppedOctets

       64 bit unsigned wrappable counter."
   ::= {pr1646v2ATMFwPerFrDlciOutPQsH2PerformanceEntry 150994944}

pr1646v2ATMFwPerFrDlciOutPQsH2PerformanceRDropOcts OBJECT-TYPE
   SYNTAX      Counter64
   MAX-ACCESS  read-only
   STATUS      current
   DESCRIPTION
      "Path: atm.performance.pvcTable.frameRelay.dlciTable.outPriorityQueues.h2Performance.redDroppedOctets

       64 bit unsigned wrappable counter."
   ::= {pr1646v2ATMFwPerFrDlciOutPQsH2PerformanceEntry 218103808}

pr1646v2ATMFwPerFrDlciOutPQsH2PerformanceCirTxOcts OBJECT-TYPE
   SYNTAX      Counter64
   MAX-ACCESS  read-only
   STATUS      current
   DESCRIPTION
      "Path: atm.performance.pvcTable.frameRelay.dlciTable.outPriorityQueues.h2Performance.cirTxOctets

       64 bit unsigned wrappable counter."
   ::= {pr1646v2ATMFwPerFrDlciOutPQsH2PerformanceEntry 167772160}

pr1646v2ATMFwPerFrDlciOutPQsH2PerformanceEirTxOcts OBJECT-TYPE
   SYNTAX      Counter64
   MAX-ACCESS  read-only
   STATUS      current
   DESCRIPTION
      "Path: atm.performance.pvcTable.frameRelay.dlciTable.outPriorityQueues.h2Performance.eirTxOctets

       64 bit unsigned wrappable counter."
   ::= {pr1646v2ATMFwPerFrDlciOutPQsH2PerformanceEntry 184549376}

pr1646v2ATMFwPerFrDlciOutPQsH2PerformanceViolTxOcts OBJECT-TYPE
   SYNTAX      Counter64
   MAX-ACCESS  read-only
   STATUS      current
   DESCRIPTION
      "Path: atm.performance.pvcTable.frameRelay.dlciTable.outPriorityQueues.h2Performance.violateTxOctets

       64 bit unsigned wrappable counter."
   ::= {pr1646v2ATMFwPerFrDlciOutPQsH2PerformanceEntry 318767104}

pr1646v2ATMFwPerFrDlciOutPQsH2PerformanceBandwidth OBJECT-TYPE
   SYNTAX      Integer32
   MAX-ACCESS  read-only
   STATUS      current
   DESCRIPTION
      "Path: atm.performance.pvcTable.frameRelay.dlciTable.outPriorityQueues.h2Performance.bandwidth

       unit name = bps
       formula = 8 * ; 8 /"
   ::= {pr1646v2ATMFwPerFrDlciOutPQsH2PerformanceEntry 268435456}

pr1646v2ATMFwPerFrDlciOutPQsH24Performance OBJECT-TYPE
   SYNTAX      SEQUENCE OF Pr1646v2ATMFwPerFrDlciOutPQsH24PerformanceEntry
   MAX-ACCESS  not-accessible
   STATUS      current
   DESCRIPTION
      ""
   ::= {pr1646v2ATMFwPer 503448838}

pr1646v2ATMFwPerFrDlciOutPQsH24PerformanceEntry OBJECT-TYPE
   SYNTAX      Pr1646v2ATMFwPerFrDlciOutPQsH24PerformanceEntry
   MAX-ACCESS  not-accessible
   STATUS      current
   DESCRIPTION
      ""
   INDEX      { pr1646v2ATMFwPerFrDlciOutPQsH24PerformanceGlobalIx,
                pr1646v2ATMFwPerTableIx,
                pr1646v2ATMFwPerFrDlciTableIx,
                pr1646v2ATMFwPerFrDlciOutPQsTableIx,
                pr1646v2ATMFwPerFrDlciOutPQsH24PerformanceTableIx }
   ::= {pr1646v2ATMFwPerFrDlciOutPQsH24Performance 1}

Pr1646v2ATMFwPerFrDlciOutPQsH24PerformanceEntry ::=
   SEQUENCE
      {
      pr1646v2ATMFwPerFrDlciOutPQsH24PerformanceGlobalIx
         GlobalIndex,
      pr1646v2ATMFwPerFrDlciOutPQsH24PerformanceTableIx
         TableIndex,
      pr1646v2ATMFwPerFrDlciOutPQsH24PerformanceSysUpTime
         TimeTicks,
      pr1646v2ATMFwPerFrDlciOutPQsH24PerformanceTotPkts
         Counter64,
      pr1646v2ATMFwPerFrDlciOutPQsH24PerformanceDirTxPkts
         Counter64,
      pr1646v2ATMFwPerFrDlciOutPQsH24PerformanceQdPkts
         Counter64,
      pr1646v2ATMFwPerFrDlciOutPQsH24PerformanceDropPkts
         Counter64,
      pr1646v2ATMFwPerFrDlciOutPQsH24PerformanceRDropPkts
         Counter64,
      pr1646v2ATMFwPerFrDlciOutPQsH24PerformanceCirTxPkts
         Counter64,
      pr1646v2ATMFwPerFrDlciOutPQsH24PerformanceEirTxPkts
         Counter64,
      pr1646v2ATMFwPerFrDlciOutPQsH24PerformanceViolTxPkts
         Counter64,
      pr1646v2ATMFwPerFrDlciOutPQsH24PerformanceTotOcts
         Counter64,
      pr1646v2ATMFwPerFrDlciOutPQsH24PerformanceDirTxOcts
         Counter64,
      pr1646v2ATMFwPerFrDlciOutPQsH24PerformanceQdOcts
         Counter64,
      pr1646v2ATMFwPerFrDlciOutPQsH24PerformanceDropOcts
         Counter64,
      pr1646v2ATMFwPerFrDlciOutPQsH24PerformanceRDropOcts
         Counter64,
      pr1646v2ATMFwPerFrDlciOutPQsH24PerformanceCirTxOcts
         Counter64,
      pr1646v2ATMFwPerFrDlciOutPQsH24PerformanceEirTxOcts
         Counter64,
      pr1646v2ATMFwPerFrDlciOutPQsH24PerformanceViolTxOcts
         Counter64,
      pr1646v2ATMFwPerFrDlciOutPQsH24PerformanceBandwidth
         Integer32
      }

pr1646v2ATMFwPerFrDlciOutPQsH24PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciOutPQsH24PerformanceEntry 10}

pr1646v2ATMFwPerFrDlciOutPQsH24PerformanceTableIx OBJECT-TYPE
   SYNTAX      TableIndex
   MAX-ACCESS  not-accessible
   STATUS      current
   DESCRIPTION
      ""
   ::= {pr1646v2ATMFwPerFrDlciOutPQsH24PerformanceEntry 11}

pr1646v2ATMFwPerFrDlciOutPQsH24PerformanceSysUpTime OBJECT-TYPE
   SYNTAX      TimeTicks
   MAX-ACCESS  read-only
   STATUS      current
   DESCRIPTION
      "Path: atm.performance.pvcTable.frameRelay.dlciTable.outPriorityQueues.h24Performance.sysUpTime

       Time in centi-second."
   ::= {pr1646v2ATMFwPerFrDlciOutPQsH24PerformanceEntry 16777216}

pr1646v2ATMFwPerFrDlciOutPQsH24PerformanceTotPkts OBJECT-TYPE
   SYNTAX      Counter64
   MAX-ACCESS  read-only
   STATUS      current
   DESCRIPTION
      "Path: atm.performance.pvcTable.frameRelay.dlciTable.outPriorityQueues.h24Performance.totalPkts

       64 bit unsigned wrappable counter."
   ::= {pr1646v2ATMFwPerFrDlciOutPQsH24PerformanceEntry 234881024}

pr1646v2ATMFwPerFrDlciOutPQsH24PerformanceDirTxPkts OBJECT-TYPE
   SYNTAX      Counter64
   MAX-ACCESS  read-only
   STATUS      current
   DESCRIPTION
      "Path: atm.performance.pvcTable.frameRelay.dlciTable.outPriorityQueues.h24Performance.directTxPkts

       64 bit unsigned wrappable counter."
   ::= {pr1646v2ATMFwPerFrDlciOutPQsH24PerformanceEntry 33554432}

pr1646v2ATMFwPerFrDlciOutPQsH24PerformanceQdPkts OBJECT-TYPE
   SYNTAX      Counter64
   MAX-ACCESS  read-only
   STATUS      current
   DESCRIPTION
      "Path: atm.performance.pvcTable.frameRelay.dlciTable.outPriorityQueues.h24Performance.queuedPkts

       64 bit unsigned wrappable counter."
   ::= {pr1646v2ATMFwPerFrDlciOutPQsH24PerformanceEntry 50331648}

pr1646v2ATMFwPerFrDlciOutPQsH24PerformanceDropPkts OBJECT-TYPE
   SYNTAX      Counter64
   MAX-ACCESS  read-only
   STATUS      current
   DESCRIPTION
      "Path: atm.performance.pvcTable.frameRelay.dlciTable.outPriorityQueues.h24Performance.droppedPkts

       64 bit unsigned wrappable counter."
   ::= {pr1646v2ATMFwPerFrDlciOutPQsH24PerformanceEntry 67108864}

pr1646v2ATMFwPerFrDlciOutPQsH24PerformanceRDropPkts OBJECT-TYPE
   SYNTAX      Counter64
   MAX-ACCESS  read-only
   STATUS      current
   DESCRIPTION
      "Path: atm.performance.pvcTable.frameRelay.dlciTable.outPriorityQueues.h24Performance.redDroppedPkts

       64 bit unsigned wrappable counter."
   ::= {pr1646v2ATMFwPerFrDlciOutPQsH24PerformanceEntry 201326592}

pr1646v2ATMFwPerFrDlciOutPQsH24PerformanceCirTxPkts OBJECT-TYPE
   SYNTAX      Counter64
   MAX-ACCESS  read-only
   STATUS      current
   DESCRIPTION
      "Path: atm.performance.pvcTable.frameRelay.dlciTable.outPriorityQueues.h24Performance.cirTxPkts

       64 bit unsigned wrappable counter."
   ::= {pr1646v2ATMFwPerFrDlciOutPQsH24PerformanceEntry 83886080}

pr1646v2ATMFwPerFrDlciOutPQsH24PerformanceEirTxPkts OBJECT-TYPE
   SYNTAX      Counter64
   MAX-ACCESS  read-only
   STATUS      current
   DESCRIPTION
      "Path: atm.performance.pvcTable.frameRelay.dlciTable.outPriorityQueues.h24Performance.eirTxPkts

       64 bit unsigned wrappable counter."
   ::= {pr1646v2ATMFwPerFrDlciOutPQsH24PerformanceEntry 100663296}

pr1646v2ATMFwPerFrDlciOutPQsH24PerformanceViolTxPkts OBJECT-TYPE
   SYNTAX      Counter64
   MAX-ACCESS  read-only
   STATUS      current
   DESCRIPTION
      "Path: atm.performance.pvcTable.frameRelay.dlciTable.outPriorityQueues.h24Performance.violateTxPkts

       64 bit unsigned wrappable counter."
   ::= {pr1646v2ATMFwPerFrDlciOutPQsH24PerformanceEntry 301989888}

pr1646v2ATMFwPerFrDlciOutPQsH24PerformanceTotOcts OBJECT-TYPE
   SYNTAX      Counter64
   MAX-ACCESS  read-only
   STATUS      current
   DESCRIPTION
      "Path: atm.performance.pvcTable.frameRelay.dlciTable.outPriorityQueues.h24Performance.totalOctets

       64 bit unsigned wrappable counter."
   ::= {pr1646v2ATMFwPerFrDlciOutPQsH24PerformanceEntry 251658240}

pr1646v2ATMFwPerFrDlciOutPQsH24PerformanceDirTxOcts OBJECT-TYPE
   SYNTAX      Counter64
   MAX-ACCESS  read-only
   STATUS      current
   DESCRIPTION
      "Path: atm.performance.pvcTable.frameRelay.dlciTable.outPriorityQueues.h24Performance.directTxOctets

       64 bit unsigned wrappable counter."
   ::= {pr1646v2ATMFwPerFrDlciOutPQsH24PerformanceEntry 117440512}

pr1646v2ATMFwPerFrDlciOutPQsH24PerformanceQdOcts OBJECT-TYPE
   SYNTAX      Counter64
   MAX-ACCESS  read-only
   STATUS      current
   DESCRIPTION
      "Path: atm.performance.pvcTable.frameRelay.dlciTable.outPriorityQueues.h24Performance.queuedOctets

       64 bit unsigned wrappable counter."
   ::= {pr1646v2ATMFwPerFrDlciOutPQsH24PerformanceEntry 134217728}

pr1646v2ATMFwPerFrDlciOutPQsH24PerformanceDropOcts OBJECT-TYPE
   SYNTAX      Counter64
   MAX-ACCESS  read-only
   STATUS      current
   DESCRIPTION
      "Path: atm.performance.pvcTable.frameRelay.dlciTable.outPriorityQueues.h24Performance.droppedOctets

       64 bit unsigned wrappable counter."
   ::= {pr1646v2ATMFwPerFrDlciOutPQsH24PerformanceEntry 150994944}

pr1646v2ATMFwPerFrDlciOutPQsH24PerformanceRDropOcts OBJECT-TYPE
   SYNTAX      Counter64
   MAX-ACCESS  read-only
   STATUS      current
   DESCRIPTION
      "Path: atm.performance.pvcTable.frameRelay.dlciTable.outPriorityQueues.h24Performance.redDroppedOctets

       64 bit unsigned wrappable counter."
   ::= {pr1646v2ATMFwPerFrDlciOutPQsH24PerformanceEntry 218103808}

pr1646v2ATMFwPerFrDlciOutPQsH24PerformanceCirTxOcts OBJECT-TYPE
   SYNTAX      Counter64
   MAX-ACCESS  read-only
   STATUS      current
   DESCRIPTION
      "Path: atm.performance.pvcTable.frameRelay.dlciTable.outPriorityQueues.h24Performance.cirTxOctets

       64 bit unsigned wrappable counter."
   ::= {pr1646v2ATMFwPerFrDlciOutPQsH24PerformanceEntry 167772160}

pr1646v2ATMFwPerFrDlciOutPQsH24PerformanceEirTxOcts OBJECT-TYPE
   SYNTAX      Counter64
   MAX-ACCESS  read-only
   STATUS      current
   DESCRIPTION
      "Path: atm.performance.pvcTable.frameRelay.dlciTable.outPriorityQueues.h24Performance.eirTxOctets

       64 bit unsigned wrappable counter."
   ::= {pr1646v2ATMFwPerFrDlciOutPQsH24PerformanceEntry 184549376}

pr1646v2ATMFwPerFrDlciOutPQsH24PerformanceViolTxOcts OBJECT-TYPE
   SYNTAX      Counter64
   MAX-ACCESS  read-only
   STATUS      current
   DESCRIPTION
      "Path: atm.performance.pvcTable.frameRelay.dlciTable.outPriorityQueues.h24Performance.violateTxOctets

       64 bit unsigned wrappable counter."
   ::= {pr1646v2ATMFwPerFrDlciOutPQsH24PerformanceEntry 318767104}

pr1646v2ATMFwPerFrDlciOutPQsH24PerformanceBandwidth OBJECT-TYPE
   SYNTAX      Integer32
   MAX-ACCESS  read-only
   STATUS      current
   DESCRIPTION
      "Path: atm.performance.pvcTable.frameRelay.dlciTable.outPriorityQueues.h24Performance.bandwidth

       unit name = bps
       formula = 8 * ; 8 /"
   ::= {pr1646v2ATMFwPerFrDlciOutPQsH24PerformanceEntry 268435456}

pr1646v2ATMFwPerFrDlciOutPQsD7Performance OBJECT-TYPE
   SYNTAX      SEQUENCE OF Pr1646v2ATMFwPerFrDlciOutPQsD7PerformanceEntry
   MAX-ACCESS  not-accessible
   STATUS      current
   DESCRIPTION
      ""
   ::= {pr1646v2ATMFwPer 503448839}

pr1646v2ATMFwPerFrDlciOutPQsD7PerformanceEntry OBJECT-TYPE
   SYNTAX      Pr1646v2ATMFwPerFrDlciOutPQsD7PerformanceEntry
   MAX-ACCESS  not-accessible
   STATUS      current
   DESCRIPTION
      ""
   INDEX      { pr1646v2ATMFwPerFrDlciOutPQsD7PerformanceGlobalIx,
                pr1646v2ATMFwPerTableIx,
                pr1646v2ATMFwPerFrDlciTableIx,
                pr1646v2ATMFwPerFrDlciOutPQsTableIx,
                pr1646v2ATMFwPerFrDlciOutPQsD7PerformanceTableIx }
   ::= {pr1646v2ATMFwPerFrDlciOutPQsD7Performance 1}

Pr1646v2ATMFwPerFrDlciOutPQsD7PerformanceEntry ::=
   SEQUENCE
      {
      pr1646v2ATMFwPerFrDlciOutPQsD7PerformanceGlobalIx
         GlobalIndex,
      pr1646v2ATMFwPerFrDlciOutPQsD7PerformanceTableIx
         TableIndex,
      pr1646v2ATMFwPerFrDlciOutPQsD7PerformanceSysUpTime
         TimeTicks,
      pr1646v2ATMFwPerFrDlciOutPQsD7PerformanceTotPkts
         Counter64,
      pr1646v2ATMFwPerFrDlciOutPQsD7PerformanceDirTxPkts
         Counter64,
      pr1646v2ATMFwPerFrDlciOutPQsD7PerformanceQdPkts
         Counter64,
      pr1646v2ATMFwPerFrDlciOutPQsD7PerformanceDropPkts
         Counter64,
      pr1646v2ATMFwPerFrDlciOutPQsD7PerformanceRDropPkts
         Counter64,
      pr1646v2ATMFwPerFrDlciOutPQsD7PerformanceCirTxPkts
         Counter64,
      pr1646v2ATMFwPerFrDlciOutPQsD7PerformanceEirTxPkts
         Counter64,
      pr1646v2ATMFwPerFrDlciOutPQsD7PerformanceViolTxPkts
         Counter64,
      pr1646v2ATMFwPerFrDlciOutPQsD7PerformanceTotOcts
         Counter64,
      pr1646v2ATMFwPerFrDlciOutPQsD7PerformanceDirTxOcts
         Counter64,
      pr1646v2ATMFwPerFrDlciOutPQsD7PerformanceQdOcts
         Counter64,
      pr1646v2ATMFwPerFrDlciOutPQsD7PerformanceDropOcts
         Counter64,
      pr1646v2ATMFwPerFrDlciOutPQsD7PerformanceRDropOcts
         Counter64,
      pr1646v2ATMFwPerFrDlciOutPQsD7PerformanceCirTxOcts
         Counter64,
      pr1646v2ATMFwPerFrDlciOutPQsD7PerformanceEirTxOcts
         Counter64,
      pr1646v2ATMFwPerFrDlciOutPQsD7PerformanceViolTxOcts
         Counter64,
      pr1646v2ATMFwPerFrDlciOutPQsD7PerformanceBandwidth
         Integer32
      }

pr1646v2ATMFwPerFrDlciOutPQsD7PerformanceGlobalIx OBJECT-TYPE
   SYNTAX      GlobalIndex
   MAX-ACCESS  not-accessible
   STATUS      current
   DESCRIPTION
      "The value of the tlsCntTreeGlobalIndex of the MANAGED OBJECT."
   ::= {pr1646v2ATMFwPerFrDlciOutPQsD7PerformanceEntry 10}

pr1646v2ATMFwPerFrDlciOutPQsD7PerformanceTableIx OBJECT-TYPE
   SYNTAX      TableIndex
   MAX-ACCESS  not-accessible
   STATUS      current
   DESCRIPTION
      ""
   ::= {pr1646v2ATMFwPerFrDlciOutPQsD7PerformanceEntry 11}

pr1646v2ATMFwPerFrDlciOutPQsD7PerformanceSysUpTime OBJECT-TYPE
   SYNTAX      TimeTicks
   MAX-ACCESS  read-only
   STATUS      current
   DESCRIPTION
      "Path: atm.performance.pvcTable.frameRelay.dlciTable.outPriorityQueues.d7Performance.sysUpTime

       Time in centi-second."
   ::= {pr1646v2ATMFwPerFrDlciOutPQsD7PerformanceEntry 16777216}

pr1646v2ATMFwPerFrDlciOutPQsD7PerformanceTotPkts OBJECT-TYPE
   SYNTAX      Counter64
   MAX-ACCESS  read-only
   STATUS      current
   DESCRIPTION
      "Path: atm.performance.pvcTable.frameRelay.dlciTable.outPriorityQueues.d7Performance.totalPkts

       64 bit unsigned wrappable counter."
   ::= {pr1646v2ATMFwPerFrDlciOutPQsD7PerformanceEntry 234881024}

pr1646v2ATMFwPerFrDlciOutPQsD7PerformanceDirTxPkts OBJECT-TYPE
   SYNTAX      Counter64
   MAX-ACCESS  read-only
   STATUS      current
   DESCRIPTION
      "Path: atm.performance.pvcTable.frameRelay.dlciTable.outPriorityQueues.d7Performance.directTxPkts

       64 bit unsigned wrappable counter."
   ::= {pr1646v2ATMFwPerFrDlciOutPQsD7PerformanceEntry 33554432}

pr1646v2ATMFwPerFrDlciOutPQsD7PerformanceQdPkts OBJECT-TYPE
   SYNTAX      Counter64
   MAX-ACCESS  read-only
   STATUS      current
   DESCRIPTION
      "Path: atm.performance.pvcTable.frameRelay.dlciTable.outPriorityQueues.d7Performance.queuedPkts

       64 bit unsigned wrappable counter."
   ::= {pr1646v2ATMFwPerFrDlciOutPQsD7PerformanceEntry 50331648}

pr1646v2ATMFwPerFrDlciOutPQsD7PerformanceDropPkts OBJECT-TYPE
   SYNTAX      Counter64
   MAX-ACCESS  read-only
   STATUS      current
   DESCRIPTION
      "Path: atm.performance.pvcTable.frameRelay.dlciTable.outPriorityQueues.d7Performance.droppedPkts

       64 bit unsigned wrappable counter."
   ::= {pr1646v2ATMFwPerFrDlciOutPQsD7PerformanceEntry 67108864}

pr1646v2ATMFwPerFrDlciOutPQsD7PerformanceRDropPkts OBJECT-TYPE
   SYNTAX      Counter64
   MAX-ACCESS  read-only
   STATUS      current
   DESCRIPTION
      "Path: atm.performance.pvcTable.frameRelay.dlciTable.outPriorityQueues.d7Performance.redDroppedPkts

       64 bit unsigned wrappable counter."
   ::= {pr1646v2ATMFwPerFrDlciOutPQsD7PerformanceEntry 201326592}

pr1646v2ATMFwPerFrDlciOutPQsD7PerformanceCirTxPkts OBJECT-TYPE
   SYNTAX      Counter64
   MAX-ACCESS  read-only
   STATUS      current
   DESCRIPTION
      "Path: atm.performance.pvcTable.frameRelay.dlciTable.outPriorityQueues.d7Performance.cirTxPkts

       64 bit unsigned wrappable counter."
   ::= {pr1646v2ATMFwPerFrDlciOutPQsD7PerformanceEntry 83886080}

pr1646v2ATMFwPerFrDlciOutPQsD7PerformanceEirTxPkts OBJECT-TYPE
   SYNTAX      Counter64
   MAX-ACCESS  read-only
   STATUS      current
   DESCRIPTION
      "Path: atm.performance.pvcTable.frameRelay.dlciTable.outPriorityQueues.d7Performance.eirTxPkts

       64 bit unsigned wrappable counter."
   ::= {pr1646v2ATMFwPerFrDlciOutPQsD7PerformanceEntry 100663296}

pr1646v2ATMFwPerFrDlciOutPQsD7PerformanceViolTxPkts OBJECT-TYPE
   SYNTAX      Counter64
   MAX-ACCESS  read-only
   STATUS      current
   DESCRIPTION
      "Path: atm.performance.pvcTable.frameRelay.dlciTable.outPriorityQueues.d7Performance.violateTxPkts

       64 bit unsigned wrappable counter."
   ::= {pr1646v2ATMFwPerFrDlciOutPQsD7PerformanceEntry 301989888}

pr1646v2ATMFwPerFrDlciOutPQsD7PerformanceTotOcts OBJECT-TYPE
   SYNTAX      Counter64
   MAX-ACCESS  read-only
   STATUS      current
   DESCRIPTION
      "Path: atm.performance.pvcTable.frameRelay.dlciTable.outPriorityQueues.d7Performance.totalOctets

       64 bit unsigned wrappable counter."
   ::= {pr1646v2ATMFwPerFrDlciOutPQsD7PerformanceEntry 251658240}

pr1646v2ATMFwPerFrDlciOutPQsD7PerformanceDirTxOcts OBJECT-TYPE
   SYNTAX      Counter64
   MAX-ACCESS  read-only
   STATUS      current
   DESCRIPTION
      "Path: atm.performance.pvcTable.frameRelay.dlciTable.outPriorityQueues.d7Performance.directTxOctets

       64 bit unsigned wrappable counter."
   ::= {pr1646v2ATMFwPerFrDlciOutPQsD7PerformanceEntry 117440512}

pr1646v2ATMFwPerFrDlciOutPQsD7PerformanceQdOcts OBJECT-TYPE
   SYNTAX      Counter64
   MAX-ACCESS  read-only
   STATUS      current
   DESCRIPTION
      "Path: atm.performance.pvcTable.frameRelay.dlciTable.outPriorityQueues.d7Performance.queuedOctets

       64 bit unsigned wrappable counter."
   ::= {pr1646v2ATMFwPerFrDlciOutPQsD7PerformanceEntry 134217728}

pr1646v2ATMFwPerFrDlciOutPQsD7PerformanceDropOcts OBJECT-TYPE
   SYNTAX      Counter64
   MAX-ACCESS  read-only
   STATUS      current
   DESCRIPTION
      "Path: atm.performance.pvcTable.frameRelay.dlciTable.outPriorityQueues.d7Performance.droppedOctets

       64 bit unsigned wrappable counter."
   ::= {pr1646v2ATMFwPerFrDlciOutPQsD7PerformanceEntry 150994944}

pr1646v2ATMFwPerFrDlciOutPQsD7PerformanceRDropOcts OBJECT-TYPE
   SYNTAX      Counter64
   MAX-ACCESS  read-only
   STATUS      current
   DESCRIPTION
      "Path: atm.performance.pvcTable.frameRelay.dlciTable.outPriorityQueues.d7Performance.redDroppedOctets

       64 bit unsigned wrappable counter."
   ::= {pr1646v2ATMFwPerFrDlciOutPQsD7PerformanceEntry 218103808}

pr1646v2ATMFwPerFrDlciOutPQsD7PerformanceCirTxOcts OBJECT-TYPE
   SYNTAX      Counter64
   MAX-ACCESS  read-only
   STATUS      current
   DESCRIPTION
      "Path: atm.performance.pvcTable.frameRelay.dlciTable.outPriorityQueues.d7Performance.cirTxOctets

       64 bit unsigned wrappable counter."
   ::= {pr1646v2ATMFwPerFrDlciOutPQsD7PerformanceEntry 167772160}

pr1646v2ATMFwPerFrDlciOutPQsD7PerformanceEirTxOcts OBJECT-TYPE
   SYNTAX      Counter64
   MAX-ACCESS  read-only
   STATUS      current
   DESCRIPTION
      "Path: atm.performance.pvcTable.frameRelay.dlciTable.outPriorityQueues.d7Performance.eirTxOctets

       64 bit unsigned wrappable counter."
   ::= {pr1646v2ATMFwPerFrDlciOutPQsD7PerformanceEntry 184549376}

pr1646v2ATMFwPerFrDlciOutPQsD7PerformanceViolTxOcts OBJECT-TYPE
   SYNTAX      Counter64
   MAX-ACCESS  read-only
   STATUS      current
   DESCRIPTION
      "Path: atm.performance.pvcTable.frameRelay.dlciTable.outPriorityQueues.d7Performance.violateTxOctets

       64 bit unsigned wrappable counter."
   ::= {pr1646v2ATMFwPerFrDlciOutPQsD7PerformanceEntry 318767104}

pr1646v2ATMFwPerFrDlciOutPQsD7PerformanceBandwidth OBJECT-TYPE
   SYNTAX      Integer32
   MAX-ACCESS  read-only
   STATUS      current
   DESCRIPTION
      "Path: atm.performance.pvcTable.frameRelay.dlciTable.outPriorityQueues.d7Performance.bandwidth

       unit name = bps
       formula = 8 * ; 8 /"
   ::= {pr1646v2ATMFwPerFrDlciOutPQsD7PerformanceEntry 268435456}



ar1646v2ATMFw OBJECT IDENTIFIER ::= {r1646v2ATMFw 16}


ar1646v2ATMFwClearCounters OBJECT IDENTIFIER ::= {ar1646v2ATMFw 263}

ar1646v2ATMFwClearCountersTable OBJECT-TYPE
   SYNTAX      SEQUENCE OF Ar1646v2ATMFwClearCountersEntry
   MAX-ACCESS  not-accessible
   STATUS      current
   DESCRIPTION
      "reset counters"
   ::= {ar1646v2ATMFwClearCounters 1}

ar1646v2ATMFwClearCountersEntry OBJECT-TYPE
   SYNTAX      Ar1646v2ATMFwClearCountersEntry
   MAX-ACCESS  not-accessible
   STATUS      current
   DESCRIPTION
      ""
   INDEX      { ar1646v2ATMFwClearCountersGlobalIx }
   ::= {ar1646v2ATMFwClearCountersTable 1}

Ar1646v2ATMFwClearCountersEntry ::=
   SEQUENCE
      {
      ar1646v2ATMFwClearCountersGlobalIx
         GlobalIndex,
      ar1646v2ATMFwClearCountersValue
         Integer32
      }

ar1646v2ATMFwClearCountersGlobalIx OBJECT-TYPE
   SYNTAX      GlobalIndex
   MAX-ACCESS  not-accessible
   STATUS      current
   DESCRIPTION
      "The value of the tlsCntTreeGlobalIndex of the MANAGED OBJECT."
   ::= {ar1646v2ATMFwClearCountersEntry 10}

ar1646v2ATMFwClearCountersValue OBJECT-TYPE
   SYNTAX      Integer32
   MAX-ACCESS  read-write
   STATUS      current
   DESCRIPTION
      "Path: atm.actions.clearCounters"
   ::= {ar1646v2ATMFwClearCountersEntry 2147483648}



END
