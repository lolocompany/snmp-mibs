OneAccess-R1645v2-2284-ShEndLin DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2ShEndLin OBJECT IDENTIFIER ::= {r1645Rootv2 2284}

r1645v2ShEndLinMOProp OBJECT-TYPE
   SYNTAX      SEQUENCE OF R1645v2ShEndLinMOPropEntry
   MAX-ACCESS  not-accessible
   STATUS      current
   DESCRIPTION
      ""
   ::= {r1645v2ShEndLin 1}

r1645v2ShEndLinMOPropEntry OBJECT-TYPE
   SYNTAX      R1645v2ShEndLinMOPropEntry
   MAX-ACCESS  not-accessible
   STATUS      current
   DESCRIPTION
      ""
   INDEX      { r1645v2ShEndLinMOPropGlobalIx }
   ::= {r1645v2ShEndLinMOProp 1}

R1645v2ShEndLinMOPropEntry ::=
   SEQUENCE
      {
      r1645v2ShEndLinMOPropPath
         ContainmentPath,
      r1645v2ShEndLinMOPropRev
         ObjectRevision,
      r1645v2ShEndLinMOPropGlobalIx
         GlobalIndex
      }

r1645v2ShEndLinMOPropPath OBJECT-TYPE
   SYNTAX      ContainmentPath
   MAX-ACCESS  read-only
   STATUS      current
   DESCRIPTION
      "Textual description of the containment tree from the instance of
       the root object down to the instance of the current object."
   ::= {r1645v2ShEndLinMOPropEntry 3}

r1645v2ShEndLinMOPropRev OBJECT-TYPE
   SYNTAX      ObjectRevision
   MAX-ACCESS  read-only
   STATUS      current
   DESCRIPTION
      "This value corresponds with the revision of the MANAGED OBJECT."
   ::= {r1645v2ShEndLinMOPropEntry 4}

r1645v2ShEndLinMOPropGlobalIx OBJECT-TYPE
   SYNTAX      GlobalIndex
   MAX-ACCESS  read-only
   STATUS      current
   DESCRIPTION
      "The value of the tlsCntTreeGlobalIndex of the MANAGED OBJECT."
   ::= {r1645v2ShEndLinMOPropEntry 10}



pr1645v2ShEndLin OBJECT IDENTIFIER ::= {r1645v2ShEndLin 12}


pr1645v2ShEndLinH2 OBJECT IDENTIFIER ::= {pr1645v2ShEndLin 21}

pr1645v2ShEndLinH2SSCTable OBJECT-TYPE
   SYNTAX      SEQUENCE OF Pr1645v2ShEndLinH2Entry
   MAX-ACCESS  not-accessible
   STATUS      current
   DESCRIPTION
      "h2Line"
   ::= {pr1645v2ShEndLinH2 1}

pr1645v2ShEndLinH2Entry OBJECT-TYPE
   SYNTAX      Pr1645v2ShEndLinH2Entry
   MAX-ACCESS  not-accessible
   STATUS      current
   DESCRIPTION
      ""
   INDEX      { pr1645v2ShEndLinH2GlobalIx,
                pr1645v2ShEndLinH2TableIx }
   ::= {pr1645v2ShEndLinH2SSCTable 1}

Pr1645v2ShEndLinH2Entry ::=
   SEQUENCE
      {
      pr1645v2ShEndLinH2GlobalIx
         GlobalIndex,
      pr1645v2ShEndLinH2TableIx
         TableIndex,
      pr1645v2ShEndLinH2SysUpTime
         TimeTicks,
      pr1645v2ShEndLinH2LDownCnt
         Counter32,
      pr1645v2ShEndLinH2LDownTme
         TimeTicks
      }

pr1645v2ShEndLinH2GlobalIx OBJECT-TYPE
   SYNTAX      GlobalIndex
   MAX-ACCESS  not-accessible
   STATUS      current
   DESCRIPTION
      "The value of the tlsCntTreeGlobalIndex of the MANAGED OBJECT."
   ::= {pr1645v2ShEndLinH2Entry 10}

pr1645v2ShEndLinH2TableIx OBJECT-TYPE
   SYNTAX      TableIndex
   MAX-ACCESS  not-accessible
   STATUS      current
   DESCRIPTION
      ""
   ::= {pr1645v2ShEndLinH2Entry 11}

pr1645v2ShEndLinH2SysUpTime OBJECT-TYPE
   SYNTAX      TimeTicks
   MAX-ACCESS  read-only
   STATUS      current
   DESCRIPTION
      "Path: end.performance.h2Line.sysUpTime

       Time in centi-second."
   ::= {pr1645v2ShEndLinH2Entry 16777216}

pr1645v2ShEndLinH2LDownCnt OBJECT-TYPE
   SYNTAX      Counter32
   MAX-ACCESS  read-only
   STATUS      current
   DESCRIPTION
      "Path: end.performance.h2Line.linkDownCount

       32 bit unsigned wrappable counter."
   ::= {pr1645v2ShEndLinH2Entry 33554432}

pr1645v2ShEndLinH2LDownTme OBJECT-TYPE
   SYNTAX      TimeTicks
   MAX-ACCESS  read-only
   STATUS      current
   DESCRIPTION
      "Path: end.performance.h2Line.linkDownTime

       Time in centi-second."
   ::= {pr1645v2ShEndLinH2Entry 50331648}


pr1645v2ShEndLinH24 OBJECT IDENTIFIER ::= {pr1645v2ShEndLin 23}

pr1645v2ShEndLinH24SSCTable OBJECT-TYPE
   SYNTAX      SEQUENCE OF Pr1645v2ShEndLinH24Entry
   MAX-ACCESS  not-accessible
   STATUS      current
   DESCRIPTION
      "h24Line"
   ::= {pr1645v2ShEndLinH24 1}

pr1645v2ShEndLinH24Entry OBJECT-TYPE
   SYNTAX      Pr1645v2ShEndLinH24Entry
   MAX-ACCESS  not-accessible
   STATUS      current
   DESCRIPTION
      ""
   INDEX      { pr1645v2ShEndLinH24GlobalIx,
                pr1645v2ShEndLinH24TableIx }
   ::= {pr1645v2ShEndLinH24SSCTable 1}

Pr1645v2ShEndLinH24Entry ::=
   SEQUENCE
      {
      pr1645v2ShEndLinH24GlobalIx
         GlobalIndex,
      pr1645v2ShEndLinH24TableIx
         TableIndex,
      pr1645v2ShEndLinH24SysUpTime
         TimeTicks,
      pr1645v2ShEndLinH24LDownCnt
         Counter32,
      pr1645v2ShEndLinH24LDownTme
         TimeTicks
      }

pr1645v2ShEndLinH24GlobalIx OBJECT-TYPE
   SYNTAX      GlobalIndex
   MAX-ACCESS  not-accessible
   STATUS      current
   DESCRIPTION
      "The value of the tlsCntTreeGlobalIndex of the MANAGED OBJECT."
   ::= {pr1645v2ShEndLinH24Entry 10}

pr1645v2ShEndLinH24TableIx OBJECT-TYPE
   SYNTAX      TableIndex
   MAX-ACCESS  not-accessible
   STATUS      current
   DESCRIPTION
      ""
   ::= {pr1645v2ShEndLinH24Entry 11}

pr1645v2ShEndLinH24SysUpTime OBJECT-TYPE
   SYNTAX      TimeTicks
   MAX-ACCESS  read-only
   STATUS      current
   DESCRIPTION
      "Path: end.performance.h24Line.sysUpTime

       Time in centi-second."
   ::= {pr1645v2ShEndLinH24Entry 16777216}

pr1645v2ShEndLinH24LDownCnt OBJECT-TYPE
   SYNTAX      Counter32
   MAX-ACCESS  read-only
   STATUS      current
   DESCRIPTION
      "Path: end.performance.h24Line.linkDownCount

       32 bit unsigned wrappable counter."
   ::= {pr1645v2ShEndLinH24Entry 33554432}

pr1645v2ShEndLinH24LDownTme OBJECT-TYPE
   SYNTAX      TimeTicks
   MAX-ACCESS  read-only
   STATUS      current
   DESCRIPTION
      "Path: end.performance.h24Line.linkDownTime

       Time in centi-second."
   ::= {pr1645v2ShEndLinH24Entry 50331648}


pr1645v2ShEndLinD7 OBJECT IDENTIFIER ::= {pr1645v2ShEndLin 26}

pr1645v2ShEndLinD7SSCTable OBJECT-TYPE
   SYNTAX      SEQUENCE OF Pr1645v2ShEndLinD7Entry
   MAX-ACCESS  not-accessible
   STATUS      current
   DESCRIPTION
      "d7Line"
   ::= {pr1645v2ShEndLinD7 1}

pr1645v2ShEndLinD7Entry OBJECT-TYPE
   SYNTAX      Pr1645v2ShEndLinD7Entry
   MAX-ACCESS  not-accessible
   STATUS      current
   DESCRIPTION
      ""
   INDEX      { pr1645v2ShEndLinD7GlobalIx,
                pr1645v2ShEndLinD7TableIx }
   ::= {pr1645v2ShEndLinD7SSCTable 1}

Pr1645v2ShEndLinD7Entry ::=
   SEQUENCE
      {
      pr1645v2ShEndLinD7GlobalIx
         GlobalIndex,
      pr1645v2ShEndLinD7TableIx
         TableIndex,
      pr1645v2ShEndLinD7SysUpTime
         TimeTicks,
      pr1645v2ShEndLinD7LDownCnt
         Counter32,
      pr1645v2ShEndLinD7LDownTme
         TimeTicks
      }

pr1645v2ShEndLinD7GlobalIx OBJECT-TYPE
   SYNTAX      GlobalIndex
   MAX-ACCESS  not-accessible
   STATUS      current
   DESCRIPTION
      "The value of the tlsCntTreeGlobalIndex of the MANAGED OBJECT."
   ::= {pr1645v2ShEndLinD7Entry 10}

pr1645v2ShEndLinD7TableIx OBJECT-TYPE
   SYNTAX      TableIndex
   MAX-ACCESS  not-accessible
   STATUS      current
   DESCRIPTION
      ""
   ::= {pr1645v2ShEndLinD7Entry 11}

pr1645v2ShEndLinD7SysUpTime OBJECT-TYPE
   SYNTAX      TimeTicks
   MAX-ACCESS  read-only
   STATUS      current
   DESCRIPTION
      "Path: end.performance.d7Line.sysUpTime

       Time in centi-second."
   ::= {pr1645v2ShEndLinD7Entry 16777216}

pr1645v2ShEndLinD7LDownCnt OBJECT-TYPE
   SYNTAX      Counter32
   MAX-ACCESS  read-only
   STATUS      current
   DESCRIPTION
      "Path: end.performance.d7Line.linkDownCount

       32 bit unsigned wrappable counter."
   ::= {pr1645v2ShEndLinD7Entry 33554432}

pr1645v2ShEndLinD7LDownTme OBJECT-TYPE
   SYNTAX      TimeTicks
   MAX-ACCESS  read-only
   STATUS      current
   DESCRIPTION
      "Path: end.performance.d7Line.linkDownTime

       Time in centi-second."
   ::= {pr1645v2ShEndLinD7Entry 50331648}


pr1645v2ShEndLinRel OBJECT IDENTIFIER ::= {pr1645v2ShEndLin 30}

pr1645v2ShEndLinRelSSCTable OBJECT-TYPE
   SYNTAX      SEQUENCE OF Pr1645v2ShEndLinRelEntry
   MAX-ACCESS  not-accessible
   STATUS      current
   DESCRIPTION
      "relLine"
   ::= {pr1645v2ShEndLinRel 1}

pr1645v2ShEndLinRelEntry OBJECT-TYPE
   SYNTAX      Pr1645v2ShEndLinRelEntry
   MAX-ACCESS  not-accessible
   STATUS      current
   DESCRIPTION
      ""
   INDEX      { pr1645v2ShEndLinRelGlobalIx }
   ::= {pr1645v2ShEndLinRelSSCTable 1}

Pr1645v2ShEndLinRelEntry ::=
   SEQUENCE
      {
      pr1645v2ShEndLinRelGlobalIx
         GlobalIndex,
      pr1645v2ShEndLinRelLDownCnt
         Counter32,
      pr1645v2ShEndLinRelLDownTme
         TimeTicks
      }

pr1645v2ShEndLinRelGlobalIx OBJECT-TYPE
   SYNTAX      GlobalIndex
   MAX-ACCESS  not-accessible
   STATUS      current
   DESCRIPTION
      "The value of the tlsCntTreeGlobalIndex of the MANAGED OBJECT."
   ::= {pr1645v2ShEndLinRelEntry 10}

pr1645v2ShEndLinRelLDownCnt OBJECT-TYPE
   SYNTAX      Counter32
   MAX-ACCESS  read-only
   STATUS      current
   DESCRIPTION
      "Path: end.performance.line.linkDownCount

       32 bit unsigned wrappable counter."
   ::= {pr1645v2ShEndLinRelEntry 16777216}

pr1645v2ShEndLinRelLDownTme OBJECT-TYPE
   SYNTAX      TimeTicks
   MAX-ACCESS  read-only
   STATUS      current
   DESCRIPTION
      "Path: end.performance.line.linkDownTime

       Time in centi-second."
   ::= {pr1645v2ShEndLinRelEntry 33554432}



ar1645v2ShEndLin OBJECT IDENTIFIER ::= {r1645v2ShEndLin 16}


ar1645v2ShEndLinClearCounters OBJECT IDENTIFIER ::= {ar1645v2ShEndLin 263}

ar1645v2ShEndLinClearCountersTable OBJECT-TYPE
   SYNTAX      SEQUENCE OF Ar1645v2ShEndLinClearCountersEntry
   MAX-ACCESS  not-accessible
   STATUS      current
   DESCRIPTION
      "reset counters"
   ::= {ar1645v2ShEndLinClearCounters 1}

ar1645v2ShEndLinClearCountersEntry OBJECT-TYPE
   SYNTAX      Ar1645v2ShEndLinClearCountersEntry
   MAX-ACCESS  not-accessible
   STATUS      current
   DESCRIPTION
      ""
   INDEX      { ar1645v2ShEndLinClearCountersGlobalIx }
   ::= {ar1645v2ShEndLinClearCountersTable 1}

Ar1645v2ShEndLinClearCountersEntry ::=
   SEQUENCE
      {
      ar1645v2ShEndLinClearCountersGlobalIx
         GlobalIndex,
      ar1645v2ShEndLinClearCountersValue
         Integer32
      }

ar1645v2ShEndLinClearCountersGlobalIx OBJECT-TYPE
   SYNTAX      GlobalIndex
   MAX-ACCESS  not-accessible
   STATUS      current
   DESCRIPTION
      "The value of the tlsCntTreeGlobalIndex of the MANAGED OBJECT."
   ::= {ar1645v2ShEndLinClearCountersEntry 10}

ar1645v2ShEndLinClearCountersValue OBJECT-TYPE
   SYNTAX      Integer32
   MAX-ACCESS  read-write
   STATUS      current
   DESCRIPTION
      "Path: end.actions.clearCounters"
   ::= {ar1645v2ShEndLinClearCountersEntry 2147483648}


ar1645v2ShEndLinLoopbActivation OBJECT IDENTIFIER ::= {ar1645v2ShEndLin 150}

ar1645v2ShEndLinLoopbActivationTable OBJECT-TYPE
   SYNTAX      SEQUENCE OF Ar1645v2ShEndLinLoopbActivationEntry
   MAX-ACCESS  not-accessible
   STATUS      current
   DESCRIPTION
      "loopbackActivation"
   ::= {ar1645v2ShEndLinLoopbActivation 1}

ar1645v2ShEndLinLoopbActivationEntry OBJECT-TYPE
   SYNTAX      Ar1645v2ShEndLinLoopbActivationEntry
   MAX-ACCESS  not-accessible
   STATUS      current
   DESCRIPTION
      ""
   INDEX      { ar1645v2ShEndLinLoopbActivationGlobalIx }
   ::= {ar1645v2ShEndLinLoopbActivationTable 1}

Ar1645v2ShEndLinLoopbActivationEntry ::=
   SEQUENCE
      {
      ar1645v2ShEndLinLoopbActivationGlobalIx
         GlobalIndex,
      ar1645v2ShEndLinLoopbActivationValue
         Integer32
      }

ar1645v2ShEndLinLoopbActivationGlobalIx OBJECT-TYPE
   SYNTAX      GlobalIndex
   MAX-ACCESS  not-accessible
   STATUS      current
   DESCRIPTION
      "The value of the tlsCntTreeGlobalIndex of the MANAGED OBJECT."
   ::= {ar1645v2ShEndLinLoopbActivationEntry 10}

ar1645v2ShEndLinLoopbActivationValue OBJECT-TYPE
   SYNTAX      Integer32
   MAX-ACCESS  read-write
   STATUS      current
   DESCRIPTION
      "Path: end.actions.loopbActivation"
   ::= {ar1645v2ShEndLinLoopbActivationEntry 2147483648}


ar1645v2ShEndLinTestActivationType OBJECT IDENTIFIER ::= {ar1645v2ShEndLin 99}

ar1645v2ShEndLinTestActivationTypeTable OBJECT-TYPE
   SYNTAX      SEQUENCE OF Ar1645v2ShEndLinTestActivationTypeEntry
   MAX-ACCESS  not-accessible
   STATUS      current
   DESCRIPTION
      "loopbackActivationType"
   ::= {ar1645v2ShEndLinTestActivationType 1}

ar1645v2ShEndLinTestActivationTypeEntry OBJECT-TYPE
   SYNTAX      Ar1645v2ShEndLinTestActivationTypeEntry
   MAX-ACCESS  not-accessible
   STATUS      current
   DESCRIPTION
      ""
   INDEX      { ar1645v2ShEndLinTestActivationTypeGlobalIx }
   ::= {ar1645v2ShEndLinTestActivationTypeTable 1}

Ar1645v2ShEndLinTestActivationTypeEntry ::=
   SEQUENCE
      {
      ar1645v2ShEndLinTestActivationTypeGlobalIx
         GlobalIndex,
      ar1645v2ShEndLinTestActivationTypeValue
         INTEGER
      }

ar1645v2ShEndLinTestActivationTypeGlobalIx OBJECT-TYPE
   SYNTAX      GlobalIndex
   MAX-ACCESS  not-accessible
   STATUS      current
   DESCRIPTION
      "The value of the tlsCntTreeGlobalIndex of the MANAGED OBJECT."
   ::= {ar1645v2ShEndLinTestActivationTypeEntry 10}

ar1645v2ShEndLinTestActivationTypeValue OBJECT-TYPE
   SYNTAX      INTEGER
               {
               customerLoopback (4),
               networkLoopback (8),
               no (64)
               }
   MAX-ACCESS  read-write
   STATUS      current
   DESCRIPTION
      "Path: end.actions.testActivationType

       Possibilities:
               customerLoopback   (4)
               networkLoopback   (8)
               no   (64)"
   ::= {ar1645v2ShEndLinTestActivationTypeEntry 2147483648}



sr1645v2ShEndLin OBJECT IDENTIFIER ::= {r1645v2ShEndLin 14}


sr1645v2ShEndLinVendId OBJECT IDENTIFIER ::= {sr1645v2ShEndLin 110}

sr1645v2ShEndLinVendIdSSCTable OBJECT-TYPE
   SYNTAX      SEQUENCE OF Sr1645v2ShEndLinVendIdEntry
   MAX-ACCESS  not-accessible
   STATUS      current
   DESCRIPTION
      "vendor ID"
   ::= {sr1645v2ShEndLinVendId 1}

sr1645v2ShEndLinVendIdEntry OBJECT-TYPE
   SYNTAX      Sr1645v2ShEndLinVendIdEntry
   MAX-ACCESS  not-accessible
   STATUS      current
   DESCRIPTION
      ""
   INDEX      { sr1645v2ShEndLinVendIdGlobalIx }
   ::= {sr1645v2ShEndLinVendIdSSCTable 1}

Sr1645v2ShEndLinVendIdEntry ::=
   SEQUENCE
      {
      sr1645v2ShEndLinVendIdGlobalIx
         GlobalIndex,
      sr1645v2ShEndLinVendIdCountryCode
         INTEGER,
      sr1645v2ShEndLinVendIdProviderCode
         DisplayString,
      sr1645v2ShEndLinVendIdVendorSpec
         Integer32
      }

sr1645v2ShEndLinVendIdGlobalIx OBJECT-TYPE
   SYNTAX      GlobalIndex
   MAX-ACCESS  not-accessible
   STATUS      current
   DESCRIPTION
      "The value of the tlsCntTreeGlobalIndex of the MANAGED OBJECT."
   ::= {sr1645v2ShEndLinVendIdEntry 10}

sr1645v2ShEndLinVendIdCountryCode OBJECT-TYPE
   SYNTAX      INTEGER
               {
               japan (65280),
               germany (65284),
               belgium (65295),
               denmark (65329),
               finland (65340),
               france (65341),
               greece (65350),
               hungary (65361),
               ireland (65367),
               italy (65369),
               netherlands (65403),
               poland (65418),
               portugal (65419),
               spain (65440),
               sweden (65445),
               switzerland (65446),
               unitedsKingdom (65460),
               unitedsStates (65461)
               }
   MAX-ACCESS  read-only
   STATUS      current
   DESCRIPTION
      "Path: end.status.vendorId.countryCode

       Possibilities:
               Japan   (65280)
               Germany   (65284)
               Belgium   (65295)
               Denmark   (65329)
               Finland   (65340)
               France   (65341)
               Greece   (65350)
               Hungary   (65361)
               Ireland   (65367)
               Italy   (65369)
               Netherlands   (65403)
               Poland   (65418)
               Portugal   (65419)
               Spain   (65440)
               Sweden   (65445)
               Switzerland   (65446)
               United Kingdom   (65460)
               United States   (65461)"
   ::= {sr1645v2ShEndLinVendIdEntry 16777216}

sr1645v2ShEndLinVendIdProviderCode OBJECT-TYPE
   SYNTAX      DisplayString
   MAX-ACCESS  read-only
   STATUS      current
   DESCRIPTION
      "Path: end.status.vendorId.providerCode"
   ::= {sr1645v2ShEndLinVendIdEntry 33554432}

sr1645v2ShEndLinVendIdVendorSpec OBJECT-TYPE
   SYNTAX      Integer32
   MAX-ACCESS  read-only
   STATUS      current
   DESCRIPTION
      "Path: end.status.vendorId.vendorSpecific"
   ::= {sr1645v2ShEndLinVendIdEntry 50331648}


sr1645v2ShEndLinVendorModel OBJECT IDENTIFIER ::= {sr1645v2ShEndLin 111}

sr1645v2ShEndLinVendorModelTable OBJECT-TYPE
   SYNTAX      SEQUENCE OF Sr1645v2ShEndLinVendorModelEntry
   MAX-ACCESS  not-accessible
   STATUS      current
   DESCRIPTION
      "vendor model"
   ::= {sr1645v2ShEndLinVendorModel 1}

sr1645v2ShEndLinVendorModelEntry OBJECT-TYPE
   SYNTAX      Sr1645v2ShEndLinVendorModelEntry
   MAX-ACCESS  not-accessible
   STATUS      current
   DESCRIPTION
      ""
   INDEX      { sr1645v2ShEndLinVendorModelGlobalIx }
   ::= {sr1645v2ShEndLinVendorModelTable 1}

Sr1645v2ShEndLinVendorModelEntry ::=
   SEQUENCE
      {
      sr1645v2ShEndLinVendorModelGlobalIx
         GlobalIndex,
      sr1645v2ShEndLinVendorModelValue
         DisplayString
      }

sr1645v2ShEndLinVendorModelGlobalIx OBJECT-TYPE
   SYNTAX      GlobalIndex
   MAX-ACCESS  not-accessible
   STATUS      current
   DESCRIPTION
      "The value of the tlsCntTreeGlobalIndex of the MANAGED OBJECT."
   ::= {sr1645v2ShEndLinVendorModelEntry 10}

sr1645v2ShEndLinVendorModelValue OBJECT-TYPE
   SYNTAX      DisplayString
   MAX-ACCESS  read-only
   STATUS      current
   DESCRIPTION
      "Path: end.status.vendorModel"
   ::= {sr1645v2ShEndLinVendorModelEntry 2147483648}


sr1645v2ShEndLinVendorSerial OBJECT IDENTIFIER ::= {sr1645v2ShEndLin 112}

sr1645v2ShEndLinVendorSerialTable OBJECT-TYPE
   SYNTAX      SEQUENCE OF Sr1645v2ShEndLinVendorSerialEntry
   MAX-ACCESS  not-accessible
   STATUS      current
   DESCRIPTION
      "vendor serial nr"
   ::= {sr1645v2ShEndLinVendorSerial 1}

sr1645v2ShEndLinVendorSerialEntry OBJECT-TYPE
   SYNTAX      Sr1645v2ShEndLinVendorSerialEntry
   MAX-ACCESS  not-accessible
   STATUS      current
   DESCRIPTION
      ""
   INDEX      { sr1645v2ShEndLinVendorSerialGlobalIx }
   ::= {sr1645v2ShEndLinVendorSerialTable 1}

Sr1645v2ShEndLinVendorSerialEntry ::=
   SEQUENCE
      {
      sr1645v2ShEndLinVendorSerialGlobalIx
         GlobalIndex,
      sr1645v2ShEndLinVendorSerialValue
         DisplayString
      }

sr1645v2ShEndLinVendorSerialGlobalIx OBJECT-TYPE
   SYNTAX      GlobalIndex
   MAX-ACCESS  not-accessible
   STATUS      current
   DESCRIPTION
      "The value of the tlsCntTreeGlobalIndex of the MANAGED OBJECT."
   ::= {sr1645v2ShEndLinVendorSerialEntry 10}

sr1645v2ShEndLinVendorSerialValue OBJECT-TYPE
   SYNTAX      DisplayString
   MAX-ACCESS  read-only
   STATUS      current
   DESCRIPTION
      "Path: end.status.vendorSerial"
   ::= {sr1645v2ShEndLinVendorSerialEntry 2147483648}


sr1645v2ShEndLinVendorSoftVersion OBJECT IDENTIFIER ::= {sr1645v2ShEndLin 113}

sr1645v2ShEndLinVendorSoftVersionTable OBJECT-TYPE
   SYNTAX      SEQUENCE OF Sr1645v2ShEndLinVendorSoftVersionEntry
   MAX-ACCESS  not-accessible
   STATUS      current
   DESCRIPTION
      "vendor software version"
   ::= {sr1645v2ShEndLinVendorSoftVersion 1}

sr1645v2ShEndLinVendorSoftVersionEntry OBJECT-TYPE
   SYNTAX      Sr1645v2ShEndLinVendorSoftVersionEntry
   MAX-ACCESS  not-accessible
   STATUS      current
   DESCRIPTION
      ""
   INDEX      { sr1645v2ShEndLinVendorSoftVersionGlobalIx }
   ::= {sr1645v2ShEndLinVendorSoftVersionTable 1}

Sr1645v2ShEndLinVendorSoftVersionEntry ::=
   SEQUENCE
      {
      sr1645v2ShEndLinVendorSoftVersionGlobalIx
         GlobalIndex,
      sr1645v2ShEndLinVendorSoftVersionValue
         DisplayString
      }

sr1645v2ShEndLinVendorSoftVersionGlobalIx OBJECT-TYPE
   SYNTAX      GlobalIndex
   MAX-ACCESS  not-accessible
   STATUS      current
   DESCRIPTION
      "The value of the tlsCntTreeGlobalIndex of the MANAGED OBJECT."
   ::= {sr1645v2ShEndLinVendorSoftVersionEntry 10}

sr1645v2ShEndLinVendorSoftVersionValue OBJECT-TYPE
   SYNTAX      DisplayString
   MAX-ACCESS  read-only
   STATUS      current
   DESCRIPTION
      "Path: end.status.vendorSoftVersion"
   ::= {sr1645v2ShEndLinVendorSoftVersionEntry 2147483648}


sr1645v2ShEndLinEocSoftVersion OBJECT IDENTIFIER ::= {sr1645v2ShEndLin 114}

sr1645v2ShEndLinEocSoftVersionTable OBJECT-TYPE
   SYNTAX      SEQUENCE OF Sr1645v2ShEndLinEocSoftVersionEntry
   MAX-ACCESS  not-accessible
   STATUS      current
   DESCRIPTION
      "vendor Eoc software version"
   ::= {sr1645v2ShEndLinEocSoftVersion 1}

sr1645v2ShEndLinEocSoftVersionEntry OBJECT-TYPE
   SYNTAX      Sr1645v2ShEndLinEocSoftVersionEntry
   MAX-ACCESS  not-accessible
   STATUS      current
   DESCRIPTION
      ""
   INDEX      { sr1645v2ShEndLinEocSoftVersionGlobalIx }
   ::= {sr1645v2ShEndLinEocSoftVersionTable 1}

Sr1645v2ShEndLinEocSoftVersionEntry ::=
   SEQUENCE
      {
      sr1645v2ShEndLinEocSoftVersionGlobalIx
         GlobalIndex,
      sr1645v2ShEndLinEocSoftVersionValue
         Integer32
      }

sr1645v2ShEndLinEocSoftVersionGlobalIx OBJECT-TYPE
   SYNTAX      GlobalIndex
   MAX-ACCESS  not-accessible
   STATUS      current
   DESCRIPTION
      "The value of the tlsCntTreeGlobalIndex of the MANAGED OBJECT."
   ::= {sr1645v2ShEndLinEocSoftVersionEntry 10}

sr1645v2ShEndLinEocSoftVersionValue OBJECT-TYPE
   SYNTAX      Integer32
   MAX-ACCESS  read-only
   STATUS      current
   DESCRIPTION
      "Path: end.status.eocSoftVersion"
   ::= {sr1645v2ShEndLinEocSoftVersionEntry 2147483648}


sr1645v2ShEndLinShdslVersion OBJECT IDENTIFIER ::= {sr1645v2ShEndLin 115}

sr1645v2ShEndLinShdslVersionTable OBJECT-TYPE
   SYNTAX      SEQUENCE OF Sr1645v2ShEndLinShdslVersionEntry
   MAX-ACCESS  not-accessible
   STATUS      current
   DESCRIPTION
      "shdsl version"
   ::= {sr1645v2ShEndLinShdslVersion 1}

sr1645v2ShEndLinShdslVersionEntry OBJECT-TYPE
   SYNTAX      Sr1645v2ShEndLinShdslVersionEntry
   MAX-ACCESS  not-accessible
   STATUS      current
   DESCRIPTION
      ""
   INDEX      { sr1645v2ShEndLinShdslVersionGlobalIx }
   ::= {sr1645v2ShEndLinShdslVersionTable 1}

Sr1645v2ShEndLinShdslVersionEntry ::=
   SEQUENCE
      {
      sr1645v2ShEndLinShdslVersionGlobalIx
         GlobalIndex,
      sr1645v2ShEndLinShdslVersionValue
         Integer32
      }

sr1645v2ShEndLinShdslVersionGlobalIx OBJECT-TYPE
   SYNTAX      GlobalIndex
   MAX-ACCESS  not-accessible
   STATUS      current
   DESCRIPTION
      "The value of the tlsCntTreeGlobalIndex of the MANAGED OBJECT."
   ::= {sr1645v2ShEndLinShdslVersionEntry 10}

sr1645v2ShEndLinShdslVersionValue OBJECT-TYPE
   SYNTAX      Integer32
   MAX-ACCESS  read-only
   STATUS      current
   DESCRIPTION
      "Path: end.status.shdslVersion"
   ::= {sr1645v2ShEndLinShdslVersionEntry 2147483648}


sr1645v2ShEndLinEocState OBJECT IDENTIFIER ::= {sr1645v2ShEndLin 116}

sr1645v2ShEndLinEocStateTable OBJECT-TYPE
   SYNTAX      SEQUENCE OF Sr1645v2ShEndLinEocStateEntry
   MAX-ACCESS  not-accessible
   STATUS      current
   DESCRIPTION
      "eoc state"
   ::= {sr1645v2ShEndLinEocState 1}

sr1645v2ShEndLinEocStateEntry OBJECT-TYPE
   SYNTAX      Sr1645v2ShEndLinEocStateEntry
   MAX-ACCESS  not-accessible
   STATUS      current
   DESCRIPTION
      ""
   INDEX      { sr1645v2ShEndLinEocStateGlobalIx }
   ::= {sr1645v2ShEndLinEocStateTable 1}

Sr1645v2ShEndLinEocStateEntry ::=
   SEQUENCE
      {
      sr1645v2ShEndLinEocStateGlobalIx
         GlobalIndex,
      sr1645v2ShEndLinEocStateValue
         INTEGER
      }

sr1645v2ShEndLinEocStateGlobalIx OBJECT-TYPE
   SYNTAX      GlobalIndex
   MAX-ACCESS  not-accessible
   STATUS      current
   DESCRIPTION
      "The value of the tlsCntTreeGlobalIndex of the MANAGED OBJECT."
   ::= {sr1645v2ShEndLinEocStateEntry 10}

sr1645v2ShEndLinEocStateValue OBJECT-TYPE
   SYNTAX      INTEGER
               {
               offline (0),
               discoverysready (1),
               online (2)
               }
   MAX-ACCESS  read-only
   STATUS      current
   DESCRIPTION
      "Path: end.status.eocState

       Possibilities:
               Offline   (0)
               Discovery ready   (1)
               Online   (2)"
   ::= {sr1645v2ShEndLinEocStateEntry 2147483648}


sr1645v2ShEndLinTestType OBJECT IDENTIFIER ::= {sr1645v2ShEndLin 120}

sr1645v2ShEndLinTestTypeTable OBJECT-TYPE
   SYNTAX      SEQUENCE OF Sr1645v2ShEndLinTestTypeEntry
   MAX-ACCESS  not-accessible
   STATUS      current
   DESCRIPTION
      "test state"
   ::= {sr1645v2ShEndLinTestType 1}

sr1645v2ShEndLinTestTypeEntry OBJECT-TYPE
   SYNTAX      Sr1645v2ShEndLinTestTypeEntry
   MAX-ACCESS  not-accessible
   STATUS      current
   DESCRIPTION
      ""
   INDEX      { sr1645v2ShEndLinTestTypeGlobalIx }
   ::= {sr1645v2ShEndLinTestTypeTable 1}

Sr1645v2ShEndLinTestTypeEntry ::=
   SEQUENCE
      {
      sr1645v2ShEndLinTestTypeGlobalIx
         GlobalIndex,
      sr1645v2ShEndLinTestTypeValue
         INTEGER
      }

sr1645v2ShEndLinTestTypeGlobalIx OBJECT-TYPE
   SYNTAX      GlobalIndex
   MAX-ACCESS  not-accessible
   STATUS      current
   DESCRIPTION
      "The value of the tlsCntTreeGlobalIndex of the MANAGED OBJECT."
   ::= {sr1645v2ShEndLinTestTypeEntry 10}

sr1645v2ShEndLinTestTypeValue OBJECT-TYPE
   SYNTAX      INTEGER
               {
               no (0),
               proprietary (1),
               networkLoopback (2),
               customerLoopback (3)
               }
   MAX-ACCESS  read-only
   STATUS      current
   DESCRIPTION
      "Path: end.status.testType

       Possibilities:
               no   (0)
               proprietary   (1)
               networkLoopback   (2)
               customerLoopback   (3)"
   ::= {sr1645v2ShEndLinTestTypeEntry 2147483648}


sr1645v2ShEndLinEocAlThr OBJECT IDENTIFIER ::= {sr1645v2ShEndLin 130}

sr1645v2ShEndLinEocAlThrSSCTable OBJECT-TYPE
   SYNTAX      SEQUENCE OF Sr1645v2ShEndLinEocAlThrEntry
   MAX-ACCESS  not-accessible
   STATUS      current
   DESCRIPTION
      "on threshold values transmittted by the eoc channel"
   ::= {sr1645v2ShEndLinEocAlThr 1}

sr1645v2ShEndLinEocAlThrEntry OBJECT-TYPE
   SYNTAX      Sr1645v2ShEndLinEocAlThrEntry
   MAX-ACCESS  not-accessible
   STATUS      current
   DESCRIPTION
      ""
   INDEX      { sr1645v2ShEndLinEocAlThrGlobalIx }
   ::= {sr1645v2ShEndLinEocAlThrSSCTable 1}

Sr1645v2ShEndLinEocAlThrEntry ::=
   SEQUENCE
      {
      sr1645v2ShEndLinEocAlThrGlobalIx
         GlobalIndex,
      sr1645v2ShEndLinEocAlThrLineAtt
         Integer32,
      sr1645v2ShEndLinEocAlThrNoiseMargin
         Integer32
      }

sr1645v2ShEndLinEocAlThrGlobalIx OBJECT-TYPE
   SYNTAX      GlobalIndex
   MAX-ACCESS  not-accessible
   STATUS      current
   DESCRIPTION
      "The value of the tlsCntTreeGlobalIndex of the MANAGED OBJECT."
   ::= {sr1645v2ShEndLinEocAlThrEntry 10}

sr1645v2ShEndLinEocAlThrLineAtt OBJECT-TYPE
   SYNTAX      Integer32
   MAX-ACCESS  read-only
   STATUS      current
   DESCRIPTION
      "Path: end.status.eocAlarmThresholds.lineAttenuation

       unit name = dB
       formula = 10 / ; 10 *"
   ::= {sr1645v2ShEndLinEocAlThrEntry 16777216}

sr1645v2ShEndLinEocAlThrNoiseMargin OBJECT-TYPE
   SYNTAX      Integer32
   MAX-ACCESS  read-only
   STATUS      current
   DESCRIPTION
      "Path: end.status.eocAlarmThresholds.noiseMargin

       unit name = dB
       formula = 10 / ; 10 *"
   ::= {sr1645v2ShEndLinEocAlThrEntry 33554432}


sr1645v2ShEndLinSnmpIndex OBJECT IDENTIFIER ::= {sr1645v2ShEndLin 269}

sr1645v2ShEndLinSnmpIndexTable OBJECT-TYPE
   SYNTAX      SEQUENCE OF Sr1645v2ShEndLinSnmpIndexEntry
   MAX-ACCESS  not-accessible
   STATUS      current
   DESCRIPTION
      "SNMP index assigned to this object"
   ::= {sr1645v2ShEndLinSnmpIndex 1}

sr1645v2ShEndLinSnmpIndexEntry OBJECT-TYPE
   SYNTAX      Sr1645v2ShEndLinSnmpIndexEntry
   MAX-ACCESS  not-accessible
   STATUS      current
   DESCRIPTION
      ""
   INDEX      { sr1645v2ShEndLinSnmpIndexGlobalIx }
   ::= {sr1645v2ShEndLinSnmpIndexTable 1}

Sr1645v2ShEndLinSnmpIndexEntry ::=
   SEQUENCE
      {
      sr1645v2ShEndLinSnmpIndexGlobalIx
         GlobalIndex,
      sr1645v2ShEndLinSnmpIndexValue
         Integer32
      }

sr1645v2ShEndLinSnmpIndexGlobalIx OBJECT-TYPE
   SYNTAX      GlobalIndex
   MAX-ACCESS  not-accessible
   STATUS      current
   DESCRIPTION
      "The value of the tlsCntTreeGlobalIndex of the MANAGED OBJECT."
   ::= {sr1645v2ShEndLinSnmpIndexEntry 10}

sr1645v2ShEndLinSnmpIndexValue OBJECT-TYPE
   SYNTAX      Integer32
   MAX-ACCESS  read-only
   STATUS      current
   DESCRIPTION
      "Path: end.status.snmpIndex"
   ::= {sr1645v2ShEndLinSnmpIndexEntry 2147483648}



fr1645v2ShEndLin OBJECT IDENTIFIER ::= {r1645v2ShEndLin 13}


fr1645v2ShEndLinAlInfo OBJECT IDENTIFIER ::= {fr1645v2ShEndLin 202}

fr1645v2ShEndLinAlInfoSSCTable OBJECT-TYPE
   SYNTAX      SEQUENCE OF Fr1645v2ShEndLinAlInfoEntry
   MAX-ACCESS  not-accessible
   STATUS      current
   DESCRIPTION
      "lineAlarmInfo"
   ::= {fr1645v2ShEndLinAlInfo 1}

fr1645v2ShEndLinAlInfoEntry OBJECT-TYPE
   SYNTAX      Fr1645v2ShEndLinAlInfoEntry
   MAX-ACCESS  not-accessible
   STATUS      current
   DESCRIPTION
      ""
   INDEX      { fr1645v2ShEndLinAlInfoGlobalIx }
   ::= {fr1645v2ShEndLinAlInfoSSCTable 1}

Fr1645v2ShEndLinAlInfoEntry ::=
   SEQUENCE
      {
      fr1645v2ShEndLinAlInfoGlobalIx
         GlobalIndex,
      fr1645v2ShEndLinAlInfoDiscr
         Integer32,
      fr1645v2ShEndLinAlInfoCurrAlms
         Integer32,
      fr1645v2ShEndLinAlInfoPrevAlms
         Integer32,
      fr1645v2ShEndLinAlInfoAlMask
         Integer32,
      fr1645v2ShEndLinAlInfoAlLvlLnkDwn
         Integer32,
      fr1645v2ShEndLinAlInfoAlLvlRAlmHgh
         Integer32,
      fr1645v2ShEndLinAlInfoAlLvlRAlmLw
         Integer32,
      fr1645v2ShEndLinAlInfoAlLvlUkwnSt
         Integer32
      }

fr1645v2ShEndLinAlInfoGlobalIx OBJECT-TYPE
   SYNTAX      GlobalIndex
   MAX-ACCESS  not-accessible
   STATUS      current
   DESCRIPTION
      "The value of the tlsCntTreeGlobalIndex of the MANAGED OBJECT."
   ::= {fr1645v2ShEndLinAlInfoEntry 10}

fr1645v2ShEndLinAlInfoDiscr OBJECT-TYPE
   SYNTAX      Integer32
   MAX-ACCESS  read-only
   STATUS      current
   DESCRIPTION
      "Path: end.alarms.alarmInfo.discriminator"
   ::= {fr1645v2ShEndLinAlInfoEntry 16777216}

fr1645v2ShEndLinAlInfoCurrAlms OBJECT-TYPE
   SYNTAX      Integer32
   MAX-ACCESS  read-only
   STATUS      current
   DESCRIPTION
      "Path: end.alarms.alarmInfo.currentAlarms

       Bit meanings:
               bit 0 = linkDown,
               bit 1 = remoteAlarmHigh,
               bit 2 = remoteAlarmLow,
               bit 3 = unknownState"
   ::= {fr1645v2ShEndLinAlInfoEntry 33554432}

fr1645v2ShEndLinAlInfoPrevAlms OBJECT-TYPE
   SYNTAX      Integer32
   MAX-ACCESS  read-only
   STATUS      current
   DESCRIPTION
      "Path: end.alarms.alarmInfo.previousAlarms

       Bit meanings:
               bit 0 = linkDown,
               bit 1 = remoteAlarmHigh,
               bit 2 = remoteAlarmLow,
               bit 3 = unknownState"
   ::= {fr1645v2ShEndLinAlInfoEntry 50331648}

fr1645v2ShEndLinAlInfoAlMask OBJECT-TYPE
   SYNTAX      Integer32
   MAX-ACCESS  read-only
   STATUS      current
   DESCRIPTION
      "Path: end.alarms.alarmInfo.alarmMask

       Bit meanings:
               bit 0 = linkDown,
               bit 1 = remoteAlarmHigh,
               bit 2 = remoteAlarmLow,
               bit 3 = unknownState"
   ::= {fr1645v2ShEndLinAlInfoEntry 67108864}

fr1645v2ShEndLinAlInfoAlLvlLnkDwn OBJECT-TYPE
   SYNTAX      Integer32
   MAX-ACCESS  read-only
   STATUS      current
   DESCRIPTION
      "Path: end.alarms.alarmInfo.alarmLevel.linkDown"
   ::= {fr1645v2ShEndLinAlInfoEntry 83951616}

fr1645v2ShEndLinAlInfoAlLvlRAlmHgh OBJECT-TYPE
   SYNTAX      Integer32
   MAX-ACCESS  read-only
   STATUS      current
   DESCRIPTION
      "Path: end.alarms.alarmInfo.alarmLevel.remoteAlarmHigh"
   ::= {fr1645v2ShEndLinAlInfoEntry 84017152}

fr1645v2ShEndLinAlInfoAlLvlRAlmLw OBJECT-TYPE
   SYNTAX      Integer32
   MAX-ACCESS  read-only
   STATUS      current
   DESCRIPTION
      "Path: end.alarms.alarmInfo.alarmLevel.remoteAlarmLow"
   ::= {fr1645v2ShEndLinAlInfoEntry 84082688}

fr1645v2ShEndLinAlInfoAlLvlUkwnSt OBJECT-TYPE
   SYNTAX      Integer32
   MAX-ACCESS  read-only
   STATUS      current
   DESCRIPTION
      "Path: end.alarms.alarmInfo.alarmLevel.unknownState"
   ::= {fr1645v2ShEndLinAlInfoEntry 84148224}


fr1645v2ShEndLinAlInfoE2 OBJECT IDENTIFIER ::= {fr1645v2ShEndLinAlInfo 2}

fr1645v2ShEndLinAlInfoE2Entry OBJECT IDENTIFIER ::= {fr1645v2ShEndLinAlInfoE2 1}

fr1645v2ShEndLinAlInfoE2LnkDwn OBJECT IDENTIFIER ::= {fr1645v2ShEndLinAlInfoE2Entry 10}

fr1645v2ShEndLinAlInfoE2LnkDwnPfx OBJECT IDENTIFIER ::= {fr1645v2ShEndLinAlInfoE2LnkDwn 0}

fr1645v2ShEndLinAlInfoE2LnkDwnOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'shdslEndLineNm'
                (root='router1645') has changed from the ON to the OFF state."
   ::= {fr1645v2ShEndLinAlInfoE2LnkDwnPfx 1}

fr1645v2ShEndLinAlInfoE2LnkDwnOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'shdslEndLineNm'
                (root='router1645') has changed from the OFF to the ON state."
   ::= {fr1645v2ShEndLinAlInfoE2LnkDwnPfx 2}

fr1645v2ShEndLinAlInfoE2RAlmHgh OBJECT IDENTIFIER ::= {fr1645v2ShEndLinAlInfoE2Entry 11}

fr1645v2ShEndLinAlInfoE2RAlmHghPfx OBJECT IDENTIFIER ::= {fr1645v2ShEndLinAlInfoE2RAlmHgh 0}

fr1645v2ShEndLinAlInfoE2RAlmHghOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'remoteAlarmHigh'
                representing an alarm condition in the alarm word
                of attribute 'alarmInfo' of managed object 'shdslEndLineNm'
                (root='router1645') has changed from the ON to the OFF state."
   ::= {fr1645v2ShEndLinAlInfoE2RAlmHghPfx 1}

fr1645v2ShEndLinAlInfoE2RAlmHghOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'remoteAlarmHigh'
                representing an alarm condition in the alarm word
                of attribute 'alarmInfo' of managed object 'shdslEndLineNm'
                (root='router1645') has changed from the OFF to the ON state."
   ::= {fr1645v2ShEndLinAlInfoE2RAlmHghPfx 2}

fr1645v2ShEndLinAlInfoE2RAlmLw OBJECT IDENTIFIER ::= {fr1645v2ShEndLinAlInfoE2Entry 12}

fr1645v2ShEndLinAlInfoE2RAlmLwPfx OBJECT IDENTIFIER ::= {fr1645v2ShEndLinAlInfoE2RAlmLw 0}

fr1645v2ShEndLinAlInfoE2RAlmLwOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'remoteAlarmLow'
                representing an alarm condition in the alarm word
                of attribute 'alarmInfo' of managed object 'shdslEndLineNm'
                (root='router1645') has changed from the ON to the OFF state."
   ::= {fr1645v2ShEndLinAlInfoE2RAlmLwPfx 1}

fr1645v2ShEndLinAlInfoE2RAlmLwOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'remoteAlarmLow'
                representing an alarm condition in the alarm word
                of attribute 'alarmInfo' of managed object 'shdslEndLineNm'
                (root='router1645') has changed from the OFF to the ON state."
   ::= {fr1645v2ShEndLinAlInfoE2RAlmLwPfx 2}

fr1645v2ShEndLinAlInfoE2UkwnSt OBJECT IDENTIFIER ::= {fr1645v2ShEndLinAlInfoE2Entry 13}

fr1645v2ShEndLinAlInfoE2UkwnStPfx OBJECT IDENTIFIER ::= {fr1645v2ShEndLinAlInfoE2UkwnSt 0}

fr1645v2ShEndLinAlInfoE2UkwnStOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unknownState'
                representing an alarm condition in the alarm word
                of attribute 'alarmInfo' of managed object 'shdslEndLineNm'
                (root='router1645') has changed from the ON to the OFF state."
   ::= {fr1645v2ShEndLinAlInfoE2UkwnStPfx 1}

fr1645v2ShEndLinAlInfoE2UkwnStOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unknownState'
                representing an alarm condition in the alarm word
                of attribute 'alarmInfo' of managed object 'shdslEndLineNm'
                (root='router1645') has changed from the OFF to the ON state."
   ::= {fr1645v2ShEndLinAlInfoE2UkwnStPfx 2}



END
