OneAccess-R1646v2-4601-PbbEthOamE DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2PbbEthOamE OBJECT IDENTIFIER ::= {r1646Rootv2 4601}

r1646v2PbbEthOamEMOProp OBJECT-TYPE
   SYNTAX      SEQUENCE OF R1646v2PbbEthOamEMOPropEntry
   MAX-ACCESS  not-accessible
   STATUS      current
   DESCRIPTION
      ""
   ::= {r1646v2PbbEthOamE 1}

r1646v2PbbEthOamEMOPropEntry OBJECT-TYPE
   SYNTAX      R1646v2PbbEthOamEMOPropEntry
   MAX-ACCESS  not-accessible
   STATUS      current
   DESCRIPTION
      ""
   INDEX      { r1646v2PbbEthOamEMOPropGlobalIx }
   ::= {r1646v2PbbEthOamEMOProp 1}

R1646v2PbbEthOamEMOPropEntry ::=
   SEQUENCE
      {
      r1646v2PbbEthOamEMOPropPath
         ContainmentPath,
      r1646v2PbbEthOamEMOPropRev
         ObjectRevision,
      r1646v2PbbEthOamEMOPropGlobalIx
         GlobalIndex
      }

r1646v2PbbEthOamEMOPropPath OBJECT-TYPE
   SYNTAX      ContainmentPath
   MAX-ACCESS  read-only
   STATUS      current
   DESCRIPTION
      "Textual description of the containment tree from the instance of
       the root object down to the instance of the current object."
   ::= {r1646v2PbbEthOamEMOPropEntry 3}

r1646v2PbbEthOamEMOPropRev OBJECT-TYPE
   SYNTAX      ObjectRevision
   MAX-ACCESS  read-only
   STATUS      current
   DESCRIPTION
      "This value corresponds with the revision of the MANAGED OBJECT."
   ::= {r1646v2PbbEthOamEMOPropEntry 4}

r1646v2PbbEthOamEMOPropGlobalIx OBJECT-TYPE
   SYNTAX      GlobalIndex
   MAX-ACCESS  read-only
   STATUS      current
   DESCRIPTION
      "The value of the tlsCntTreeGlobalIndex of the MANAGED OBJECT."
   ::= {r1646v2PbbEthOamEMOPropEntry 10}



er1646v2PbbEthOamE OBJECT IDENTIFIER ::= {r1646v2PbbEthOamE 11}


er1646v2PbbEthOamEMips OBJECT IDENTIFIER ::= {er1646v2PbbEthOamE 11}

er1646v2PbbEthOamEMipsSSCTable OBJECT-TYPE
   SYNTAX      SEQUENCE OF Er1646v2PbbEthOamEMipsEntry
   MAX-ACCESS  not-accessible
   STATUS      current
   DESCRIPTION
      "table with local MIPs"
   ::= {er1646v2PbbEthOamEMips 1}

er1646v2PbbEthOamEMipsEntry OBJECT-TYPE
   SYNTAX      Er1646v2PbbEthOamEMipsEntry
   MAX-ACCESS  not-accessible
   STATUS      current
   DESCRIPTION
      ""
   INDEX      { er1646v2PbbEthOamEMipsGlobalIx,
                er1646v2PbbEthOamEMipsTableIx }
   ::= {er1646v2PbbEthOamEMipsSSCTable 1}

Er1646v2PbbEthOamEMipsEntry ::=
   SEQUENCE
      {
      er1646v2PbbEthOamEMipsActions
         VariableLengthTableActions,
      er1646v2PbbEthOamEMipsGlobalIx
         GlobalIndex,
      er1646v2PbbEthOamEMipsTableIx
         TableIndex,
      er1646v2PbbEthOamEMipsName
         DisplayString,
      er1646v2PbbEthOamEMipsAdminStatus
         INTEGER,
      er1646v2PbbEthOamEMipsMode
         INTEGER,
      er1646v2PbbEthOamEMipsInterface
         DisplayString,
      er1646v2PbbEthOamEMipsVid
         INTEGER,
      er1646v2PbbEthOamEMipsTpid
         INTEGER,
      er1646v2PbbEthOamEMipsPrioMapQueue
         INTEGER,
      er1646v2PbbEthOamEMipsPrioMapDropLevel
         INTEGER,
      er1646v2PbbEthOamEMipsMegLevel
         Integer32
      }

er1646v2PbbEthOamEMipsActions OBJECT-TYPE
   SYNTAX      VariableLengthTableActions
   MAX-ACCESS  read-write
   STATUS      current
   DESCRIPTION
      "By way of this field, some manipulations
       on this table may be performed."
   ::= {er1646v2PbbEthOamEMipsEntry 2}

er1646v2PbbEthOamEMipsGlobalIx OBJECT-TYPE
   SYNTAX      GlobalIndex
   MAX-ACCESS  not-accessible
   STATUS      current
   DESCRIPTION
      "The value of the tlsCntTreeGlobalIndex of the MANAGED OBJECT."
   ::= {er1646v2PbbEthOamEMipsEntry 10}

er1646v2PbbEthOamEMipsTableIx OBJECT-TYPE
   SYNTAX      TableIndex
   MAX-ACCESS  not-accessible
   STATUS      current
   DESCRIPTION
      ""
   ::= {er1646v2PbbEthOamEMipsEntry 11}

er1646v2PbbEthOamEMipsName OBJECT-TYPE
   SYNTAX      DisplayString
   MAX-ACCESS  read-write
   STATUS      current
   DESCRIPTION
      "Path: ethOam.editConf.mips.name"
   ::= {er1646v2PbbEthOamEMipsEntry 16777216}

er1646v2PbbEthOamEMipsAdminStatus OBJECT-TYPE
   SYNTAX      INTEGER
               {
               up (1),
               down (2)
               }
   MAX-ACCESS  read-write
   STATUS      current
   DESCRIPTION
      "Path: ethOam.editConf.mips.adminStatus

       Possibilities:
               up   (1)
               down   (2)"
   ::= {er1646v2PbbEthOamEMipsEntry 33554432}

er1646v2PbbEthOamEMipsMode OBJECT-TYPE
   SYNTAX      INTEGER
               {
               ym1731 (1),
               s802m1ag (2)
               }
   MAX-ACCESS  read-write
   STATUS      current
   DESCRIPTION
      "Path: ethOam.editConf.mips.mode

       Possibilities:
               y-1731   (1)
               802-1ag   (2)"
   ::= {er1646v2PbbEthOamEMipsEntry 50331648}

er1646v2PbbEthOamEMipsInterface OBJECT-TYPE
   SYNTAX      DisplayString
   MAX-ACCESS  read-write
   STATUS      current
   DESCRIPTION
      "Path: ethOam.editConf.mips.interface"
   ::= {er1646v2PbbEthOamEMipsEntry 67108864}

er1646v2PbbEthOamEMipsVid OBJECT-TYPE
   SYNTAX      INTEGER
               {
               untagged (0)
               }
   MAX-ACCESS  read-write
   STATUS      current
   DESCRIPTION
      "Path: ethOam.editConf.mips.vid

       Possibilities:
               untagged   (0)"
   ::= {er1646v2PbbEthOamEMipsEntry 83886080}

er1646v2PbbEthOamEMipsTpid OBJECT-TYPE
   SYNTAX      INTEGER
               {
               dot1Q (33024),
               dot1ad (34984)
               }
   MAX-ACCESS  read-write
   STATUS      current
   DESCRIPTION
      "Path: ethOam.editConf.mips.tpid

       Possibilities:
               dot1Q   (33024)
               dot1ad   (34984)"
   ::= {er1646v2PbbEthOamEMipsEntry 150994944}

er1646v2PbbEthOamEMipsPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.mips.prioMap.queue

       Possibilities:
               queue1   (0)
               queue2   (1)
               queue3   (2)
               queue4   (3)
               queue5   (4)
               lowDelayQueue   (5)
               lowDelay2Queue   (6)
               systemQueue   (7)"
   ::= {er1646v2PbbEthOamEMipsEntry 117506048}

er1646v2PbbEthOamEMipsPrioMapDropLevel OBJECT-TYPE
   SYNTAX      INTEGER
               {
               dropOnQueue (0)
               }
   MAX-ACCESS  read-write
   STATUS      current
   DESCRIPTION
      "Path: ethOam.editConf.mips.prioMap.dropLevel

       Possibilities:
               dropOnQueue   (0)"
   ::= {er1646v2PbbEthOamEMipsEntry 117571584}

er1646v2PbbEthOamEMipsMegLevel OBJECT-TYPE
   SYNTAX      Integer32
   MAX-ACCESS  read-write
   STATUS      current
   DESCRIPTION
      "Path: ethOam.editConf.mips.megLevel"
   ::= {er1646v2PbbEthOamEMipsEntry 100663296}

er1646v2PbbEthOamEMipsReplyPrioMap OBJECT-TYPE
   SYNTAX      SEQUENCE OF Er1646v2PbbEthOamEMipsReplyPrioMapEntry
   MAX-ACCESS  not-accessible
   STATUS      current
   DESCRIPTION
      ""
   ::= {er1646v2PbbEthOamEMips 134217728}

er1646v2PbbEthOamEMipsReplyPrioMapEntry OBJECT-TYPE
   SYNTAX      Er1646v2PbbEthOamEMipsReplyPrioMapEntry
   MAX-ACCESS  not-accessible
   STATUS      current
   DESCRIPTION
      ""
   INDEX      { er1646v2PbbEthOamEMipsReplyPrioMapGlobalIx,
                er1646v2PbbEthOamEMipsTableIx,
                er1646v2PbbEthOamEMipsReplyPrioMapTableIx }
   ::= {er1646v2PbbEthOamEMipsReplyPrioMap 1}

Er1646v2PbbEthOamEMipsReplyPrioMapEntry ::=
   SEQUENCE
      {
      er1646v2PbbEthOamEMipsReplyPrioMapActions
         VariableLengthTableActions,
      er1646v2PbbEthOamEMipsReplyPrioMapGlobalIx
         GlobalIndex,
      er1646v2PbbEthOamEMipsReplyPrioMapTableIx
         TableIndex,
      er1646v2PbbEthOamEMipsReplyPrioMapRxPriority
         Integer32,
      er1646v2PbbEthOamEMipsReplyPrioMapTxPriority
         INTEGER,
      er1646v2PbbEthOamEMipsReplyPrioMapQueue
         INTEGER,
      er1646v2PbbEthOamEMipsReplyPrioMapDropLevel
         INTEGER
      }

er1646v2PbbEthOamEMipsReplyPrioMapActions OBJECT-TYPE
   SYNTAX      VariableLengthTableActions
   MAX-ACCESS  read-write
   STATUS      current
   DESCRIPTION
      "By way of this field, some manipulations
       on this table may be performed."
   ::= {er1646v2PbbEthOamEMipsReplyPrioMapEntry 2}

er1646v2PbbEthOamEMipsReplyPrioMapGlobalIx OBJECT-TYPE
   SYNTAX      GlobalIndex
   MAX-ACCESS  not-accessible
   STATUS      current
   DESCRIPTION
      "The value of the tlsCntTreeGlobalIndex of the MANAGED OBJECT."
   ::= {er1646v2PbbEthOamEMipsReplyPrioMapEntry 10}

er1646v2PbbEthOamEMipsReplyPrioMapTableIx OBJECT-TYPE
   SYNTAX      TableIndex
   MAX-ACCESS  not-accessible
   STATUS      current
   DESCRIPTION
      ""
   ::= {er1646v2PbbEthOamEMipsReplyPrioMapEntry 11}

er1646v2PbbEthOamEMipsReplyPrioMapRxPriority OBJECT-TYPE
   SYNTAX      Integer32
   MAX-ACCESS  read-write
   STATUS      current
   DESCRIPTION
      "Path: ethOam.editConf.mips.replyPrioMap.rxPriority"
   ::= {er1646v2PbbEthOamEMipsReplyPrioMapEntry 16777216}

er1646v2PbbEthOamEMipsReplyPrioMapTxPriority OBJECT-TYPE
   SYNTAX      INTEGER
               {
               keepRxPrio (8)
               }
   MAX-ACCESS  read-write
   STATUS      current
   DESCRIPTION
      "Path: ethOam.editConf.mips.replyPrioMap.txPriority

       Possibilities:
               keepRxPrio   (8)"
   ::= {er1646v2PbbEthOamEMipsReplyPrioMapEntry 33554432}

er1646v2PbbEthOamEMipsReplyPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.mips.replyPrioMap.queue

       Possibilities:
               queue1   (0)
               queue2   (1)
               queue3   (2)
               queue4   (3)
               queue5   (4)
               lowDelayQueue   (5)
               lowDelay2Queue   (6)
               systemQueue   (7)"
   ::= {er1646v2PbbEthOamEMipsReplyPrioMapEntry 50331648}

er1646v2PbbEthOamEMipsReplyPrioMapDropLevel OBJECT-TYPE
   SYNTAX      INTEGER
               {
               dropOnQueue (0)
               }
   MAX-ACCESS  read-write
   STATUS      current
   DESCRIPTION
      "Path: ethOam.editConf.mips.replyPrioMap.dropLevel

       Possibilities:
               dropOnQueue   (0)"
   ::= {er1646v2PbbEthOamEMipsReplyPrioMapEntry 67108864}


er1646v2PbbEthOamEMask OBJECT IDENTIFIER ::= {er1646v2PbbEthOamE 223}

er1646v2PbbEthOamEMaskTable OBJECT-TYPE
   SYNTAX      SEQUENCE OF Er1646v2PbbEthOamEMaskEntry
   MAX-ACCESS  not-accessible
   STATUS      current
   DESCRIPTION
      "ETH OAM AlarmMask"
   ::= {er1646v2PbbEthOamEMask 1}

er1646v2PbbEthOamEMaskEntry OBJECT-TYPE
   SYNTAX      Er1646v2PbbEthOamEMaskEntry
   MAX-ACCESS  not-accessible
   STATUS      current
   DESCRIPTION
      ""
   INDEX      { er1646v2PbbEthOamEMaskGlobalIx }
   ::= {er1646v2PbbEthOamEMaskTable 1}

Er1646v2PbbEthOamEMaskEntry ::=
   SEQUENCE
      {
      er1646v2PbbEthOamEMaskGlobalIx
         GlobalIndex,
      er1646v2PbbEthOamEMaskValue
         Integer32
      }

er1646v2PbbEthOamEMaskGlobalIx OBJECT-TYPE
   SYNTAX      GlobalIndex
   MAX-ACCESS  not-accessible
   STATUS      current
   DESCRIPTION
      "The value of the tlsCntTreeGlobalIndex of the MANAGED OBJECT."
   ::= {er1646v2PbbEthOamEMaskEntry 10}

er1646v2PbbEthOamEMaskValue OBJECT-TYPE
   SYNTAX      Integer32
   MAX-ACCESS  read-write
   STATUS      current
   DESCRIPTION
      "Path: ethOam.editConf.alarmMask

       Bit meanings:
               bit 1 = delay,
               bit 2 = jitter,
               bit 3 = lossOfContinuity,
               bit 4 = mismerge,
               bit 5 = unexpectedMep,
               bit 6 = unexpectedMegLevel,
               bit 7 = unexpectedPeriod,
               bit 8 = rdi,
               bit 9 = ais,
               bit 10 = macStatus,
               bit 11 = qualityMonitor"
   ::= {er1646v2PbbEthOamEMaskEntry 2147483648}


er1646v2PbbEthOamELevel OBJECT IDENTIFIER ::= {er1646v2PbbEthOamE 61}

er1646v2PbbEthOamELevelSSCTable OBJECT-TYPE
   SYNTAX      SEQUENCE OF Er1646v2PbbEthOamELevelEntry
   MAX-ACCESS  not-accessible
   STATUS      current
   DESCRIPTION
      "ETH OAM AlarmLevel"
   ::= {er1646v2PbbEthOamELevel 1}

er1646v2PbbEthOamELevelEntry OBJECT-TYPE
   SYNTAX      Er1646v2PbbEthOamELevelEntry
   MAX-ACCESS  not-accessible
   STATUS      current
   DESCRIPTION
      ""
   INDEX      { er1646v2PbbEthOamELevelGlobalIx }
   ::= {er1646v2PbbEthOamELevelSSCTable 1}

Er1646v2PbbEthOamELevelEntry ::=
   SEQUENCE
      {
      er1646v2PbbEthOamELevelGlobalIx
         GlobalIndex,
      er1646v2PbbEthOamELevelDelay
         Integer32,
      er1646v2PbbEthOamELevelJitter
         Integer32,
      er1646v2PbbEthOamELevelLossOfContinuity
         Integer32,
      er1646v2PbbEthOamELevelMismerge
         Integer32,
      er1646v2PbbEthOamELevelUnexpectedMep
         Integer32,
      er1646v2PbbEthOamELevelUnexpectedMegLevel
         Integer32,
      er1646v2PbbEthOamELevelUnexpectedPeriod
         Integer32,
      er1646v2PbbEthOamELevelRdi
         Integer32,
      er1646v2PbbEthOamELevelAis
         Integer32,
      er1646v2PbbEthOamELevelMacStatus
         Integer32,
      er1646v2PbbEthOamELevelQualityMonitor
         Integer32
      }

er1646v2PbbEthOamELevelGlobalIx OBJECT-TYPE
   SYNTAX      GlobalIndex
   MAX-ACCESS  not-accessible
   STATUS      current
   DESCRIPTION
      "The value of the tlsCntTreeGlobalIndex of the MANAGED OBJECT."
   ::= {er1646v2PbbEthOamELevelEntry 10}

er1646v2PbbEthOamELevelDelay OBJECT-TYPE
   SYNTAX      Integer32
   MAX-ACCESS  read-write
   STATUS      current
   DESCRIPTION
      "Path: ethOam.editConf.alarmLevel.delay"
   ::= {er1646v2PbbEthOamELevelEntry 33554432}

er1646v2PbbEthOamELevelJitter OBJECT-TYPE
   SYNTAX      Integer32
   MAX-ACCESS  read-write
   STATUS      current
   DESCRIPTION
      "Path: ethOam.editConf.alarmLevel.jitter"
   ::= {er1646v2PbbEthOamELevelEntry 50331648}

er1646v2PbbEthOamELevelLossOfContinuity OBJECT-TYPE
   SYNTAX      Integer32
   MAX-ACCESS  read-write
   STATUS      current
   DESCRIPTION
      "Path: ethOam.editConf.alarmLevel.lossOfContinuity"
   ::= {er1646v2PbbEthOamELevelEntry 67108864}

er1646v2PbbEthOamELevelMismerge OBJECT-TYPE
   SYNTAX      Integer32
   MAX-ACCESS  read-write
   STATUS      current
   DESCRIPTION
      "Path: ethOam.editConf.alarmLevel.mismerge"
   ::= {er1646v2PbbEthOamELevelEntry 83886080}

er1646v2PbbEthOamELevelUnexpectedMep OBJECT-TYPE
   SYNTAX      Integer32
   MAX-ACCESS  read-write
   STATUS      current
   DESCRIPTION
      "Path: ethOam.editConf.alarmLevel.unexpectedMep"
   ::= {er1646v2PbbEthOamELevelEntry 100663296}

er1646v2PbbEthOamELevelUnexpectedMegLevel OBJECT-TYPE
   SYNTAX      Integer32
   MAX-ACCESS  read-write
   STATUS      current
   DESCRIPTION
      "Path: ethOam.editConf.alarmLevel.unexpectedMegLevel"
   ::= {er1646v2PbbEthOamELevelEntry 117440512}

er1646v2PbbEthOamELevelUnexpectedPeriod OBJECT-TYPE
   SYNTAX      Integer32
   MAX-ACCESS  read-write
   STATUS      current
   DESCRIPTION
      "Path: ethOam.editConf.alarmLevel.unexpectedPeriod"
   ::= {er1646v2PbbEthOamELevelEntry 134217728}

er1646v2PbbEthOamELevelRdi OBJECT-TYPE
   SYNTAX      Integer32
   MAX-ACCESS  read-write
   STATUS      current
   DESCRIPTION
      "Path: ethOam.editConf.alarmLevel.rdi"
   ::= {er1646v2PbbEthOamELevelEntry 150994944}

er1646v2PbbEthOamELevelAis OBJECT-TYPE
   SYNTAX      Integer32
   MAX-ACCESS  read-write
   STATUS      current
   DESCRIPTION
      "Path: ethOam.editConf.alarmLevel.ais"
   ::= {er1646v2PbbEthOamELevelEntry 167772160}

er1646v2PbbEthOamELevelMacStatus OBJECT-TYPE
   SYNTAX      Integer32
   MAX-ACCESS  read-write
   STATUS      current
   DESCRIPTION
      "Path: ethOam.editConf.alarmLevel.macStatus"
   ::= {er1646v2PbbEthOamELevelEntry 184549376}

er1646v2PbbEthOamELevelQualityMonitor OBJECT-TYPE
   SYNTAX      Integer32
   MAX-ACCESS  read-write
   STATUS      current
   DESCRIPTION
      "Path: ethOam.editConf.alarmLevel.qualityMonitor"
   ::= {er1646v2PbbEthOamELevelEntry 201326592}


er1646v2PbbEthOamEStartDelay OBJECT IDENTIFIER ::= {er1646v2PbbEthOamE 38}

er1646v2PbbEthOamEStartDelayTable OBJECT-TYPE
   SYNTAX      SEQUENCE OF Er1646v2PbbEthOamEStartDelayEntry
   MAX-ACCESS  not-accessible
   STATUS      current
   DESCRIPTION
      "the amount of time the OAM module waits before being started after a reboot of the device"
   ::= {er1646v2PbbEthOamEStartDelay 1}

er1646v2PbbEthOamEStartDelayEntry OBJECT-TYPE
   SYNTAX      Er1646v2PbbEthOamEStartDelayEntry
   MAX-ACCESS  not-accessible
   STATUS      current
   DESCRIPTION
      ""
   INDEX      { er1646v2PbbEthOamEStartDelayGlobalIx }
   ::= {er1646v2PbbEthOamEStartDelayTable 1}

Er1646v2PbbEthOamEStartDelayEntry ::=
   SEQUENCE
      {
      er1646v2PbbEthOamEStartDelayGlobalIx
         GlobalIndex,
      er1646v2PbbEthOamEStartDelayValue
         INTEGER
      }

er1646v2PbbEthOamEStartDelayGlobalIx OBJECT-TYPE
   SYNTAX      GlobalIndex
   MAX-ACCESS  not-accessible
   STATUS      current
   DESCRIPTION
      "The value of the tlsCntTreeGlobalIndex of the MANAGED OBJECT."
   ::= {er1646v2PbbEthOamEStartDelayEntry 10}

er1646v2PbbEthOamEStartDelayValue OBJECT-TYPE
   SYNTAX      INTEGER
               {
               disabled (0)
               }
   MAX-ACCESS  read-write
   STATUS      current
   DESCRIPTION
      "Path: ethOam.editConf.startDelay

       Possibilities:
               disabled   (0)"
   ::= {er1646v2PbbEthOamEStartDelayEntry 2147483648}


er1646v2PbbEthOamELocDelay OBJECT IDENTIFIER ::= {er1646v2PbbEthOamE 36}

er1646v2PbbEthOamELocDelayTable OBJECT-TYPE
   SYNTAX      SEQUENCE OF Er1646v2PbbEthOamELocDelayEntry
   MAX-ACCESS  not-accessible
   STATUS      current
   DESCRIPTION
      "the amount of time a device waits for remote MEPs before the crosscheck operation is started"
   ::= {er1646v2PbbEthOamELocDelay 1}

er1646v2PbbEthOamELocDelayEntry OBJECT-TYPE
   SYNTAX      Er1646v2PbbEthOamELocDelayEntry
   MAX-ACCESS  not-accessible
   STATUS      current
   DESCRIPTION
      ""
   INDEX      { er1646v2PbbEthOamELocDelayGlobalIx }
   ::= {er1646v2PbbEthOamELocDelayTable 1}

Er1646v2PbbEthOamELocDelayEntry ::=
   SEQUENCE
      {
      er1646v2PbbEthOamELocDelayGlobalIx
         GlobalIndex,
      er1646v2PbbEthOamELocDelayValue
         INTEGER
      }

er1646v2PbbEthOamELocDelayGlobalIx OBJECT-TYPE
   SYNTAX      GlobalIndex
   MAX-ACCESS  not-accessible
   STATUS      current
   DESCRIPTION
      "The value of the tlsCntTreeGlobalIndex of the MANAGED OBJECT."
   ::= {er1646v2PbbEthOamELocDelayEntry 10}

er1646v2PbbEthOamELocDelayValue OBJECT-TYPE
   SYNTAX      INTEGER
               {
               disabled (0)
               }
   MAX-ACCESS  read-write
   STATUS      current
   DESCRIPTION
      "Path: ethOam.editConf.locDelay

       Possibilities:
               disabled   (0)"
   ::= {er1646v2PbbEthOamELocDelayEntry 2147483648}


er1646v2PbbEthOamEMode OBJECT IDENTIFIER ::= {er1646v2PbbEthOamE 12}

er1646v2PbbEthOamEModeTable OBJECT-TYPE
   SYNTAX      SEQUENCE OF Er1646v2PbbEthOamEModeEntry
   MAX-ACCESS  not-accessible
   STATUS      current
   DESCRIPTION
      "mode of the ETH OAM object"
   ::= {er1646v2PbbEthOamEMode 1}

er1646v2PbbEthOamEModeEntry OBJECT-TYPE
   SYNTAX      Er1646v2PbbEthOamEModeEntry
   MAX-ACCESS  not-accessible
   STATUS      current
   DESCRIPTION
      ""
   INDEX      { er1646v2PbbEthOamEModeGlobalIx }
   ::= {er1646v2PbbEthOamEModeTable 1}

Er1646v2PbbEthOamEModeEntry ::=
   SEQUENCE
      {
      er1646v2PbbEthOamEModeGlobalIx
         GlobalIndex,
      er1646v2PbbEthOamEModeValue
         INTEGER
      }

er1646v2PbbEthOamEModeGlobalIx OBJECT-TYPE
   SYNTAX      GlobalIndex
   MAX-ACCESS  not-accessible
   STATUS      current
   DESCRIPTION
      "The value of the tlsCntTreeGlobalIndex of the MANAGED OBJECT."
   ::= {er1646v2PbbEthOamEModeEntry 10}

er1646v2PbbEthOamEModeValue OBJECT-TYPE
   SYNTAX      INTEGER
               {
               disabled (0),
               enabled (1)
               }
   MAX-ACCESS  read-write
   STATUS      current
   DESCRIPTION
      "Path: ethOam.editConf.mode

       Possibilities:
               disabled   (0)
               enabled   (1)"
   ::= {er1646v2PbbEthOamEModeEntry 2147483648}


er1646v2PbbEthOamEMeps OBJECT IDENTIFIER ::= {er1646v2PbbEthOamE 10}

er1646v2PbbEthOamEMepsSSCTable OBJECT-TYPE
   SYNTAX      SEQUENCE OF Er1646v2PbbEthOamEMepsEntry
   MAX-ACCESS  not-accessible
   STATUS      current
   DESCRIPTION
      "table with local MEPs"
   ::= {er1646v2PbbEthOamEMeps 1}

er1646v2PbbEthOamEMepsEntry OBJECT-TYPE
   SYNTAX      Er1646v2PbbEthOamEMepsEntry
   MAX-ACCESS  not-accessible
   STATUS      current
   DESCRIPTION
      ""
   INDEX      { er1646v2PbbEthOamEMepsGlobalIx,
                er1646v2PbbEthOamEMepsTableIx }
   ::= {er1646v2PbbEthOamEMepsSSCTable 1}

Er1646v2PbbEthOamEMepsEntry ::=
   SEQUENCE
      {
      er1646v2PbbEthOamEMepsActions
         VariableLengthTableActions,
      er1646v2PbbEthOamEMepsGlobalIx
         GlobalIndex,
      er1646v2PbbEthOamEMepsTableIx
         TableIndex,
      er1646v2PbbEthOamEMepsName
         DisplayString,
      er1646v2PbbEthOamEMepsAdminStatus
         INTEGER,
      er1646v2PbbEthOamEMepsMode
         INTEGER,
      er1646v2PbbEthOamEMepsType
         INTEGER,
      er1646v2PbbEthOamEMepsInterface
         DisplayString,
      er1646v2PbbEthOamEMepsVid
         INTEGER,
      er1646v2PbbEthOamEMepsTpid
         INTEGER,
      er1646v2PbbEthOamEMepsPrioMapQueue
         INTEGER,
      er1646v2PbbEthOamEMepsPrioMapDropLevel
         INTEGER,
      er1646v2PbbEthOamEMepsMegLevel
         Integer32,
      er1646v2PbbEthOamEMepsMepId
         Integer32,
      er1646v2PbbEthOamEMepsAlarmMask
         Integer32,
      er1646v2PbbEthOamEMepsEfd
         INTEGER,
      er1646v2PbbEthOamEMepsRdiMask
         Integer32,
      er1646v2PbbEthOamEMepsProtocolVersionLoss
         INTEGER,
      er1646v2PbbEthOamEMepsCcMegIdMaintDomainName
         DisplayString,
      er1646v2PbbEthOamEMepsCcMegIdShortMaName
         DisplayString,
      er1646v2PbbEthOamEMepsCcPriority
         Integer32,
      er1646v2PbbEthOamEMepsCcPeriod
         INTEGER,
      er1646v2PbbEthOamEMepsCcState
         INTEGER,
      er1646v2PbbEthOamEMepsCcLossThreshold
         Integer32,
      er1646v2PbbEthOamEMepsAisMegLevel
         Integer32,
      er1646v2PbbEthOamEMepsAisPriority
         Integer32,
      er1646v2PbbEthOamEMepsAisPeriod
         INTEGER,
      er1646v2PbbEthOamEMepsAisState
         INTEGER,
      er1646v2PbbEthOamEMepsLossDataCount
         Integer32,
      er1646v2PbbEthOamEMepsIndex
         INTEGER
      }

er1646v2PbbEthOamEMepsActions OBJECT-TYPE
   SYNTAX      VariableLengthTableActions
   MAX-ACCESS  read-write
   STATUS      current
   DESCRIPTION
      "By way of this field, some manipulations
       on this table may be performed."
   ::= {er1646v2PbbEthOamEMepsEntry 2}

er1646v2PbbEthOamEMepsGlobalIx OBJECT-TYPE
   SYNTAX      GlobalIndex
   MAX-ACCESS  not-accessible
   STATUS      current
   DESCRIPTION
      "The value of the tlsCntTreeGlobalIndex of the MANAGED OBJECT."
   ::= {er1646v2PbbEthOamEMepsEntry 10}

er1646v2PbbEthOamEMepsTableIx OBJECT-TYPE
   SYNTAX      TableIndex
   MAX-ACCESS  not-accessible
   STATUS      current
   DESCRIPTION
      ""
   ::= {er1646v2PbbEthOamEMepsEntry 11}

er1646v2PbbEthOamEMepsName OBJECT-TYPE
   SYNTAX      DisplayString
   MAX-ACCESS  read-write
   STATUS      current
   DESCRIPTION
      "Path: ethOam.editConf.meps.name"
   ::= {er1646v2PbbEthOamEMepsEntry 16777216}

er1646v2PbbEthOamEMepsAdminStatus OBJECT-TYPE
   SYNTAX      INTEGER
               {
               up (1),
               down (2)
               }
   MAX-ACCESS  read-write
   STATUS      current
   DESCRIPTION
      "Path: ethOam.editConf.meps.adminStatus

       Possibilities:
               up   (1)
               down   (2)"
   ::= {er1646v2PbbEthOamEMepsEntry 33554432}

er1646v2PbbEthOamEMepsMode OBJECT-TYPE
   SYNTAX      INTEGER
               {
               ym1731 (1),
               s802m1ag (2),
               hybrid (3)
               }
   MAX-ACCESS  read-write
   STATUS      current
   DESCRIPTION
      "Path: ethOam.editConf.meps.mode

       Possibilities:
               y-1731   (1)
               802-1ag   (2)
               hybrid   (3)"
   ::= {er1646v2PbbEthOamEMepsEntry 50331648}

er1646v2PbbEthOamEMepsType OBJECT-TYPE
   SYNTAX      INTEGER
               {
               inwardFacing (1),
               outwardFacing (2),
               pbb (3)
               }
   MAX-ACCESS  read-write
   STATUS      current
   DESCRIPTION
      "Path: ethOam.editConf.meps.type

       Possibilities:
               inwardFacing   (1)
               outwardFacing   (2)
               pbb   (3)"
   ::= {er1646v2PbbEthOamEMepsEntry 67108864}

er1646v2PbbEthOamEMepsInterface OBJECT-TYPE
   SYNTAX      DisplayString
   MAX-ACCESS  read-write
   STATUS      current
   DESCRIPTION
      "Path: ethOam.editConf.meps.interface"
   ::= {er1646v2PbbEthOamEMepsEntry 83886080}

er1646v2PbbEthOamEMepsVid OBJECT-TYPE
   SYNTAX      INTEGER
               {
               untagged (0)
               }
   MAX-ACCESS  read-write
   STATUS      current
   DESCRIPTION
      "Path: ethOam.editConf.meps.vid

       Possibilities:
               untagged   (0)"
   ::= {er1646v2PbbEthOamEMepsEntry 100663296}

er1646v2PbbEthOamEMepsTpid OBJECT-TYPE
   SYNTAX      INTEGER
               {
               dot1Q (33024),
               dot1ad (34984)
               }
   MAX-ACCESS  read-write
   STATUS      current
   DESCRIPTION
      "Path: ethOam.editConf.meps.tpid

       Possibilities:
               dot1Q   (33024)
               dot1ad   (34984)"
   ::= {er1646v2PbbEthOamEMepsEntry 402653184}

er1646v2PbbEthOamEMepsPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.meps.prioMap.queue

       Possibilities:
               queue1   (0)
               queue2   (1)
               queue3   (2)
               queue4   (3)
               queue5   (4)
               lowDelayQueue   (5)
               lowDelay2Queue   (6)
               systemQueue   (7)"
   ::= {er1646v2PbbEthOamEMepsEntry 251723776}

er1646v2PbbEthOamEMepsPrioMapDropLevel OBJECT-TYPE
   SYNTAX      INTEGER
               {
               dropOnQueue (0)
               }
   MAX-ACCESS  read-write
   STATUS      current
   DESCRIPTION
      "Path: ethOam.editConf.meps.prioMap.dropLevel

       Possibilities:
               dropOnQueue   (0)"
   ::= {er1646v2PbbEthOamEMepsEntry 251789312}

er1646v2PbbEthOamEMepsMegLevel OBJECT-TYPE
   SYNTAX      Integer32
   MAX-ACCESS  read-write
   STATUS      current
   DESCRIPTION
      "Path: ethOam.editConf.meps.megLevel"
   ::= {er1646v2PbbEthOamEMepsEntry 117440512}

er1646v2PbbEthOamEMepsMepId OBJECT-TYPE
   SYNTAX      Integer32
   MAX-ACCESS  read-write
   STATUS      current
   DESCRIPTION
      "Path: ethOam.editConf.meps.mepId"
   ::= {er1646v2PbbEthOamEMepsEntry 134217728}

er1646v2PbbEthOamEMepsAlarmMask OBJECT-TYPE
   SYNTAX      Integer32
   MAX-ACCESS  read-write
   STATUS      current
   DESCRIPTION
      "Path: ethOam.editConf.meps.alarmMask

       Bit meanings:
               bit 4 = mismerge,
               bit 5 = unexpectedMep,
               bit 6 = unexpectedMegLevel,
               bit 7 = unexpectedPeriod,
               bit 8 = rdi,
               bit 9 = ais,
               bit 10 = macStatus"
   ::= {er1646v2PbbEthOamEMepsEntry 150994944}

er1646v2PbbEthOamEMepsEfd OBJECT-TYPE
   SYNTAX      INTEGER
               {
               disabled (0),
               enabled (1),
               enabledLfp (2)
               }
   MAX-ACCESS  read-write
   STATUS      current
   DESCRIPTION
      "Path: ethOam.editConf.meps.efd

       Possibilities:
               disabled   (0)
               enabled   (1)
               enabledLfp   (2)"
   ::= {er1646v2PbbEthOamEMepsEntry 285212672}

er1646v2PbbEthOamEMepsRdiMask OBJECT-TYPE
   SYNTAX      Integer32
   MAX-ACCESS  read-write
   STATUS      current
   DESCRIPTION
      "Path: ethOam.editConf.meps.rdiMask

       Bit meanings:
               bit 3 = lossOfContinuity,
               bit 4 = mismerge,
               bit 5 = unexpectedMep,
               bit 6 = unexpectedMegLevel,
               bit 7 = unexpectedPeriod,
               bit 10 = macStatus"
   ::= {er1646v2PbbEthOamEMepsEntry 318767104}

er1646v2PbbEthOamEMepsProtocolVersionLoss OBJECT-TYPE
   SYNTAX      INTEGER
               {
               ym1731u05m2006 (1),
               ym1731u02m2008 (2)
               }
   MAX-ACCESS  read-write
   STATUS      current
   DESCRIPTION
      "Path: ethOam.editConf.meps.protocolVersion.loss

       Possibilities:
               y-1731_05-2006   (1)
               y-1731_02-2008   (2)"
   ::= {er1646v2PbbEthOamEMepsEntry 335609856}

er1646v2PbbEthOamEMepsCcMegIdMaintDomainName OBJECT-TYPE
   SYNTAX      DisplayString
   MAX-ACCESS  read-write
   STATUS      current
   DESCRIPTION
      "Path: ethOam.editConf.meps.cc.megId.maintDomainName"
   ::= {er1646v2PbbEthOamEMepsEntry 167837952}

er1646v2PbbEthOamEMepsCcMegIdShortMaName OBJECT-TYPE
   SYNTAX      DisplayString
   MAX-ACCESS  read-write
   STATUS      current
   DESCRIPTION
      "Path: ethOam.editConf.meps.cc.megId.shortMaName"
   ::= {er1646v2PbbEthOamEMepsEntry 167838208}

er1646v2PbbEthOamEMepsCcPriority OBJECT-TYPE
   SYNTAX      Integer32
   MAX-ACCESS  read-write
   STATUS      current
   DESCRIPTION
      "Path: ethOam.editConf.meps.cc.priority"
   ::= {er1646v2PbbEthOamEMepsEntry 167903232}

er1646v2PbbEthOamEMepsCcPeriod OBJECT-TYPE
   SYNTAX      INTEGER
               {
               s10ms (2),
               s100ms (3),
               s1s (4),
               s10s (5),
               s1min (6),
               s10min (7)
               }
   MAX-ACCESS  read-write
   STATUS      current
   DESCRIPTION
      "Path: ethOam.editConf.meps.cc.period

       Possibilities:
               10ms   (2)
               100ms   (3)
               1s   (4)
               10s   (5)
               1min   (6)
               10min   (7)"
   ::= {er1646v2PbbEthOamEMepsEntry 167968768}

er1646v2PbbEthOamEMepsCcState OBJECT-TYPE
   SYNTAX      INTEGER
               {
               disabled (0),
               enabled (1)
               }
   MAX-ACCESS  read-write
   STATUS      current
   DESCRIPTION
      "Path: ethOam.editConf.meps.cc.state

       Possibilities:
               disabled   (0)
               enabled   (1)"
   ::= {er1646v2PbbEthOamEMepsEntry 168034304}

er1646v2PbbEthOamEMepsCcLossThreshold OBJECT-TYPE
   SYNTAX      Integer32
   MAX-ACCESS  read-write
   STATUS      current
   DESCRIPTION
      "Path: ethOam.editConf.meps.cc.lossThreshold"
   ::= {er1646v2PbbEthOamEMepsEntry 168099840}

er1646v2PbbEthOamEMepsAisMegLevel OBJECT-TYPE
   SYNTAX      Integer32
   MAX-ACCESS  read-write
   STATUS      current
   DESCRIPTION
      "Path: ethOam.editConf.meps.ais.megLevel"
   ::= {er1646v2PbbEthOamEMepsEntry 268500992}

er1646v2PbbEthOamEMepsAisPriority OBJECT-TYPE
   SYNTAX      Integer32
   MAX-ACCESS  read-write
   STATUS      current
   DESCRIPTION
      "Path: ethOam.editConf.meps.ais.priority"
   ::= {er1646v2PbbEthOamEMepsEntry 268566528}

er1646v2PbbEthOamEMepsAisPeriod OBJECT-TYPE
   SYNTAX      INTEGER
               {
               s1s (4),
               s1min (6)
               }
   MAX-ACCESS  read-write
   STATUS      current
   DESCRIPTION
      "Path: ethOam.editConf.meps.ais.period

       Possibilities:
               1s   (4)
               1min   (6)"
   ::= {er1646v2PbbEthOamEMepsEntry 268632064}

er1646v2PbbEthOamEMepsAisState OBJECT-TYPE
   SYNTAX      INTEGER
               {
               disabled (0),
               enabled (1)
               }
   MAX-ACCESS  read-write
   STATUS      current
   DESCRIPTION
      "Path: ethOam.editConf.meps.ais.state

       Possibilities:
               disabled   (0)
               enabled   (1)"
   ::= {er1646v2PbbEthOamEMepsEntry 268697600}

er1646v2PbbEthOamEMepsLossDataCount OBJECT-TYPE
   SYNTAX      Integer32
   MAX-ACCESS  read-write
   STATUS      current
   DESCRIPTION
      "Path: ethOam.editConf.meps.lossDataCount

       Bit meanings:
               bit 0 = data,
               bit 1 = cc,
               bit 2 = loss,
               bit 3 = delay"
   ::= {er1646v2PbbEthOamEMepsEntry 369098752}

er1646v2PbbEthOamEMepsIndex OBJECT-TYPE
   SYNTAX      INTEGER
               {
               auto (0)
               }
   MAX-ACCESS  read-write
   STATUS      current
   DESCRIPTION
      "Path: ethOam.editConf.meps.index

       Possibilities:
               auto   (0)"
   ::= {er1646v2PbbEthOamEMepsEntry 419430400}

er1646v2PbbEthOamEMepsReplyPrioMap OBJECT-TYPE
   SYNTAX      SEQUENCE OF Er1646v2PbbEthOamEMepsReplyPrioMapEntry
   MAX-ACCESS  not-accessible
   STATUS      current
   DESCRIPTION
      ""
   ::= {er1646v2PbbEthOamEMeps 352321536}

er1646v2PbbEthOamEMepsReplyPrioMapEntry OBJECT-TYPE
   SYNTAX      Er1646v2PbbEthOamEMepsReplyPrioMapEntry
   MAX-ACCESS  not-accessible
   STATUS      current
   DESCRIPTION
      ""
   INDEX      { er1646v2PbbEthOamEMepsReplyPrioMapGlobalIx,
                er1646v2PbbEthOamEMepsTableIx,
                er1646v2PbbEthOamEMepsReplyPrioMapTableIx }
   ::= {er1646v2PbbEthOamEMepsReplyPrioMap 1}

Er1646v2PbbEthOamEMepsReplyPrioMapEntry ::=
   SEQUENCE
      {
      er1646v2PbbEthOamEMepsReplyPrioMapActions
         VariableLengthTableActions,
      er1646v2PbbEthOamEMepsReplyPrioMapGlobalIx
         GlobalIndex,
      er1646v2PbbEthOamEMepsReplyPrioMapTableIx
         TableIndex,
      er1646v2PbbEthOamEMepsReplyPrioMapRxPriority
         Integer32,
      er1646v2PbbEthOamEMepsReplyPrioMapTxPriority
         INTEGER,
      er1646v2PbbEthOamEMepsReplyPrioMapQueue
         INTEGER,
      er1646v2PbbEthOamEMepsReplyPrioMapDropLevel
         INTEGER
      }

er1646v2PbbEthOamEMepsReplyPrioMapActions OBJECT-TYPE
   SYNTAX      VariableLengthTableActions
   MAX-ACCESS  read-write
   STATUS      current
   DESCRIPTION
      "By way of this field, some manipulations
       on this table may be performed."
   ::= {er1646v2PbbEthOamEMepsReplyPrioMapEntry 2}

er1646v2PbbEthOamEMepsReplyPrioMapGlobalIx OBJECT-TYPE
   SYNTAX      GlobalIndex
   MAX-ACCESS  not-accessible
   STATUS      current
   DESCRIPTION
      "The value of the tlsCntTreeGlobalIndex of the MANAGED OBJECT."
   ::= {er1646v2PbbEthOamEMepsReplyPrioMapEntry 10}

er1646v2PbbEthOamEMepsReplyPrioMapTableIx OBJECT-TYPE
   SYNTAX      TableIndex
   MAX-ACCESS  not-accessible
   STATUS      current
   DESCRIPTION
      ""
   ::= {er1646v2PbbEthOamEMepsReplyPrioMapEntry 11}

er1646v2PbbEthOamEMepsReplyPrioMapRxPriority OBJECT-TYPE
   SYNTAX      Integer32
   MAX-ACCESS  read-write
   STATUS      current
   DESCRIPTION
      "Path: ethOam.editConf.meps.replyPrioMap.rxPriority"
   ::= {er1646v2PbbEthOamEMepsReplyPrioMapEntry 16777216}

er1646v2PbbEthOamEMepsReplyPrioMapTxPriority OBJECT-TYPE
   SYNTAX      INTEGER
               {
               keepRxPrio (8)
               }
   MAX-ACCESS  read-write
   STATUS      current
   DESCRIPTION
      "Path: ethOam.editConf.meps.replyPrioMap.txPriority

       Possibilities:
               keepRxPrio   (8)"
   ::= {er1646v2PbbEthOamEMepsReplyPrioMapEntry 33554432}

er1646v2PbbEthOamEMepsReplyPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.meps.replyPrioMap.queue

       Possibilities:
               queue1   (0)
               queue2   (1)
               queue3   (2)
               queue4   (3)
               queue5   (4)
               lowDelayQueue   (5)
               lowDelay2Queue   (6)
               systemQueue   (7)"
   ::= {er1646v2PbbEthOamEMepsReplyPrioMapEntry 50331648}

er1646v2PbbEthOamEMepsReplyPrioMapDropLevel OBJECT-TYPE
   SYNTAX      INTEGER
               {
               dropOnQueue (0)
               }
   MAX-ACCESS  read-write
   STATUS      current
   DESCRIPTION
      "Path: ethOam.editConf.meps.replyPrioMap.dropLevel

       Possibilities:
               dropOnQueue   (0)"
   ::= {er1646v2PbbEthOamEMepsReplyPrioMapEntry 67108864}

er1646v2PbbEthOamEMepsManagedMep OBJECT-TYPE
   SYNTAX      SEQUENCE OF Er1646v2PbbEthOamEMepsManagedMepEntry
   MAX-ACCESS  not-accessible
   STATUS      current
   DESCRIPTION
      ""
   ::= {er1646v2PbbEthOamEMeps 184549376}

er1646v2PbbEthOamEMepsManagedMepEntry OBJECT-TYPE
   SYNTAX      Er1646v2PbbEthOamEMepsManagedMepEntry
   MAX-ACCESS  not-accessible
   STATUS      current
   DESCRIPTION
      ""
   INDEX      { er1646v2PbbEthOamEMepsManagedMepGlobalIx,
                er1646v2PbbEthOamEMepsTableIx,
                er1646v2PbbEthOamEMepsManagedMepTableIx }
   ::= {er1646v2PbbEthOamEMepsManagedMep 1}

Er1646v2PbbEthOamEMepsManagedMepEntry ::=
   SEQUENCE
      {
      er1646v2PbbEthOamEMepsManagedMepActions
         VariableLengthTableActions,
      er1646v2PbbEthOamEMepsManagedMepGlobalIx
         GlobalIndex,
      er1646v2PbbEthOamEMepsManagedMepTableIx
         TableIndex,
      er1646v2PbbEthOamEMepsManagedMepManagedMepName
         DisplayString,
      er1646v2PbbEthOamEMepsManagedMepMepId
         Integer32,
      er1646v2PbbEthOamEMepsManagedMepAlarmMask
         Integer32,
      er1646v2PbbEthOamEMepsManagedMepMacAddress
         OCTET STRING
      }

er1646v2PbbEthOamEMepsManagedMepActions OBJECT-TYPE
   SYNTAX      VariableLengthTableActions
   MAX-ACCESS  read-write
   STATUS      current
   DESCRIPTION
      "By way of this field, some manipulations
       on this table may be performed."
   ::= {er1646v2PbbEthOamEMepsManagedMepEntry 2}

er1646v2PbbEthOamEMepsManagedMepGlobalIx OBJECT-TYPE
   SYNTAX      GlobalIndex
   MAX-ACCESS  not-accessible
   STATUS      current
   DESCRIPTION
      "The value of the tlsCntTreeGlobalIndex of the MANAGED OBJECT."
   ::= {er1646v2PbbEthOamEMepsManagedMepEntry 10}

er1646v2PbbEthOamEMepsManagedMepTableIx OBJECT-TYPE
   SYNTAX      TableIndex
   MAX-ACCESS  not-accessible
   STATUS      current
   DESCRIPTION
      ""
   ::= {er1646v2PbbEthOamEMepsManagedMepEntry 11}

er1646v2PbbEthOamEMepsManagedMepManagedMepName OBJECT-TYPE
   SYNTAX      DisplayString
   MAX-ACCESS  read-write
   STATUS      current
   DESCRIPTION
      "Path: ethOam.editConf.meps.managedMep.managedMepName"
   ::= {er1646v2PbbEthOamEMepsManagedMepEntry 67108864}

er1646v2PbbEthOamEMepsManagedMepMepId OBJECT-TYPE
   SYNTAX      Integer32
   MAX-ACCESS  read-write
   STATUS      current
   DESCRIPTION
      "Path: ethOam.editConf.meps.managedMep.mepId"
   ::= {er1646v2PbbEthOamEMepsManagedMepEntry 16777216}

er1646v2PbbEthOamEMepsManagedMepAlarmMask OBJECT-TYPE
   SYNTAX      Integer32
   MAX-ACCESS  read-write
   STATUS      current
   DESCRIPTION
      "Path: ethOam.editConf.meps.managedMep.alarmMask

       Bit meanings:
               bit 3 = lossOfContinuity"
   ::= {er1646v2PbbEthOamEMepsManagedMepEntry 33554432}

er1646v2PbbEthOamEMepsManagedMepMacAddress OBJECT-TYPE
   SYNTAX      OCTET STRING
   MAX-ACCESS  read-write
   STATUS      current
   DESCRIPTION
      "Path: ethOam.editConf.meps.managedMep.macAddress

       MAC address."
   ::= {er1646v2PbbEthOamEMepsManagedMepEntry 50331648}

er1646v2PbbEthOamEMepsLoopback OBJECT-TYPE
   SYNTAX      SEQUENCE OF Er1646v2PbbEthOamEMepsLoopbackEntry
   MAX-ACCESS  not-accessible
   STATUS      current
   DESCRIPTION
      ""
   ::= {er1646v2PbbEthOamEMeps 201326592}

er1646v2PbbEthOamEMepsLoopbackEntry OBJECT-TYPE
   SYNTAX      Er1646v2PbbEthOamEMepsLoopbackEntry
   MAX-ACCESS  not-accessible
   STATUS      current
   DESCRIPTION
      ""
   INDEX      { er1646v2PbbEthOamEMepsLoopbackGlobalIx,
                er1646v2PbbEthOamEMepsTableIx,
                er1646v2PbbEthOamEMepsLoopbackTableIx }
   ::= {er1646v2PbbEthOamEMepsLoopback 1}

Er1646v2PbbEthOamEMepsLoopbackEntry ::=
   SEQUENCE
      {
      er1646v2PbbEthOamEMepsLoopbackActions
         VariableLengthTableActions,
      er1646v2PbbEthOamEMepsLoopbackGlobalIx
         GlobalIndex,
      er1646v2PbbEthOamEMepsLoopbackTableIx
         TableIndex,
      er1646v2PbbEthOamEMepsLoopbackDestinationMepId
         Integer32,
      er1646v2PbbEthOamEMepsLoopbackDestinationMacAddress
         OCTET STRING,
      er1646v2PbbEthOamEMepsLoopbackPriority
         Integer32,
      er1646v2PbbEthOamEMepsLoopbackPeriod
         INTEGER,
      er1646v2PbbEthOamEMepsLoopbackDataTlvSize
         Integer32,
      er1646v2PbbEthOamEMepsLoopbackState
         INTEGER
      }

er1646v2PbbEthOamEMepsLoopbackActions OBJECT-TYPE
   SYNTAX      VariableLengthTableActions
   MAX-ACCESS  read-write
   STATUS      current
   DESCRIPTION
      "By way of this field, some manipulations
       on this table may be performed."
   ::= {er1646v2PbbEthOamEMepsLoopbackEntry 2}

er1646v2PbbEthOamEMepsLoopbackGlobalIx OBJECT-TYPE
   SYNTAX      GlobalIndex
   MAX-ACCESS  not-accessible
   STATUS      current
   DESCRIPTION
      "The value of the tlsCntTreeGlobalIndex of the MANAGED OBJECT."
   ::= {er1646v2PbbEthOamEMepsLoopbackEntry 10}

er1646v2PbbEthOamEMepsLoopbackTableIx OBJECT-TYPE
   SYNTAX      TableIndex
   MAX-ACCESS  not-accessible
   STATUS      current
   DESCRIPTION
      ""
   ::= {er1646v2PbbEthOamEMepsLoopbackEntry 11}

er1646v2PbbEthOamEMepsLoopbackDestinationMepId OBJECT-TYPE
   SYNTAX      Integer32
   MAX-ACCESS  read-write
   STATUS      current
   DESCRIPTION
      "Path: ethOam.editConf.meps.loopback.destination.mepId"
   ::= {er1646v2PbbEthOamEMepsLoopbackEntry 16842752}

er1646v2PbbEthOamEMepsLoopbackDestinationMacAddress OBJECT-TYPE
   SYNTAX      OCTET STRING
   MAX-ACCESS  read-write
   STATUS      current
   DESCRIPTION
      "Path: ethOam.editConf.meps.loopback.destination.macAddress

       MAC address."
   ::= {er1646v2PbbEthOamEMepsLoopbackEntry 16908288}

er1646v2PbbEthOamEMepsLoopbackPriority OBJECT-TYPE
   SYNTAX      Integer32
   MAX-ACCESS  read-write
   STATUS      current
   DESCRIPTION
      "Path: ethOam.editConf.meps.loopback.priority"
   ::= {er1646v2PbbEthOamEMepsLoopbackEntry 33554432}

er1646v2PbbEthOamEMepsLoopbackPeriod OBJECT-TYPE
   SYNTAX      INTEGER
               {
               s100ms (3),
               s1s (4),
               s10s (5),
               s1min (6),
               s10min (7)
               }
   MAX-ACCESS  read-write
   STATUS      current
   DESCRIPTION
      "Path: ethOam.editConf.meps.loopback.period

       Possibilities:
               100ms   (3)
               1s   (4)
               10s   (5)
               1min   (6)
               10min   (7)"
   ::= {er1646v2PbbEthOamEMepsLoopbackEntry 50331648}

er1646v2PbbEthOamEMepsLoopbackDataTlvSize OBJECT-TYPE
   SYNTAX      Integer32
   MAX-ACCESS  read-write
   STATUS      current
   DESCRIPTION
      "Path: ethOam.editConf.meps.loopback.dataTlvSize"
   ::= {er1646v2PbbEthOamEMepsLoopbackEntry 83886080}

er1646v2PbbEthOamEMepsLoopbackState OBJECT-TYPE
   SYNTAX      INTEGER
               {
               paused (0),
               running (1)
               }
   MAX-ACCESS  read-write
   STATUS      current
   DESCRIPTION
      "Path: ethOam.editConf.meps.loopback.state

       Possibilities:
               paused   (0)
               running   (1)"
   ::= {er1646v2PbbEthOamEMepsLoopbackEntry 67108864}

er1646v2PbbEthOamEMepsLoss OBJECT-TYPE
   SYNTAX      SEQUENCE OF Er1646v2PbbEthOamEMepsLossEntry
   MAX-ACCESS  not-accessible
   STATUS      current
   DESCRIPTION
      ""
   ::= {er1646v2PbbEthOamEMeps 218103808}

er1646v2PbbEthOamEMepsLossEntry OBJECT-TYPE
   SYNTAX      Er1646v2PbbEthOamEMepsLossEntry
   MAX-ACCESS  not-accessible
   STATUS      current
   DESCRIPTION
      ""
   INDEX      { er1646v2PbbEthOamEMepsLossGlobalIx,
                er1646v2PbbEthOamEMepsTableIx,
                er1646v2PbbEthOamEMepsLossTableIx }
   ::= {er1646v2PbbEthOamEMepsLoss 1}

Er1646v2PbbEthOamEMepsLossEntry ::=
   SEQUENCE
      {
      er1646v2PbbEthOamEMepsLossActions
         VariableLengthTableActions,
      er1646v2PbbEthOamEMepsLossGlobalIx
         GlobalIndex,
      er1646v2PbbEthOamEMepsLossTableIx
         TableIndex,
      er1646v2PbbEthOamEMepsLossDestinationMepId
         Integer32,
      er1646v2PbbEthOamEMepsLossDestinationMacAddress
         OCTET STRING,
      er1646v2PbbEthOamEMepsLossPriority
         Integer32,
      er1646v2PbbEthOamEMepsLossPeriod
         INTEGER,
      er1646v2PbbEthOamEMepsLossLogging
         INTEGER,
      er1646v2PbbEthOamEMepsLossState
         INTEGER
      }

er1646v2PbbEthOamEMepsLossActions OBJECT-TYPE
   SYNTAX      VariableLengthTableActions
   MAX-ACCESS  read-write
   STATUS      current
   DESCRIPTION
      "By way of this field, some manipulations
       on this table may be performed."
   ::= {er1646v2PbbEthOamEMepsLossEntry 2}

er1646v2PbbEthOamEMepsLossGlobalIx OBJECT-TYPE
   SYNTAX      GlobalIndex
   MAX-ACCESS  not-accessible
   STATUS      current
   DESCRIPTION
      "The value of the tlsCntTreeGlobalIndex of the MANAGED OBJECT."
   ::= {er1646v2PbbEthOamEMepsLossEntry 10}

er1646v2PbbEthOamEMepsLossTableIx OBJECT-TYPE
   SYNTAX      TableIndex
   MAX-ACCESS  not-accessible
   STATUS      current
   DESCRIPTION
      ""
   ::= {er1646v2PbbEthOamEMepsLossEntry 11}

er1646v2PbbEthOamEMepsLossDestinationMepId OBJECT-TYPE
   SYNTAX      Integer32
   MAX-ACCESS  read-write
   STATUS      current
   DESCRIPTION
      "Path: ethOam.editConf.meps.loss.destination.mepId"
   ::= {er1646v2PbbEthOamEMepsLossEntry 16842752}

er1646v2PbbEthOamEMepsLossDestinationMacAddress OBJECT-TYPE
   SYNTAX      OCTET STRING
   MAX-ACCESS  read-write
   STATUS      current
   DESCRIPTION
      "Path: ethOam.editConf.meps.loss.destination.macAddress

       MAC address."
   ::= {er1646v2PbbEthOamEMepsLossEntry 16908288}

er1646v2PbbEthOamEMepsLossPriority OBJECT-TYPE
   SYNTAX      Integer32
   MAX-ACCESS  read-write
   STATUS      current
   DESCRIPTION
      "Path: ethOam.editConf.meps.loss.priority"
   ::= {er1646v2PbbEthOamEMepsLossEntry 33554432}

er1646v2PbbEthOamEMepsLossPeriod OBJECT-TYPE
   SYNTAX      INTEGER
               {
               s100ms (3),
               s1s (4),
               s10s (5),
               s1min (6),
               s10min (7)
               }
   MAX-ACCESS  read-write
   STATUS      current
   DESCRIPTION
      "Path: ethOam.editConf.meps.loss.period

       Possibilities:
               100ms   (3)
               1s   (4)
               10s   (5)
               1min   (6)
               10min   (7)"
   ::= {er1646v2PbbEthOamEMepsLossEntry 50331648}

er1646v2PbbEthOamEMepsLossLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: ethOam.editConf.meps.loss.logging

       Possibilities:
               disabled   (0)
               3min   (3)
               5min   (5)
               10min   (10)
               15min   (15)
               30min   (30)
               60min   (60)"
   ::= {er1646v2PbbEthOamEMepsLossEntry 100663296}

er1646v2PbbEthOamEMepsLossState OBJECT-TYPE
   SYNTAX      INTEGER
               {
               paused (0),
               running (1)
               }
   MAX-ACCESS  read-write
   STATUS      current
   DESCRIPTION
      "Path: ethOam.editConf.meps.loss.state

       Possibilities:
               paused   (0)
               running   (1)"
   ::= {er1646v2PbbEthOamEMepsLossEntry 117440512}

er1646v2PbbEthOamEMepsDelay OBJECT-TYPE
   SYNTAX      SEQUENCE OF Er1646v2PbbEthOamEMepsDelayEntry
   MAX-ACCESS  not-accessible
   STATUS      current
   DESCRIPTION
      ""
   ::= {er1646v2PbbEthOamEMeps 234881024}

er1646v2PbbEthOamEMepsDelayEntry OBJECT-TYPE
   SYNTAX      Er1646v2PbbEthOamEMepsDelayEntry
   MAX-ACCESS  not-accessible
   STATUS      current
   DESCRIPTION
      ""
   INDEX      { er1646v2PbbEthOamEMepsDelayGlobalIx,
                er1646v2PbbEthOamEMepsTableIx,
                er1646v2PbbEthOamEMepsDelayTableIx }
   ::= {er1646v2PbbEthOamEMepsDelay 1}

Er1646v2PbbEthOamEMepsDelayEntry ::=
   SEQUENCE
      {
      er1646v2PbbEthOamEMepsDelayActions
         VariableLengthTableActions,
      er1646v2PbbEthOamEMepsDelayGlobalIx
         GlobalIndex,
      er1646v2PbbEthOamEMepsDelayTableIx
         TableIndex,
      er1646v2PbbEthOamEMepsDelayDestinationMepId
         Integer32,
      er1646v2PbbEthOamEMepsDelayDestinationMacAddress
         OCTET STRING,
      er1646v2PbbEthOamEMepsDelayPriority
         Integer32,
      er1646v2PbbEthOamEMepsDelayPeriod
         INTEGER,
      er1646v2PbbEthOamEMepsDelayTimeOut
         Integer32,
      er1646v2PbbEthOamEMepsDelayAlarmSamples
         Integer32,
      er1646v2PbbEthOamEMepsDelayAlarmAlarmAvgOn
         Integer32,
      er1646v2PbbEthOamEMepsDelayAlarmAlarmAvgOff
         Integer32,
      er1646v2PbbEthOamEMepsDelayAlarmAlarmMaxOn
         Integer32,
      er1646v2PbbEthOamEMepsDelayAlarmAlarmMaxOff
         Integer32,
      er1646v2PbbEthOamEMepsDelayAlarmAlarmMinMaxOn
         Integer32,
      er1646v2PbbEthOamEMepsDelayAlarmAlarmMinMaxOff
         Integer32,
      er1646v2PbbEthOamEMepsDelayAlarmAlarmAvgJitterOn
         Integer32,
      er1646v2PbbEthOamEMepsDelayAlarmAlarmAvgJitterOff
         Integer32,
      er1646v2PbbEthOamEMepsDelayAlarmAlarmMaxJitterOn
         Integer32,
      er1646v2PbbEthOamEMepsDelayAlarmAlarmMaxJitterOff
         Integer32,
      er1646v2PbbEthOamEMepsDelayAlarmAlarmMask
         Integer32,
      er1646v2PbbEthOamEMepsDelayLogging
         INTEGER,
      er1646v2PbbEthOamEMepsDelayState
         INTEGER
      }

er1646v2PbbEthOamEMepsDelayActions OBJECT-TYPE
   SYNTAX      VariableLengthTableActions
   MAX-ACCESS  read-write
   STATUS      current
   DESCRIPTION
      "By way of this field, some manipulations
       on this table may be performed."
   ::= {er1646v2PbbEthOamEMepsDelayEntry 2}

er1646v2PbbEthOamEMepsDelayGlobalIx OBJECT-TYPE
   SYNTAX      GlobalIndex
   MAX-ACCESS  not-accessible
   STATUS      current
   DESCRIPTION
      "The value of the tlsCntTreeGlobalIndex of the MANAGED OBJECT."
   ::= {er1646v2PbbEthOamEMepsDelayEntry 10}

er1646v2PbbEthOamEMepsDelayTableIx OBJECT-TYPE
   SYNTAX      TableIndex
   MAX-ACCESS  not-accessible
   STATUS      current
   DESCRIPTION
      ""
   ::= {er1646v2PbbEthOamEMepsDelayEntry 11}

er1646v2PbbEthOamEMepsDelayDestinationMepId OBJECT-TYPE
   SYNTAX      Integer32
   MAX-ACCESS  read-write
   STATUS      current
   DESCRIPTION
      "Path: ethOam.editConf.meps.delay.destination.mepId"
   ::= {er1646v2PbbEthOamEMepsDelayEntry 16842752}

er1646v2PbbEthOamEMepsDelayDestinationMacAddress OBJECT-TYPE
   SYNTAX      OCTET STRING
   MAX-ACCESS  read-write
   STATUS      current
   DESCRIPTION
      "Path: ethOam.editConf.meps.delay.destination.macAddress

       MAC address."
   ::= {er1646v2PbbEthOamEMepsDelayEntry 16908288}

er1646v2PbbEthOamEMepsDelayPriority OBJECT-TYPE
   SYNTAX      Integer32
   MAX-ACCESS  read-write
   STATUS      current
   DESCRIPTION
      "Path: ethOam.editConf.meps.delay.priority"
   ::= {er1646v2PbbEthOamEMepsDelayEntry 33554432}

er1646v2PbbEthOamEMepsDelayPeriod OBJECT-TYPE
   SYNTAX      INTEGER
               {
               s100ms (3),
               s1s (4),
               s10s (5),
               s1min (6),
               s10min (7)
               }
   MAX-ACCESS  read-write
   STATUS      current
   DESCRIPTION
      "Path: ethOam.editConf.meps.delay.period

       Possibilities:
               100ms   (3)
               1s   (4)
               10s   (5)
               1min   (6)
               10min   (7)"
   ::= {er1646v2PbbEthOamEMepsDelayEntry 50331648}

er1646v2PbbEthOamEMepsDelayTimeOut OBJECT-TYPE
   SYNTAX      Integer32
   UNITS       "100msec"
   MAX-ACCESS  read-write
   STATUS      current
   DESCRIPTION
      "Path: ethOam.editConf.meps.delay.timeOut

       unit name = 100msec"
   ::= {er1646v2PbbEthOamEMepsDelayEntry 117440512}

er1646v2PbbEthOamEMepsDelayAlarmSamples OBJECT-TYPE
   SYNTAX      Integer32
   MAX-ACCESS  read-write
   STATUS      current
   DESCRIPTION
      "Path: ethOam.editConf.meps.delay.alarm.samples"
   ::= {er1646v2PbbEthOamEMepsDelayEntry 67174400}

er1646v2PbbEthOamEMepsDelayAlarmAlarmAvgOn OBJECT-TYPE
   SYNTAX      Integer32
   UNITS       "msec"
   MAX-ACCESS  read-write
   STATUS      current
   DESCRIPTION
      "Path: ethOam.editConf.meps.delay.alarm.alarmAvgOn

       unit name = msec"
   ::= {er1646v2PbbEthOamEMepsDelayEntry 67239936}

er1646v2PbbEthOamEMepsDelayAlarmAlarmAvgOff OBJECT-TYPE
   SYNTAX      Integer32
   UNITS       "msec"
   MAX-ACCESS  read-write
   STATUS      current
   DESCRIPTION
      "Path: ethOam.editConf.meps.delay.alarm.alarmAvgOff

       unit name = msec"
   ::= {er1646v2PbbEthOamEMepsDelayEntry 67305472}

er1646v2PbbEthOamEMepsDelayAlarmAlarmMaxOn OBJECT-TYPE
   SYNTAX      Integer32
   UNITS       "msec"
   MAX-ACCESS  read-write
   STATUS      current
   DESCRIPTION
      "Path: ethOam.editConf.meps.delay.alarm.alarmMaxOn

       unit name = msec"
   ::= {er1646v2PbbEthOamEMepsDelayEntry 67371008}

er1646v2PbbEthOamEMepsDelayAlarmAlarmMaxOff OBJECT-TYPE
   SYNTAX      Integer32
   UNITS       "msec"
   MAX-ACCESS  read-write
   STATUS      current
   DESCRIPTION
      "Path: ethOam.editConf.meps.delay.alarm.alarmMaxOff

       unit name = msec"
   ::= {er1646v2PbbEthOamEMepsDelayEntry 67436544}

er1646v2PbbEthOamEMepsDelayAlarmAlarmMinMaxOn OBJECT-TYPE
   SYNTAX      Integer32
   UNITS       "msec"
   MAX-ACCESS  read-write
   STATUS      current
   DESCRIPTION
      "Path: ethOam.editConf.meps.delay.alarm.alarmMinMaxOn

       unit name = msec"
   ::= {er1646v2PbbEthOamEMepsDelayEntry 67764224}

er1646v2PbbEthOamEMepsDelayAlarmAlarmMinMaxOff OBJECT-TYPE
   SYNTAX      Integer32
   UNITS       "msec"
   MAX-ACCESS  read-write
   STATUS      current
   DESCRIPTION
      "Path: ethOam.editConf.meps.delay.alarm.alarmMinMaxOff

       unit name = msec"
   ::= {er1646v2PbbEthOamEMepsDelayEntry 67829760}

er1646v2PbbEthOamEMepsDelayAlarmAlarmAvgJitterOn OBJECT-TYPE
   SYNTAX      Integer32
   UNITS       "msec"
   MAX-ACCESS  read-write
   STATUS      current
   DESCRIPTION
      "Path: ethOam.editConf.meps.delay.alarm.alarmAvgJitterOn

       unit name = msec"
   ::= {er1646v2PbbEthOamEMepsDelayEntry 67502080}

er1646v2PbbEthOamEMepsDelayAlarmAlarmAvgJitterOff OBJECT-TYPE
   SYNTAX      Integer32
   UNITS       "msec"
   MAX-ACCESS  read-write
   STATUS      current
   DESCRIPTION
      "Path: ethOam.editConf.meps.delay.alarm.alarmAvgJitterOff

       unit name = msec"
   ::= {er1646v2PbbEthOamEMepsDelayEntry 67567616}

er1646v2PbbEthOamEMepsDelayAlarmAlarmMaxJitterOn OBJECT-TYPE
   SYNTAX      Integer32
   UNITS       "msec"
   MAX-ACCESS  read-write
   STATUS      current
   DESCRIPTION
      "Path: ethOam.editConf.meps.delay.alarm.alarmMaxJitterOn

       unit name = msec"
   ::= {er1646v2PbbEthOamEMepsDelayEntry 67633152}

er1646v2PbbEthOamEMepsDelayAlarmAlarmMaxJitterOff OBJECT-TYPE
   SYNTAX      Integer32
   UNITS       "msec"
   MAX-ACCESS  read-write
   STATUS      current
   DESCRIPTION
      "Path: ethOam.editConf.meps.delay.alarm.alarmMaxJitterOff

       unit name = msec"
   ::= {er1646v2PbbEthOamEMepsDelayEntry 67698688}

er1646v2PbbEthOamEMepsDelayAlarmAlarmMask OBJECT-TYPE
   SYNTAX      Integer32
   MAX-ACCESS  read-write
   STATUS      current
   DESCRIPTION
      "Path: ethOam.editConf.meps.delay.alarm.alarmMask

       Bit meanings:
               bit 1 = delay,
               bit 2 = jitter"
   ::= {er1646v2PbbEthOamEMepsDelayEntry 67895296}

er1646v2PbbEthOamEMepsDelayLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: ethOam.editConf.meps.delay.logging

       Possibilities:
               disabled   (0)
               3min   (3)
               5min   (5)
               10min   (10)
               15min   (15)
               30min   (30)
               60min   (60)"
   ::= {er1646v2PbbEthOamEMepsDelayEntry 83886080}

er1646v2PbbEthOamEMepsDelayState OBJECT-TYPE
   SYNTAX      INTEGER
               {
               paused (0),
               running (1)
               }
   MAX-ACCESS  read-write
   STATUS      current
   DESCRIPTION
      "Path: ethOam.editConf.meps.delay.state

       Possibilities:
               paused   (0)
               running   (1)"
   ::= {er1646v2PbbEthOamEMepsDelayEntry 100663296}

er1646v2PbbEthOamEMepsQm OBJECT-TYPE
   SYNTAX      SEQUENCE OF Er1646v2PbbEthOamEMepsQmEntry
   MAX-ACCESS  not-accessible
   STATUS      current
   DESCRIPTION
      ""
   ::= {er1646v2PbbEthOamEMeps 301989888}

er1646v2PbbEthOamEMepsQmEntry OBJECT-TYPE
   SYNTAX      Er1646v2PbbEthOamEMepsQmEntry
   MAX-ACCESS  not-accessible
   STATUS      current
   DESCRIPTION
      ""
   INDEX      { er1646v2PbbEthOamEMepsQmGlobalIx,
                er1646v2PbbEthOamEMepsTableIx,
                er1646v2PbbEthOamEMepsQmTableIx }
   ::= {er1646v2PbbEthOamEMepsQm 1}

Er1646v2PbbEthOamEMepsQmEntry ::=
   SEQUENCE
      {
      er1646v2PbbEthOamEMepsQmActions
         VariableLengthTableActions,
      er1646v2PbbEthOamEMepsQmGlobalIx
         GlobalIndex,
      er1646v2PbbEthOamEMepsQmTableIx
         TableIndex,
      er1646v2PbbEthOamEMepsQmName
         DisplayString,
      er1646v2PbbEthOamEMepsQmAdminStatus
         INTEGER,
      er1646v2PbbEthOamEMepsQmDestinationMepId
         Integer32,
      er1646v2PbbEthOamEMepsQmDestinationMacAddress
         OCTET STRING,
      er1646v2PbbEthOamEMepsQmPriority
         Integer32,
      er1646v2PbbEthOamEMepsQmPrioMapQueue
         INTEGER,
      er1646v2PbbEthOamEMepsQmPrioMapDropLevel
         INTEGER,
      er1646v2PbbEthOamEMepsQmProtocol
         INTEGER,
      er1646v2PbbEthOamEMepsQmInterval
         Integer32,
      er1646v2PbbEthOamEMepsQmTimeOut
         Integer32,
      er1646v2PbbEthOamEMepsQmLength
         Integer32,
      er1646v2PbbEthOamEMepsQmIdleSamples
         Integer32,
      er1646v2PbbEthOamEMepsQmLossAlarmSamples
         Integer32,
      er1646v2PbbEthOamEMepsQmLossAlarmAlarmOn
         Integer32,
      er1646v2PbbEthOamEMepsQmLossAlarmAlarmOff
         Integer32,
      er1646v2PbbEthOamEMepsQmLossAlarmAlarmUpOn
         Integer32,
      er1646v2PbbEthOamEMepsQmLossAlarmAlarmUpOff
         Integer32,
      er1646v2PbbEthOamEMepsQmLossAlarmAlarmDownOn
         Integer32,
      er1646v2PbbEthOamEMepsQmLossAlarmAlarmDownOff
         Integer32,
      er1646v2PbbEthOamEMepsQmDelayAlarmSamples
         Integer32,
      er1646v2PbbEthOamEMepsQmDelayAlarmDelayAvrgOn
         Integer32,
      er1646v2PbbEthOamEMepsQmDelayAlarmDelayAvrgOff
         Integer32,
      er1646v2PbbEthOamEMepsQmDelayAlarmDelayMaxOn
         Integer32,
      er1646v2PbbEthOamEMepsQmDelayAlarmDelayMaxOff
         Integer32,
      er1646v2PbbEthOamEMepsQmDelayAlarmDelayMinMaxOn
         Integer32,
      er1646v2PbbEthOamEMepsQmDelayAlarmDelayMinMaxOff
         Integer32,
      er1646v2PbbEthOamEMepsQmDelayAlarmDsType
         INTEGER,
      er1646v2PbbEthOamEMepsQmDelayAlarmDsBinsN
         INTEGER,
      er1646v2PbbEthOamEMepsQmDelayAlarmDsBinsNMn
         Integer32,
      er1646v2PbbEthOamEMepsQmDelayAlarmDsBinsNMx
         Integer32,
      er1646v2PbbEthOamEMepsQmDelayAlarmDsBinsTB1
         Integer32,
      er1646v2PbbEthOamEMepsQmDelayAlarmDsBinsTB2
         Integer32,
      er1646v2PbbEthOamEMepsQmDelayAlarmDsBinsTB3
         Integer32,
      er1646v2PbbEthOamEMepsQmDelayAlarmDsBinsTB4
         Integer32,
      er1646v2PbbEthOamEMepsQmDelayAlarmDsBinsTB5
         Integer32,
      er1646v2PbbEthOamEMepsQmDelayAlarmDsBinsTB6
         Integer32,
      er1646v2PbbEthOamEMepsQmDelayAlarmDsBinsTB7
         Integer32,
      er1646v2PbbEthOamEMepsQmDelayAlarmDsBinsTB8
         Integer32,
      er1646v2PbbEthOamEMepsQmDelayAlarmDsBinsTMx
         Integer32,
      er1646v2PbbEthOamEMepsQmDelayAlarmJitterAvrgOn
         Integer32,
      er1646v2PbbEthOamEMepsQmDelayAlarmJitterAvrgOff
         Integer32,
      er1646v2PbbEthOamEMepsQmDelayAlarmJitterMaxOn
         Integer32,
      er1646v2PbbEthOamEMepsQmDelayAlarmJitterMaxOff
         Integer32,
      er1646v2PbbEthOamEMepsQmDelayAlarmJsN
         INTEGER,
      er1646v2PbbEthOamEMepsQmDelayAlarmJsNMn
         Integer32,
      er1646v2PbbEthOamEMepsQmDelayAlarmJsNMx
         Integer32,
      er1646v2PbbEthOamEMepsQmDelayAlarmJsTB1
         Integer32,
      er1646v2PbbEthOamEMepsQmDelayAlarmJsTB2
         Integer32,
      er1646v2PbbEthOamEMepsQmDelayAlarmJsTB3
         Integer32,
      er1646v2PbbEthOamEMepsQmDelayAlarmJsTB4
         Integer32,
      er1646v2PbbEthOamEMepsQmDelayAlarmJsTB5
         Integer32,
      er1646v2PbbEthOamEMepsQmDelayAlarmJsTB6
         Integer32,
      er1646v2PbbEthOamEMepsQmDelayAlarmJsTB7
         Integer32,
      er1646v2PbbEthOamEMepsQmDelayAlarmJsTB8
         Integer32,
      er1646v2PbbEthOamEMepsQmDelayAlarmJsTMx
         Integer32,
      er1646v2PbbEthOamEMepsQmDelayAlarmJitterUpAvrgOn
         Integer32,
      er1646v2PbbEthOamEMepsQmDelayAlarmJitterUpAvrgOff
         Integer32,
      er1646v2PbbEthOamEMepsQmDelayAlarmJitterUpMaxOn
         Integer32,
      er1646v2PbbEthOamEMepsQmDelayAlarmJitterUpMaxOff
         Integer32,
      er1646v2PbbEthOamEMepsQmDelayAlarmJupsN
         INTEGER,
      er1646v2PbbEthOamEMepsQmDelayAlarmJupsNMn
         Integer32,
      er1646v2PbbEthOamEMepsQmDelayAlarmJupsNMx
         Integer32,
      er1646v2PbbEthOamEMepsQmDelayAlarmJupsTB1
         Integer32,
      er1646v2PbbEthOamEMepsQmDelayAlarmJupsTB2
         Integer32,
      er1646v2PbbEthOamEMepsQmDelayAlarmJupsTB3
         Integer32,
      er1646v2PbbEthOamEMepsQmDelayAlarmJupsTB4
         Integer32,
      er1646v2PbbEthOamEMepsQmDelayAlarmJupsTB5
         Integer32,
      er1646v2PbbEthOamEMepsQmDelayAlarmJupsTB6
         Integer32,
      er1646v2PbbEthOamEMepsQmDelayAlarmJupsTB7
         Integer32,
      er1646v2PbbEthOamEMepsQmDelayAlarmJupsTB8
         Integer32,
      er1646v2PbbEthOamEMepsQmDelayAlarmJupsTMx
         Integer32,
      er1646v2PbbEthOamEMepsQmDelayAlarmJitterDownAvrgOn
         Integer32,
      er1646v2PbbEthOamEMepsQmDelayAlarmJitterDownAvrgOff
         Integer32,
      er1646v2PbbEthOamEMepsQmDelayAlarmJitterDownMaxOn
         Integer32,
      er1646v2PbbEthOamEMepsQmDelayAlarmJitterDownMaxOff
         Integer32,
      er1646v2PbbEthOamEMepsQmDelayAlarmJdownsN
         INTEGER,
      er1646v2PbbEthOamEMepsQmDelayAlarmJdownsNMn
         Integer32,
      er1646v2PbbEthOamEMepsQmDelayAlarmJdownsNMx
         Integer32,
      er1646v2PbbEthOamEMepsQmDelayAlarmJdownsTB1
         Integer32,
      er1646v2PbbEthOamEMepsQmDelayAlarmJdownsTB2
         Integer32,
      er1646v2PbbEthOamEMepsQmDelayAlarmJdownsTB3
         Integer32,
      er1646v2PbbEthOamEMepsQmDelayAlarmJdownsTB4
         Integer32,
      er1646v2PbbEthOamEMepsQmDelayAlarmJdownsTB5
         Integer32,
      er1646v2PbbEthOamEMepsQmDelayAlarmJdownsTB6
         Integer32,
      er1646v2PbbEthOamEMepsQmDelayAlarmJdownsTB7
         Integer32,
      er1646v2PbbEthOamEMepsQmDelayAlarmJdownsTB8
         Integer32,
      er1646v2PbbEthOamEMepsQmDelayAlarmJdownsTMx
         Integer32,
      er1646v2PbbEthOamEMepsQmDelayAlarmDelayUpAvrgOn
         Integer32,
      er1646v2PbbEthOamEMepsQmDelayAlarmDelayUpAvrgOff
         Integer32,
      er1646v2PbbEthOamEMepsQmDelayAlarmDelayUpMaxOn
         Integer32,
      er1646v2PbbEthOamEMepsQmDelayAlarmDelayUpMaxOff
         Integer32,
      er1646v2PbbEthOamEMepsQmDelayAlarmDupsType
         INTEGER,
      er1646v2PbbEthOamEMepsQmDelayAlarmDupsBinsN
         INTEGER,
      er1646v2PbbEthOamEMepsQmDelayAlarmDupsBinsNMn
         Integer32,
      er1646v2PbbEthOamEMepsQmDelayAlarmDupsBinsNMx
         Integer32,
      er1646v2PbbEthOamEMepsQmDelayAlarmDupsBinsTB1
         Integer32,
      er1646v2PbbEthOamEMepsQmDelayAlarmDupsBinsTB2
         Integer32,
      er1646v2PbbEthOamEMepsQmDelayAlarmDupsBinsTB3
         Integer32,
      er1646v2PbbEthOamEMepsQmDelayAlarmDupsBinsTB4
         Integer32,
      er1646v2PbbEthOamEMepsQmDelayAlarmDupsBinsTB5
         Integer32,
      er1646v2PbbEthOamEMepsQmDelayAlarmDupsBinsTB6
         Integer32,
      er1646v2PbbEthOamEMepsQmDelayAlarmDupsBinsTB7
         Integer32,
      er1646v2PbbEthOamEMepsQmDelayAlarmDupsBinsTB8
         Integer32,
      er1646v2PbbEthOamEMepsQmDelayAlarmDupsBinsTMx
         Integer32,
      er1646v2PbbEthOamEMepsQmDelayAlarmDelayDownAvrgOn
         Integer32,
      er1646v2PbbEthOamEMepsQmDelayAlarmDelayDownAvrgOff
         Integer32,
      er1646v2PbbEthOamEMepsQmDelayAlarmDelayDownMaxOn
         Integer32,
      er1646v2PbbEthOamEMepsQmDelayAlarmDelayDownMaxOff
         Integer32,
      er1646v2PbbEthOamEMepsQmDelayAlarmDdownsType
         INTEGER,
      er1646v2PbbEthOamEMepsQmDelayAlarmDdownsBinsN
         INTEGER,
      er1646v2PbbEthOamEMepsQmDelayAlarmDdownsBinsNMn
         Integer32,
      er1646v2PbbEthOamEMepsQmDelayAlarmDdownsBinsNMx
         Integer32,
      er1646v2PbbEthOamEMepsQmDelayAlarmDdownsBinsTB1
         Integer32,
      er1646v2PbbEthOamEMepsQmDelayAlarmDdownsBinsTB2
         Integer32,
      er1646v2PbbEthOamEMepsQmDelayAlarmDdownsBinsTB3
         Integer32,
      er1646v2PbbEthOamEMepsQmDelayAlarmDdownsBinsTB4
         Integer32,
      er1646v2PbbEthOamEMepsQmDelayAlarmDdownsBinsTB5
         Integer32,
      er1646v2PbbEthOamEMepsQmDelayAlarmDdownsBinsTB6
         Integer32,
      er1646v2PbbEthOamEMepsQmDelayAlarmDdownsBinsTB7
         Integer32,
      er1646v2PbbEthOamEMepsQmDelayAlarmDdownsBinsTB8
         Integer32,
      er1646v2PbbEthOamEMepsQmDelayAlarmDdownsBinsTMx
         Integer32,
      er1646v2PbbEthOamEMepsQmAlarmMask
         Integer32,
      er1646v2PbbEthOamEMepsQmEventMask
         Integer32,
      er1646v2PbbEthOamEMepsQmLogging
         INTEGER,
      er1646v2PbbEthOamEMepsQmLoggingDepth
         INTEGER
      }

er1646v2PbbEthOamEMepsQmActions OBJECT-TYPE
   SYNTAX      VariableLengthTableActions
   MAX-ACCESS  read-write
   STATUS      current
   DESCRIPTION
      "By way of this field, some manipulations
       on this table may be performed."
   ::= {er1646v2PbbEthOamEMepsQmEntry 2}

er1646v2PbbEthOamEMepsQmGlobalIx OBJECT-TYPE
   SYNTAX      GlobalIndex
   MAX-ACCESS  not-accessible
   STATUS      current
   DESCRIPTION
      "The value of the tlsCntTreeGlobalIndex of the MANAGED OBJECT."
   ::= {er1646v2PbbEthOamEMepsQmEntry 10}

er1646v2PbbEthOamEMepsQmTableIx OBJECT-TYPE
   SYNTAX      TableIndex
   MAX-ACCESS  not-accessible
   STATUS      current
   DESCRIPTION
      ""
   ::= {er1646v2PbbEthOamEMepsQmEntry 11}

er1646v2PbbEthOamEMepsQmName OBJECT-TYPE
   SYNTAX      DisplayString
   MAX-ACCESS  read-write
   STATUS      current
   DESCRIPTION
      "Path: ethOam.editConf.meps.qualityMonitor.name"
   ::= {er1646v2PbbEthOamEMepsQmEntry 234881024}

er1646v2PbbEthOamEMepsQmAdminStatus OBJECT-TYPE
   SYNTAX      INTEGER
               {
               enabled (1),
               disabled (3)
               }
   MAX-ACCESS  read-write
   STATUS      current
   DESCRIPTION
      "Path: ethOam.editConf.meps.qualityMonitor.adminStatus

       Possibilities:
               enabled   (1)
               disabled   (3)"
   ::= {er1646v2PbbEthOamEMepsQmEntry 402653184}

er1646v2PbbEthOamEMepsQmDestinationMepId OBJECT-TYPE
   SYNTAX      Integer32
   MAX-ACCESS  read-write
   STATUS      current
   DESCRIPTION
      "Path: ethOam.editConf.meps.qualityMonitor.destination.mepId"
   ::= {er1646v2PbbEthOamEMepsQmEntry 16842752}

er1646v2PbbEthOamEMepsQmDestinationMacAddress OBJECT-TYPE
   SYNTAX      OCTET STRING
   MAX-ACCESS  read-write
   STATUS      current
   DESCRIPTION
      "Path: ethOam.editConf.meps.qualityMonitor.destination.macAddress

       MAC address."
   ::= {er1646v2PbbEthOamEMepsQmEntry 16908288}

er1646v2PbbEthOamEMepsQmPriority OBJECT-TYPE
   SYNTAX      Integer32
   MAX-ACCESS  read-write
   STATUS      current
   DESCRIPTION
      "Path: ethOam.editConf.meps.qualityMonitor.priority"
   ::= {er1646v2PbbEthOamEMepsQmEntry 33554432}

er1646v2PbbEthOamEMepsQmPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.meps.qualityMonitor.prioMap.queue

       Possibilities:
               queue1   (0)
               queue2   (1)
               queue3   (2)
               queue4   (3)
               queue5   (4)
               lowDelayQueue   (5)
               lowDelay2Queue   (6)
               systemQueue   (7)"
   ::= {er1646v2PbbEthOamEMepsQmEntry 285278208}

er1646v2PbbEthOamEMepsQmPrioMapDropLevel OBJECT-TYPE
   SYNTAX      INTEGER
               {
               dropOnQueue (0)
               }
   MAX-ACCESS  read-write
   STATUS      current
   DESCRIPTION
      "Path: ethOam.editConf.meps.qualityMonitor.prioMap.dropLevel

       Possibilities:
               dropOnQueue   (0)"
   ::= {er1646v2PbbEthOamEMepsQmEntry 285343744}

er1646v2PbbEthOamEMepsQmProtocol OBJECT-TYPE
   SYNTAX      INTEGER
               {
               loopback (4),
               synthLoss (6),
               delay (7)
               }
   MAX-ACCESS  read-write
   STATUS      current
   DESCRIPTION
      "Path: ethOam.editConf.meps.qualityMonitor.protocol

       Possibilities:
               loopback   (4)
               synthLoss   (6)
               delay   (7)"
   ::= {er1646v2PbbEthOamEMepsQmEntry 520093696}

er1646v2PbbEthOamEMepsQmInterval OBJECT-TYPE
   SYNTAX      Integer32
   UNITS       "100msec"
   MAX-ACCESS  read-write
   STATUS      current
   DESCRIPTION
      "Path: ethOam.editConf.meps.qualityMonitor.interval

       unit name = 100msec"
   ::= {er1646v2PbbEthOamEMepsQmEntry 50331648}

er1646v2PbbEthOamEMepsQmTimeOut OBJECT-TYPE
   SYNTAX      Integer32
   UNITS       "100msec"
   MAX-ACCESS  read-write
   STATUS      current
   DESCRIPTION
      "Path: ethOam.editConf.meps.qualityMonitor.timeOut

       unit name = 100msec"
   ::= {er1646v2PbbEthOamEMepsQmEntry 150994944}

er1646v2PbbEthOamEMepsQmLength OBJECT-TYPE
   SYNTAX      Integer32
   MAX-ACCESS  read-write
   STATUS      current
   DESCRIPTION
      "Path: ethOam.editConf.meps.qualityMonitor.length"
   ::= {er1646v2PbbEthOamEMepsQmEntry 83886080}

er1646v2PbbEthOamEMepsQmIdleSamples OBJECT-TYPE
   SYNTAX      Integer32
   MAX-ACCESS  read-write
   STATUS      current
   DESCRIPTION
      "Path: ethOam.editConf.meps.qualityMonitor.idleSamples"
   ::= {er1646v2PbbEthOamEMepsQmEntry 419430400}

er1646v2PbbEthOamEMepsQmLossAlarmSamples OBJECT-TYPE
   SYNTAX      Integer32
   MAX-ACCESS  read-write
   STATUS      current
   DESCRIPTION
      "Path: ethOam.editConf.meps.qualityMonitor.lossAlarm.samples"
   ::= {er1646v2PbbEthOamEMepsQmEntry 100728832}

er1646v2PbbEthOamEMepsQmLossAlarmAlarmOn OBJECT-TYPE
   SYNTAX      Integer32
   MAX-ACCESS  read-write
   STATUS      current
   DESCRIPTION
      "Path: ethOam.editConf.meps.qualityMonitor.lossAlarm.alarmOn"
   ::= {er1646v2PbbEthOamEMepsQmEntry 100794368}

er1646v2PbbEthOamEMepsQmLossAlarmAlarmOff OBJECT-TYPE
   SYNTAX      Integer32
   MAX-ACCESS  read-write
   STATUS      current
   DESCRIPTION
      "Path: ethOam.editConf.meps.qualityMonitor.lossAlarm.alarmOff"
   ::= {er1646v2PbbEthOamEMepsQmEntry 100859904}

er1646v2PbbEthOamEMepsQmLossAlarmAlarmUpOn OBJECT-TYPE
   SYNTAX      Integer32
   MAX-ACCESS  read-write
   STATUS      current
   DESCRIPTION
      "Path: ethOam.editConf.meps.qualityMonitor.lossAlarm.alarmUpOn"
   ::= {er1646v2PbbEthOamEMepsQmEntry 100925440}

er1646v2PbbEthOamEMepsQmLossAlarmAlarmUpOff OBJECT-TYPE
   SYNTAX      Integer32
   MAX-ACCESS  read-write
   STATUS      current
   DESCRIPTION
      "Path: ethOam.editConf.meps.qualityMonitor.lossAlarm.alarmUpOff"
   ::= {er1646v2PbbEthOamEMepsQmEntry 100990976}

er1646v2PbbEthOamEMepsQmLossAlarmAlarmDownOn OBJECT-TYPE
   SYNTAX      Integer32
   MAX-ACCESS  read-write
   STATUS      current
   DESCRIPTION
      "Path: ethOam.editConf.meps.qualityMonitor.lossAlarm.alarmDownOn"
   ::= {er1646v2PbbEthOamEMepsQmEntry 101056512}

er1646v2PbbEthOamEMepsQmLossAlarmAlarmDownOff OBJECT-TYPE
   SYNTAX      Integer32
   MAX-ACCESS  read-write
   STATUS      current
   DESCRIPTION
      "Path: ethOam.editConf.meps.qualityMonitor.lossAlarm.alarmDownOff"
   ::= {er1646v2PbbEthOamEMepsQmEntry 101122048}

er1646v2PbbEthOamEMepsQmDelayAlarmSamples OBJECT-TYPE
   SYNTAX      Integer32
   MAX-ACCESS  read-write
   STATUS      current
   DESCRIPTION
      "Path: ethOam.editConf.meps.qualityMonitor.delayAlarm.samples"
   ::= {er1646v2PbbEthOamEMepsQmEntry 117506048}

er1646v2PbbEthOamEMepsQmDelayAlarmDelayAvrgOn OBJECT-TYPE
   SYNTAX      Integer32
   UNITS       "msec"
   MAX-ACCESS  read-write
   STATUS      current
   DESCRIPTION
      "Path: ethOam.editConf.meps.qualityMonitor.delayAlarm.delayAvrgOn

       unit name = msec"
   ::= {er1646v2PbbEthOamEMepsQmEntry 117571584}

er1646v2PbbEthOamEMepsQmDelayAlarmDelayAvrgOff OBJECT-TYPE
   SYNTAX      Integer32
   UNITS       "msec"
   MAX-ACCESS  read-write
   STATUS      current
   DESCRIPTION
      "Path: ethOam.editConf.meps.qualityMonitor.delayAlarm.delayAvrgOff

       unit name = msec"
   ::= {er1646v2PbbEthOamEMepsQmEntry 117637120}

er1646v2PbbEthOamEMepsQmDelayAlarmDelayMaxOn OBJECT-TYPE
   SYNTAX      Integer32
   UNITS       "msec"
   MAX-ACCESS  read-write
   STATUS      current
   DESCRIPTION
      "Path: ethOam.editConf.meps.qualityMonitor.delayAlarm.delayMaxOn

       unit name = msec"
   ::= {er1646v2PbbEthOamEMepsQmEntry 117702656}

er1646v2PbbEthOamEMepsQmDelayAlarmDelayMaxOff OBJECT-TYPE
   SYNTAX      Integer32
   UNITS       "msec"
   MAX-ACCESS  read-write
   STATUS      current
   DESCRIPTION
      "Path: ethOam.editConf.meps.qualityMonitor.delayAlarm.delayMaxOff

       unit name = msec"
   ::= {er1646v2PbbEthOamEMepsQmEntry 117768192}

er1646v2PbbEthOamEMepsQmDelayAlarmDelayMinMaxOn OBJECT-TYPE
   SYNTAX      Integer32
   UNITS       "msec"
   MAX-ACCESS  read-write
   STATUS      current
   DESCRIPTION
      "Path: ethOam.editConf.meps.qualityMonitor.delayAlarm.delayMinMaxOn

       unit name = msec"
   ::= {er1646v2PbbEthOamEMepsQmEntry 118095872}

er1646v2PbbEthOamEMepsQmDelayAlarmDelayMinMaxOff OBJECT-TYPE
   SYNTAX      Integer32
   UNITS       "msec"
   MAX-ACCESS  read-write
   STATUS      current
   DESCRIPTION
      "Path: ethOam.editConf.meps.qualityMonitor.delayAlarm.delayMinMaxOff

       unit name = msec"
   ::= {er1646v2PbbEthOamEMepsQmEntry 118161408}

er1646v2PbbEthOamEMepsQmDelayAlarmDsType OBJECT-TYPE
   SYNTAX      INTEGER
               {
               fd (1),
               fdr (2)
               }
   MAX-ACCESS  read-write
   STATUS      current
   DESCRIPTION
      "Path: ethOam.editConf.meps.qualityMonitor.delayAlarm.delayStat.type

       Possibilities:
               fd   (1)
               fdr   (2)"
   ::= {er1646v2PbbEthOamEMepsQmEntry 119283712}

er1646v2PbbEthOamEMepsQmDelayAlarmDsBinsN OBJECT-TYPE
   SYNTAX      INTEGER
               {
               none (0)
               }
   MAX-ACCESS  read-write
   STATUS      current
   DESCRIPTION
      "Path: ethOam.editConf.meps.qualityMonitor.delayAlarm.delayStat.bins.none

       Possibilities:
               none   (0)"
   ::= {er1646v2PbbEthOamEMepsQmEntry 119292928}

er1646v2PbbEthOamEMepsQmDelayAlarmDsBinsNMn OBJECT-TYPE
   SYNTAX      Integer32
   UNITS       "msec"
   MAX-ACCESS  read-write
   STATUS      current
   DESCRIPTION
      "Path: ethOam.editConf.meps.qualityMonitor.delayAlarm.delayStat.bins.range.min

       unit name = msec"
   ::= {er1646v2PbbEthOamEMepsQmEntry 119294080}

er1646v2PbbEthOamEMepsQmDelayAlarmDsBinsNMx OBJECT-TYPE
   SYNTAX      Integer32
   UNITS       "msec"
   MAX-ACCESS  read-write
   STATUS      current
   DESCRIPTION
      "Path: ethOam.editConf.meps.qualityMonitor.delayAlarm.delayStat.bins.range.max

       unit name = msec"
   ::= {er1646v2PbbEthOamEMepsQmEntry 119294208}

er1646v2PbbEthOamEMepsQmDelayAlarmDsBinsTB1 OBJECT-TYPE
   SYNTAX      Integer32
   UNITS       "msec"
   MAX-ACCESS  read-write
   STATUS      current
   DESCRIPTION
      "Path: ethOam.editConf.meps.qualityMonitor.delayAlarm.delayStat.bins.table.bin1

       unit name = msec"
   ::= {er1646v2PbbEthOamEMepsQmEntry 119295040}

er1646v2PbbEthOamEMepsQmDelayAlarmDsBinsTB2 OBJECT-TYPE
   SYNTAX      Integer32
   UNITS       "msec"
   MAX-ACCESS  read-write
   STATUS      current
   DESCRIPTION
      "Path: ethOam.editConf.meps.qualityMonitor.delayAlarm.delayStat.bins.table.bin2

       unit name = msec"
   ::= {er1646v2PbbEthOamEMepsQmEntry 119295104}

er1646v2PbbEthOamEMepsQmDelayAlarmDsBinsTB3 OBJECT-TYPE
   SYNTAX      Integer32
   UNITS       "msec"
   MAX-ACCESS  read-write
   STATUS      current
   DESCRIPTION
      "Path: ethOam.editConf.meps.qualityMonitor.delayAlarm.delayStat.bins.table.bin3

       unit name = msec"
   ::= {er1646v2PbbEthOamEMepsQmEntry 119295168}

er1646v2PbbEthOamEMepsQmDelayAlarmDsBinsTB4 OBJECT-TYPE
   SYNTAX      Integer32
   UNITS       "msec"
   MAX-ACCESS  read-write
   STATUS      current
   DESCRIPTION
      "Path: ethOam.editConf.meps.qualityMonitor.delayAlarm.delayStat.bins.table.bin4

       unit name = msec"
   ::= {er1646v2PbbEthOamEMepsQmEntry 119295232}

er1646v2PbbEthOamEMepsQmDelayAlarmDsBinsTB5 OBJECT-TYPE
   SYNTAX      Integer32
   UNITS       "msec"
   MAX-ACCESS  read-write
   STATUS      current
   DESCRIPTION
      "Path: ethOam.editConf.meps.qualityMonitor.delayAlarm.delayStat.bins.table.bin5

       unit name = msec"
   ::= {er1646v2PbbEthOamEMepsQmEntry 119295296}

er1646v2PbbEthOamEMepsQmDelayAlarmDsBinsTB6 OBJECT-TYPE
   SYNTAX      Integer32
   UNITS       "msec"
   MAX-ACCESS  read-write
   STATUS      current
   DESCRIPTION
      "Path: ethOam.editConf.meps.qualityMonitor.delayAlarm.delayStat.bins.table.bin6

       unit name = msec"
   ::= {er1646v2PbbEthOamEMepsQmEntry 119295360}

er1646v2PbbEthOamEMepsQmDelayAlarmDsBinsTB7 OBJECT-TYPE
   SYNTAX      Integer32
   UNITS       "msec"
   MAX-ACCESS  read-write
   STATUS      current
   DESCRIPTION
      "Path: ethOam.editConf.meps.qualityMonitor.delayAlarm.delayStat.bins.table.bin7

       unit name = msec"
   ::= {er1646v2PbbEthOamEMepsQmEntry 119295424}

er1646v2PbbEthOamEMepsQmDelayAlarmDsBinsTB8 OBJECT-TYPE
   SYNTAX      Integer32
   UNITS       "msec"
   MAX-ACCESS  read-write
   STATUS      current
   DESCRIPTION
      "Path: ethOam.editConf.meps.qualityMonitor.delayAlarm.delayStat.bins.table.bin8

       unit name = msec"
   ::= {er1646v2PbbEthOamEMepsQmEntry 119295488}

er1646v2PbbEthOamEMepsQmDelayAlarmDsBinsTMx OBJECT-TYPE
   SYNTAX      Integer32
   UNITS       "msec"
   MAX-ACCESS  read-write
   STATUS      current
   DESCRIPTION
      "Path: ethOam.editConf.meps.qualityMonitor.delayAlarm.delayStat.bins.table.max

       unit name = msec"
   ::= {er1646v2PbbEthOamEMepsQmEntry 119295552}

er1646v2PbbEthOamEMepsQmDelayAlarmJitterAvrgOn OBJECT-TYPE
   SYNTAX      Integer32
   UNITS       "msec"
   MAX-ACCESS  read-write
   STATUS      current
   DESCRIPTION
      "Path: ethOam.editConf.meps.qualityMonitor.delayAlarm.jitterAvrgOn

       unit name = msec"
   ::= {er1646v2PbbEthOamEMepsQmEntry 117833728}

er1646v2PbbEthOamEMepsQmDelayAlarmJitterAvrgOff OBJECT-TYPE
   SYNTAX      Integer32
   UNITS       "msec"
   MAX-ACCESS  read-write
   STATUS      current
   DESCRIPTION
      "Path: ethOam.editConf.meps.qualityMonitor.delayAlarm.jitterAvrgOff

       unit name = msec"
   ::= {er1646v2PbbEthOamEMepsQmEntry 117899264}

er1646v2PbbEthOamEMepsQmDelayAlarmJitterMaxOn OBJECT-TYPE
   SYNTAX      Integer32
   UNITS       "msec"
   MAX-ACCESS  read-write
   STATUS      current
   DESCRIPTION
      "Path: ethOam.editConf.meps.qualityMonitor.delayAlarm.jitterMaxOn

       unit name = msec"
   ::= {er1646v2PbbEthOamEMepsQmEntry 117964800}

er1646v2PbbEthOamEMepsQmDelayAlarmJitterMaxOff OBJECT-TYPE
   SYNTAX      Integer32
   UNITS       "msec"
   MAX-ACCESS  read-write
   STATUS      current
   DESCRIPTION
      "Path: ethOam.editConf.meps.qualityMonitor.delayAlarm.jitterMaxOff

       unit name = msec"
   ::= {er1646v2PbbEthOamEMepsQmEntry 118030336}

er1646v2PbbEthOamEMepsQmDelayAlarmJsN OBJECT-TYPE
   SYNTAX      INTEGER
               {
               none (0)
               }
   MAX-ACCESS  read-write
   STATUS      current
   DESCRIPTION
      "Path: ethOam.editConf.meps.qualityMonitor.delayAlarm.jitterStat.none

       Possibilities:
               none   (0)"
   ::= {er1646v2PbbEthOamEMepsQmEntry 119676928}

er1646v2PbbEthOamEMepsQmDelayAlarmJsNMn OBJECT-TYPE
   SYNTAX      Integer32
   UNITS       "msec"
   MAX-ACCESS  read-write
   STATUS      current
   DESCRIPTION
      "Path: ethOam.editConf.meps.qualityMonitor.delayAlarm.jitterStat.range.min

       unit name = msec"
   ::= {er1646v2PbbEthOamEMepsQmEntry 119686144}

er1646v2PbbEthOamEMepsQmDelayAlarmJsNMx OBJECT-TYPE
   SYNTAX      Integer32
   UNITS       "msec"
   MAX-ACCESS  read-write
   STATUS      current
   DESCRIPTION
      "Path: ethOam.editConf.meps.qualityMonitor.delayAlarm.jitterStat.range.max

       unit name = msec"
   ::= {er1646v2PbbEthOamEMepsQmEntry 119687168}

er1646v2PbbEthOamEMepsQmDelayAlarmJsTB1 OBJECT-TYPE
   SYNTAX      Integer32
   UNITS       "msec"
   MAX-ACCESS  read-write
   STATUS      current
   DESCRIPTION
      "Path: ethOam.editConf.meps.qualityMonitor.delayAlarm.jitterStat.table.bin1

       unit name = msec"
   ::= {er1646v2PbbEthOamEMepsQmEntry 119693824}

er1646v2PbbEthOamEMepsQmDelayAlarmJsTB2 OBJECT-TYPE
   SYNTAX      Integer32
   UNITS       "msec"
   MAX-ACCESS  read-write
   STATUS      current
   DESCRIPTION
      "Path: ethOam.editConf.meps.qualityMonitor.delayAlarm.jitterStat.table.bin2

       unit name = msec"
   ::= {er1646v2PbbEthOamEMepsQmEntry 119694336}

er1646v2PbbEthOamEMepsQmDelayAlarmJsTB3 OBJECT-TYPE
   SYNTAX      Integer32
   UNITS       "msec"
   MAX-ACCESS  read-write
   STATUS      current
   DESCRIPTION
      "Path: ethOam.editConf.meps.qualityMonitor.delayAlarm.jitterStat.table.bin3

       unit name = msec"
   ::= {er1646v2PbbEthOamEMepsQmEntry 119694848}

er1646v2PbbEthOamEMepsQmDelayAlarmJsTB4 OBJECT-TYPE
   SYNTAX      Integer32
   UNITS       "msec"
   MAX-ACCESS  read-write
   STATUS      current
   DESCRIPTION
      "Path: ethOam.editConf.meps.qualityMonitor.delayAlarm.jitterStat.table.bin4

       unit name = msec"
   ::= {er1646v2PbbEthOamEMepsQmEntry 119695360}

er1646v2PbbEthOamEMepsQmDelayAlarmJsTB5 OBJECT-TYPE
   SYNTAX      Integer32
   UNITS       "msec"
   MAX-ACCESS  read-write
   STATUS      current
   DESCRIPTION
      "Path: ethOam.editConf.meps.qualityMonitor.delayAlarm.jitterStat.table.bin5

       unit name = msec"
   ::= {er1646v2PbbEthOamEMepsQmEntry 119695872}

er1646v2PbbEthOamEMepsQmDelayAlarmJsTB6 OBJECT-TYPE
   SYNTAX      Integer32
   UNITS       "msec"
   MAX-ACCESS  read-write
   STATUS      current
   DESCRIPTION
      "Path: ethOam.editConf.meps.qualityMonitor.delayAlarm.jitterStat.table.bin6

       unit name = msec"
   ::= {er1646v2PbbEthOamEMepsQmEntry 119696384}

er1646v2PbbEthOamEMepsQmDelayAlarmJsTB7 OBJECT-TYPE
   SYNTAX      Integer32
   UNITS       "msec"
   MAX-ACCESS  read-write
   STATUS      current
   DESCRIPTION
      "Path: ethOam.editConf.meps.qualityMonitor.delayAlarm.jitterStat.table.bin7

       unit name = msec"
   ::= {er1646v2PbbEthOamEMepsQmEntry 119696896}

er1646v2PbbEthOamEMepsQmDelayAlarmJsTB8 OBJECT-TYPE
   SYNTAX      Integer32
   UNITS       "msec"
   MAX-ACCESS  read-write
   STATUS      current
   DESCRIPTION
      "Path: ethOam.editConf.meps.qualityMonitor.delayAlarm.jitterStat.table.bin8

       unit name = msec"
   ::= {er1646v2PbbEthOamEMepsQmEntry 119697408}

er1646v2PbbEthOamEMepsQmDelayAlarmJsTMx OBJECT-TYPE
   SYNTAX      Integer32
   UNITS       "msec"
   MAX-ACCESS  read-write
   STATUS      current
   DESCRIPTION
      "Path: ethOam.editConf.meps.qualityMonitor.delayAlarm.jitterStat.table.max

       unit name = msec"
   ::= {er1646v2PbbEthOamEMepsQmEntry 119697920}

er1646v2PbbEthOamEMepsQmDelayAlarmJitterUpAvrgOn OBJECT-TYPE
   SYNTAX      Integer32
   UNITS       "msec"
   MAX-ACCESS  read-write
   STATUS      current
   DESCRIPTION
      "Path: ethOam.editConf.meps.qualityMonitor.delayAlarm.jitterUpAvrgOn

       unit name = msec"
   ::= {er1646v2PbbEthOamEMepsQmEntry 118226944}

er1646v2PbbEthOamEMepsQmDelayAlarmJitterUpAvrgOff OBJECT-TYPE
   SYNTAX      Integer32
   UNITS       "msec"
   MAX-ACCESS  read-write
   STATUS      current
   DESCRIPTION
      "Path: ethOam.editConf.meps.qualityMonitor.delayAlarm.jitterUpAvrgOff

       unit name = msec"
   ::= {er1646v2PbbEthOamEMepsQmEntry 118292480}

er1646v2PbbEthOamEMepsQmDelayAlarmJitterUpMaxOn OBJECT-TYPE
   SYNTAX      Integer32
   UNITS       "msec"
   MAX-ACCESS  read-write
   STATUS      current
   DESCRIPTION
      "Path: ethOam.editConf.meps.qualityMonitor.delayAlarm.jitterUpMaxOn

       unit name = msec"
   ::= {er1646v2PbbEthOamEMepsQmEntry 118358016}

er1646v2PbbEthOamEMepsQmDelayAlarmJitterUpMaxOff OBJECT-TYPE
   SYNTAX      Integer32
   UNITS       "msec"
   MAX-ACCESS  read-write
   STATUS      current
   DESCRIPTION
      "Path: ethOam.editConf.meps.qualityMonitor.delayAlarm.jitterUpMaxOff

       unit name = msec"
   ::= {er1646v2PbbEthOamEMepsQmEntry 118423552}

er1646v2PbbEthOamEMepsQmDelayAlarmJupsN OBJECT-TYPE
   SYNTAX      INTEGER
               {
               none (0)
               }
   MAX-ACCESS  read-write
   STATUS      current
   DESCRIPTION
      "Path: ethOam.editConf.meps.qualityMonitor.delayAlarm.jitterUpStat.none

       Possibilities:
               none   (0)"
   ::= {er1646v2PbbEthOamEMepsQmEntry 119808000}

er1646v2PbbEthOamEMepsQmDelayAlarmJupsNMn OBJECT-TYPE
   SYNTAX      Integer32
   UNITS       "msec"
   MAX-ACCESS  read-write
   STATUS      current
   DESCRIPTION
      "Path: ethOam.editConf.meps.qualityMonitor.delayAlarm.jitterUpStat.range.min

       unit name = msec"
   ::= {er1646v2PbbEthOamEMepsQmEntry 119817216}

er1646v2PbbEthOamEMepsQmDelayAlarmJupsNMx OBJECT-TYPE
   SYNTAX      Integer32
   UNITS       "msec"
   MAX-ACCESS  read-write
   STATUS      current
   DESCRIPTION
      "Path: ethOam.editConf.meps.qualityMonitor.delayAlarm.jitterUpStat.range.max

       unit name = msec"
   ::= {er1646v2PbbEthOamEMepsQmEntry 119818240}

er1646v2PbbEthOamEMepsQmDelayAlarmJupsTB1 OBJECT-TYPE
   SYNTAX      Integer32
   UNITS       "msec"
   MAX-ACCESS  read-write
   STATUS      current
   DESCRIPTION
      "Path: ethOam.editConf.meps.qualityMonitor.delayAlarm.jitterUpStat.table.bin1

       unit name = msec"
   ::= {er1646v2PbbEthOamEMepsQmEntry 119824896}

er1646v2PbbEthOamEMepsQmDelayAlarmJupsTB2 OBJECT-TYPE
   SYNTAX      Integer32
   UNITS       "msec"
   MAX-ACCESS  read-write
   STATUS      current
   DESCRIPTION
      "Path: ethOam.editConf.meps.qualityMonitor.delayAlarm.jitterUpStat.table.bin2

       unit name = msec"
   ::= {er1646v2PbbEthOamEMepsQmEntry 119825408}

er1646v2PbbEthOamEMepsQmDelayAlarmJupsTB3 OBJECT-TYPE
   SYNTAX      Integer32
   UNITS       "msec"
   MAX-ACCESS  read-write
   STATUS      current
   DESCRIPTION
      "Path: ethOam.editConf.meps.qualityMonitor.delayAlarm.jitterUpStat.table.bin3

       unit name = msec"
   ::= {er1646v2PbbEthOamEMepsQmEntry 119825920}

er1646v2PbbEthOamEMepsQmDelayAlarmJupsTB4 OBJECT-TYPE
   SYNTAX      Integer32
   UNITS       "msec"
   MAX-ACCESS  read-write
   STATUS      current
   DESCRIPTION
      "Path: ethOam.editConf.meps.qualityMonitor.delayAlarm.jitterUpStat.table.bin4

       unit name = msec"
   ::= {er1646v2PbbEthOamEMepsQmEntry 119826432}

er1646v2PbbEthOamEMepsQmDelayAlarmJupsTB5 OBJECT-TYPE
   SYNTAX      Integer32
   UNITS       "msec"
   MAX-ACCESS  read-write
   STATUS      current
   DESCRIPTION
      "Path: ethOam.editConf.meps.qualityMonitor.delayAlarm.jitterUpStat.table.bin5

       unit name = msec"
   ::= {er1646v2PbbEthOamEMepsQmEntry 119826944}

er1646v2PbbEthOamEMepsQmDelayAlarmJupsTB6 OBJECT-TYPE
   SYNTAX      Integer32
   UNITS       "msec"
   MAX-ACCESS  read-write
   STATUS      current
   DESCRIPTION
      "Path: ethOam.editConf.meps.qualityMonitor.delayAlarm.jitterUpStat.table.bin6

       unit name = msec"
   ::= {er1646v2PbbEthOamEMepsQmEntry 119827456}

er1646v2PbbEthOamEMepsQmDelayAlarmJupsTB7 OBJECT-TYPE
   SYNTAX      Integer32
   UNITS       "msec"
   MAX-ACCESS  read-write
   STATUS      current
   DESCRIPTION
      "Path: ethOam.editConf.meps.qualityMonitor.delayAlarm.jitterUpStat.table.bin7

       unit name = msec"
   ::= {er1646v2PbbEthOamEMepsQmEntry 119827968}

er1646v2PbbEthOamEMepsQmDelayAlarmJupsTB8 OBJECT-TYPE
   SYNTAX      Integer32
   UNITS       "msec"
   MAX-ACCESS  read-write
   STATUS      current
   DESCRIPTION
      "Path: ethOam.editConf.meps.qualityMonitor.delayAlarm.jitterUpStat.table.bin8

       unit name = msec"
   ::= {er1646v2PbbEthOamEMepsQmEntry 119828480}

er1646v2PbbEthOamEMepsQmDelayAlarmJupsTMx OBJECT-TYPE
   SYNTAX      Integer32
   UNITS       "msec"
   MAX-ACCESS  read-write
   STATUS      current
   DESCRIPTION
      "Path: ethOam.editConf.meps.qualityMonitor.delayAlarm.jitterUpStat.table.max

       unit name = msec"
   ::= {er1646v2PbbEthOamEMepsQmEntry 119828992}

er1646v2PbbEthOamEMepsQmDelayAlarmJitterDownAvrgOn OBJECT-TYPE
   SYNTAX      Integer32
   UNITS       "msec"
   MAX-ACCESS  read-write
   STATUS      current
   DESCRIPTION
      "Path: ethOam.editConf.meps.qualityMonitor.delayAlarm.jitterDownAvrgOn

       unit name = msec"
   ::= {er1646v2PbbEthOamEMepsQmEntry 118489088}

er1646v2PbbEthOamEMepsQmDelayAlarmJitterDownAvrgOff OBJECT-TYPE
   SYNTAX      Integer32
   UNITS       "msec"
   MAX-ACCESS  read-write
   STATUS      current
   DESCRIPTION
      "Path: ethOam.editConf.meps.qualityMonitor.delayAlarm.jitterDownAvrgOff

       unit name = msec"
   ::= {er1646v2PbbEthOamEMepsQmEntry 118554624}

er1646v2PbbEthOamEMepsQmDelayAlarmJitterDownMaxOn OBJECT-TYPE
   SYNTAX      Integer32
   UNITS       "msec"
   MAX-ACCESS  read-write
   STATUS      current
   DESCRIPTION
      "Path: ethOam.editConf.meps.qualityMonitor.delayAlarm.jitterDownMaxOn

       unit name = msec"
   ::= {er1646v2PbbEthOamEMepsQmEntry 118620160}

er1646v2PbbEthOamEMepsQmDelayAlarmJitterDownMaxOff OBJECT-TYPE
   SYNTAX      Integer32
   UNITS       "msec"
   MAX-ACCESS  read-write
   STATUS      current
   DESCRIPTION
      "Path: ethOam.editConf.meps.qualityMonitor.delayAlarm.jitterDownMaxOff

       unit name = msec"
   ::= {er1646v2PbbEthOamEMepsQmEntry 118685696}

er1646v2PbbEthOamEMepsQmDelayAlarmJdownsN OBJECT-TYPE
   SYNTAX      INTEGER
               {
               none (0)
               }
   MAX-ACCESS  read-write
   STATUS      current
   DESCRIPTION
      "Path: ethOam.editConf.meps.qualityMonitor.delayAlarm.jitterDownStat.none

       Possibilities:
               none   (0)"
   ::= {er1646v2PbbEthOamEMepsQmEntry 119939072}

er1646v2PbbEthOamEMepsQmDelayAlarmJdownsNMn OBJECT-TYPE
   SYNTAX      Integer32
   UNITS       "msec"
   MAX-ACCESS  read-write
   STATUS      current
   DESCRIPTION
      "Path: ethOam.editConf.meps.qualityMonitor.delayAlarm.jitterDownStat.range.min

       unit name = msec"
   ::= {er1646v2PbbEthOamEMepsQmEntry 119948288}

er1646v2PbbEthOamEMepsQmDelayAlarmJdownsNMx OBJECT-TYPE
   SYNTAX      Integer32
   UNITS       "msec"
   MAX-ACCESS  read-write
   STATUS      current
   DESCRIPTION
      "Path: ethOam.editConf.meps.qualityMonitor.delayAlarm.jitterDownStat.range.max

       unit name = msec"
   ::= {er1646v2PbbEthOamEMepsQmEntry 119949312}

er1646v2PbbEthOamEMepsQmDelayAlarmJdownsTB1 OBJECT-TYPE
   SYNTAX      Integer32
   UNITS       "msec"
   MAX-ACCESS  read-write
   STATUS      current
   DESCRIPTION
      "Path: ethOam.editConf.meps.qualityMonitor.delayAlarm.jitterDownStat.table.bin1

       unit name = msec"
   ::= {er1646v2PbbEthOamEMepsQmEntry 119955968}

er1646v2PbbEthOamEMepsQmDelayAlarmJdownsTB2 OBJECT-TYPE
   SYNTAX      Integer32
   UNITS       "msec"
   MAX-ACCESS  read-write
   STATUS      current
   DESCRIPTION
      "Path: ethOam.editConf.meps.qualityMonitor.delayAlarm.jitterDownStat.table.bin2

       unit name = msec"
   ::= {er1646v2PbbEthOamEMepsQmEntry 119956480}

er1646v2PbbEthOamEMepsQmDelayAlarmJdownsTB3 OBJECT-TYPE
   SYNTAX      Integer32
   UNITS       "msec"
   MAX-ACCESS  read-write
   STATUS      current
   DESCRIPTION
      "Path: ethOam.editConf.meps.qualityMonitor.delayAlarm.jitterDownStat.table.bin3

       unit name = msec"
   ::= {er1646v2PbbEthOamEMepsQmEntry 119956992}

er1646v2PbbEthOamEMepsQmDelayAlarmJdownsTB4 OBJECT-TYPE
   SYNTAX      Integer32
   UNITS       "msec"
   MAX-ACCESS  read-write
   STATUS      current
   DESCRIPTION
      "Path: ethOam.editConf.meps.qualityMonitor.delayAlarm.jitterDownStat.table.bin4

       unit name = msec"
   ::= {er1646v2PbbEthOamEMepsQmEntry 119957504}

er1646v2PbbEthOamEMepsQmDelayAlarmJdownsTB5 OBJECT-TYPE
   SYNTAX      Integer32
   UNITS       "msec"
   MAX-ACCESS  read-write
   STATUS      current
   DESCRIPTION
      "Path: ethOam.editConf.meps.qualityMonitor.delayAlarm.jitterDownStat.table.bin5

       unit name = msec"
   ::= {er1646v2PbbEthOamEMepsQmEntry 119958016}

er1646v2PbbEthOamEMepsQmDelayAlarmJdownsTB6 OBJECT-TYPE
   SYNTAX      Integer32
   UNITS       "msec"
   MAX-ACCESS  read-write
   STATUS      current
   DESCRIPTION
      "Path: ethOam.editConf.meps.qualityMonitor.delayAlarm.jitterDownStat.table.bin6

       unit name = msec"
   ::= {er1646v2PbbEthOamEMepsQmEntry 119958528}

er1646v2PbbEthOamEMepsQmDelayAlarmJdownsTB7 OBJECT-TYPE
   SYNTAX      Integer32
   UNITS       "msec"
   MAX-ACCESS  read-write
   STATUS      current
   DESCRIPTION
      "Path: ethOam.editConf.meps.qualityMonitor.delayAlarm.jitterDownStat.table.bin7

       unit name = msec"
   ::= {er1646v2PbbEthOamEMepsQmEntry 119959040}

er1646v2PbbEthOamEMepsQmDelayAlarmJdownsTB8 OBJECT-TYPE
   SYNTAX      Integer32
   UNITS       "msec"
   MAX-ACCESS  read-write
   STATUS      current
   DESCRIPTION
      "Path: ethOam.editConf.meps.qualityMonitor.delayAlarm.jitterDownStat.table.bin8

       unit name = msec"
   ::= {er1646v2PbbEthOamEMepsQmEntry 119959552}

er1646v2PbbEthOamEMepsQmDelayAlarmJdownsTMx OBJECT-TYPE
   SYNTAX      Integer32
   UNITS       "msec"
   MAX-ACCESS  read-write
   STATUS      current
   DESCRIPTION
      "Path: ethOam.editConf.meps.qualityMonitor.delayAlarm.jitterDownStat.table.max

       unit name = msec"
   ::= {er1646v2PbbEthOamEMepsQmEntry 119960064}

er1646v2PbbEthOamEMepsQmDelayAlarmDelayUpAvrgOn OBJECT-TYPE
   SYNTAX      Integer32
   UNITS       "msec"
   MAX-ACCESS  read-write
   STATUS      current
   DESCRIPTION
      "Path: ethOam.editConf.meps.qualityMonitor.delayAlarm.delayUpAvrgOn

       unit name = msec"
   ::= {er1646v2PbbEthOamEMepsQmEntry 118751232}

er1646v2PbbEthOamEMepsQmDelayAlarmDelayUpAvrgOff OBJECT-TYPE
   SYNTAX      Integer32
   UNITS       "msec"
   MAX-ACCESS  read-write
   STATUS      current
   DESCRIPTION
      "Path: ethOam.editConf.meps.qualityMonitor.delayAlarm.delayUpAvrgOff

       unit name = msec"
   ::= {er1646v2PbbEthOamEMepsQmEntry 118816768}

er1646v2PbbEthOamEMepsQmDelayAlarmDelayUpMaxOn OBJECT-TYPE
   SYNTAX      Integer32
   UNITS       "msec"
   MAX-ACCESS  read-write
   STATUS      current
   DESCRIPTION
      "Path: ethOam.editConf.meps.qualityMonitor.delayAlarm.delayUpMaxOn

       unit name = msec"
   ::= {er1646v2PbbEthOamEMepsQmEntry 118882304}

er1646v2PbbEthOamEMepsQmDelayAlarmDelayUpMaxOff OBJECT-TYPE
   SYNTAX      Integer32
   UNITS       "msec"
   MAX-ACCESS  read-write
   STATUS      current
   DESCRIPTION
      "Path: ethOam.editConf.meps.qualityMonitor.delayAlarm.delayUpMaxOff

       unit name = msec"
   ::= {er1646v2PbbEthOamEMepsQmEntry 118947840}

er1646v2PbbEthOamEMepsQmDelayAlarmDupsType OBJECT-TYPE
   SYNTAX      INTEGER
               {
               fd (1),
               fdr (2)
               }
   MAX-ACCESS  read-write
   STATUS      current
   DESCRIPTION
      "Path: ethOam.editConf.meps.qualityMonitor.delayAlarm.delayUpStat.type

       Possibilities:
               fd   (1)
               fdr   (2)"
   ::= {er1646v2PbbEthOamEMepsQmEntry 119414784}

er1646v2PbbEthOamEMepsQmDelayAlarmDupsBinsN OBJECT-TYPE
   SYNTAX      INTEGER
               {
               none (0)
               }
   MAX-ACCESS  read-write
   STATUS      current
   DESCRIPTION
      "Path: ethOam.editConf.meps.qualityMonitor.delayAlarm.delayUpStat.bins.none

       Possibilities:
               none   (0)"
   ::= {er1646v2PbbEthOamEMepsQmEntry 119424000}

er1646v2PbbEthOamEMepsQmDelayAlarmDupsBinsNMn OBJECT-TYPE
   SYNTAX      Integer32
   UNITS       "msec"
   MAX-ACCESS  read-write
   STATUS      current
   DESCRIPTION
      "Path: ethOam.editConf.meps.qualityMonitor.delayAlarm.delayUpStat.bins.range.min

       unit name = msec"
   ::= {er1646v2PbbEthOamEMepsQmEntry 119425152}

er1646v2PbbEthOamEMepsQmDelayAlarmDupsBinsNMx OBJECT-TYPE
   SYNTAX      Integer32
   UNITS       "msec"
   MAX-ACCESS  read-write
   STATUS      current
   DESCRIPTION
      "Path: ethOam.editConf.meps.qualityMonitor.delayAlarm.delayUpStat.bins.range.max

       unit name = msec"
   ::= {er1646v2PbbEthOamEMepsQmEntry 119425280}

er1646v2PbbEthOamEMepsQmDelayAlarmDupsBinsTB1 OBJECT-TYPE
   SYNTAX      Integer32
   UNITS       "msec"
   MAX-ACCESS  read-write
   STATUS      current
   DESCRIPTION
      "Path: ethOam.editConf.meps.qualityMonitor.delayAlarm.delayUpStat.bins.table.bin1

       unit name = msec"
   ::= {er1646v2PbbEthOamEMepsQmEntry 119426112}

er1646v2PbbEthOamEMepsQmDelayAlarmDupsBinsTB2 OBJECT-TYPE
   SYNTAX      Integer32
   UNITS       "msec"
   MAX-ACCESS  read-write
   STATUS      current
   DESCRIPTION
      "Path: ethOam.editConf.meps.qualityMonitor.delayAlarm.delayUpStat.bins.table.bin2

       unit name = msec"
   ::= {er1646v2PbbEthOamEMepsQmEntry 119426176}

er1646v2PbbEthOamEMepsQmDelayAlarmDupsBinsTB3 OBJECT-TYPE
   SYNTAX      Integer32
   UNITS       "msec"
   MAX-ACCESS  read-write
   STATUS      current
   DESCRIPTION
      "Path: ethOam.editConf.meps.qualityMonitor.delayAlarm.delayUpStat.bins.table.bin3

       unit name = msec"
   ::= {er1646v2PbbEthOamEMepsQmEntry 119426240}

er1646v2PbbEthOamEMepsQmDelayAlarmDupsBinsTB4 OBJECT-TYPE
   SYNTAX      Integer32
   UNITS       "msec"
   MAX-ACCESS  read-write
   STATUS      current
   DESCRIPTION
      "Path: ethOam.editConf.meps.qualityMonitor.delayAlarm.delayUpStat.bins.table.bin4

       unit name = msec"
   ::= {er1646v2PbbEthOamEMepsQmEntry 119426304}

er1646v2PbbEthOamEMepsQmDelayAlarmDupsBinsTB5 OBJECT-TYPE
   SYNTAX      Integer32
   UNITS       "msec"
   MAX-ACCESS  read-write
   STATUS      current
   DESCRIPTION
      "Path: ethOam.editConf.meps.qualityMonitor.delayAlarm.delayUpStat.bins.table.bin5

       unit name = msec"
   ::= {er1646v2PbbEthOamEMepsQmEntry 119426368}

er1646v2PbbEthOamEMepsQmDelayAlarmDupsBinsTB6 OBJECT-TYPE
   SYNTAX      Integer32
   UNITS       "msec"
   MAX-ACCESS  read-write
   STATUS      current
   DESCRIPTION
      "Path: ethOam.editConf.meps.qualityMonitor.delayAlarm.delayUpStat.bins.table.bin6

       unit name = msec"
   ::= {er1646v2PbbEthOamEMepsQmEntry 119426432}

er1646v2PbbEthOamEMepsQmDelayAlarmDupsBinsTB7 OBJECT-TYPE
   SYNTAX      Integer32
   UNITS       "msec"
   MAX-ACCESS  read-write
   STATUS      current
   DESCRIPTION
      "Path: ethOam.editConf.meps.qualityMonitor.delayAlarm.delayUpStat.bins.table.bin7

       unit name = msec"
   ::= {er1646v2PbbEthOamEMepsQmEntry 119426496}

er1646v2PbbEthOamEMepsQmDelayAlarmDupsBinsTB8 OBJECT-TYPE
   SYNTAX      Integer32
   UNITS       "msec"
   MAX-ACCESS  read-write
   STATUS      current
   DESCRIPTION
      "Path: ethOam.editConf.meps.qualityMonitor.delayAlarm.delayUpStat.bins.table.bin8

       unit name = msec"
   ::= {er1646v2PbbEthOamEMepsQmEntry 119426560}

er1646v2PbbEthOamEMepsQmDelayAlarmDupsBinsTMx OBJECT-TYPE
   SYNTAX      Integer32
   UNITS       "msec"
   MAX-ACCESS  read-write
   STATUS      current
   DESCRIPTION
      "Path: ethOam.editConf.meps.qualityMonitor.delayAlarm.delayUpStat.bins.table.max

       unit name = msec"
   ::= {er1646v2PbbEthOamEMepsQmEntry 119426624}

er1646v2PbbEthOamEMepsQmDelayAlarmDelayDownAvrgOn OBJECT-TYPE
   SYNTAX      Integer32
   UNITS       "msec"
   MAX-ACCESS  read-write
   STATUS      current
   DESCRIPTION
      "Path: ethOam.editConf.meps.qualityMonitor.delayAlarm.delayDownAvrgOn

       unit name = msec"
   ::= {er1646v2PbbEthOamEMepsQmEntry 119013376}

er1646v2PbbEthOamEMepsQmDelayAlarmDelayDownAvrgOff OBJECT-TYPE
   SYNTAX      Integer32
   UNITS       "msec"
   MAX-ACCESS  read-write
   STATUS      current
   DESCRIPTION
      "Path: ethOam.editConf.meps.qualityMonitor.delayAlarm.delayDownAvrgOff

       unit name = msec"
   ::= {er1646v2PbbEthOamEMepsQmEntry 119078912}

er1646v2PbbEthOamEMepsQmDelayAlarmDelayDownMaxOn OBJECT-TYPE
   SYNTAX      Integer32
   UNITS       "msec"
   MAX-ACCESS  read-write
   STATUS      current
   DESCRIPTION
      "Path: ethOam.editConf.meps.qualityMonitor.delayAlarm.delayDownMaxOn

       unit name = msec"
   ::= {er1646v2PbbEthOamEMepsQmEntry 119144448}

er1646v2PbbEthOamEMepsQmDelayAlarmDelayDownMaxOff OBJECT-TYPE
   SYNTAX      Integer32
   UNITS       "msec"
   MAX-ACCESS  read-write
   STATUS      current
   DESCRIPTION
      "Path: ethOam.editConf.meps.qualityMonitor.delayAlarm.delayDownMaxOff

       unit name = msec"
   ::= {er1646v2PbbEthOamEMepsQmEntry 119209984}

er1646v2PbbEthOamEMepsQmDelayAlarmDdownsType OBJECT-TYPE
   SYNTAX      INTEGER
               {
               fd (1),
               fdr (2)
               }
   MAX-ACCESS  read-write
   STATUS      current
   DESCRIPTION
      "Path: ethOam.editConf.meps.qualityMonitor.delayAlarm.delayDownStat.type

       Possibilities:
               fd   (1)
               fdr   (2)"
   ::= {er1646v2PbbEthOamEMepsQmEntry 119545856}

er1646v2PbbEthOamEMepsQmDelayAlarmDdownsBinsN OBJECT-TYPE
   SYNTAX      INTEGER
               {
               none (0)
               }
   MAX-ACCESS  read-write
   STATUS      current
   DESCRIPTION
      "Path: ethOam.editConf.meps.qualityMonitor.delayAlarm.delayDownStat.bins.none

       Possibilities:
               none   (0)"
   ::= {er1646v2PbbEthOamEMepsQmEntry 119555072}

er1646v2PbbEthOamEMepsQmDelayAlarmDdownsBinsNMn OBJECT-TYPE
   SYNTAX      Integer32
   UNITS       "msec"
   MAX-ACCESS  read-write
   STATUS      current
   DESCRIPTION
      "Path: ethOam.editConf.meps.qualityMonitor.delayAlarm.delayDownStat.bins.range.min

       unit name = msec"
   ::= {er1646v2PbbEthOamEMepsQmEntry 119556224}

er1646v2PbbEthOamEMepsQmDelayAlarmDdownsBinsNMx OBJECT-TYPE
   SYNTAX      Integer32
   UNITS       "msec"
   MAX-ACCESS  read-write
   STATUS      current
   DESCRIPTION
      "Path: ethOam.editConf.meps.qualityMonitor.delayAlarm.delayDownStat.bins.range.max

       unit name = msec"
   ::= {er1646v2PbbEthOamEMepsQmEntry 119556352}

er1646v2PbbEthOamEMepsQmDelayAlarmDdownsBinsTB1 OBJECT-TYPE
   SYNTAX      Integer32
   UNITS       "msec"
   MAX-ACCESS  read-write
   STATUS      current
   DESCRIPTION
      "Path: ethOam.editConf.meps.qualityMonitor.delayAlarm.delayDownStat.bins.table.bin1

       unit name = msec"
   ::= {er1646v2PbbEthOamEMepsQmEntry 119557184}

er1646v2PbbEthOamEMepsQmDelayAlarmDdownsBinsTB2 OBJECT-TYPE
   SYNTAX      Integer32
   UNITS       "msec"
   MAX-ACCESS  read-write
   STATUS      current
   DESCRIPTION
      "Path: ethOam.editConf.meps.qualityMonitor.delayAlarm.delayDownStat.bins.table.bin2

       unit name = msec"
   ::= {er1646v2PbbEthOamEMepsQmEntry 119557248}

er1646v2PbbEthOamEMepsQmDelayAlarmDdownsBinsTB3 OBJECT-TYPE
   SYNTAX      Integer32
   UNITS       "msec"
   MAX-ACCESS  read-write
   STATUS      current
   DESCRIPTION
      "Path: ethOam.editConf.meps.qualityMonitor.delayAlarm.delayDownStat.bins.table.bin3

       unit name = msec"
   ::= {er1646v2PbbEthOamEMepsQmEntry 119557312}

er1646v2PbbEthOamEMepsQmDelayAlarmDdownsBinsTB4 OBJECT-TYPE
   SYNTAX      Integer32
   UNITS       "msec"
   MAX-ACCESS  read-write
   STATUS      current
   DESCRIPTION
      "Path: ethOam.editConf.meps.qualityMonitor.delayAlarm.delayDownStat.bins.table.bin4

       unit name = msec"
   ::= {er1646v2PbbEthOamEMepsQmEntry 119557376}

er1646v2PbbEthOamEMepsQmDelayAlarmDdownsBinsTB5 OBJECT-TYPE
   SYNTAX      Integer32
   UNITS       "msec"
   MAX-ACCESS  read-write
   STATUS      current
   DESCRIPTION
      "Path: ethOam.editConf.meps.qualityMonitor.delayAlarm.delayDownStat.bins.table.bin5

       unit name = msec"
   ::= {er1646v2PbbEthOamEMepsQmEntry 119557440}

er1646v2PbbEthOamEMepsQmDelayAlarmDdownsBinsTB6 OBJECT-TYPE
   SYNTAX      Integer32
   UNITS       "msec"
   MAX-ACCESS  read-write
   STATUS      current
   DESCRIPTION
      "Path: ethOam.editConf.meps.qualityMonitor.delayAlarm.delayDownStat.bins.table.bin6

       unit name = msec"
   ::= {er1646v2PbbEthOamEMepsQmEntry 119557504}

er1646v2PbbEthOamEMepsQmDelayAlarmDdownsBinsTB7 OBJECT-TYPE
   SYNTAX      Integer32
   UNITS       "msec"
   MAX-ACCESS  read-write
   STATUS      current
   DESCRIPTION
      "Path: ethOam.editConf.meps.qualityMonitor.delayAlarm.delayDownStat.bins.table.bin7

       unit name = msec"
   ::= {er1646v2PbbEthOamEMepsQmEntry 119557568}

er1646v2PbbEthOamEMepsQmDelayAlarmDdownsBinsTB8 OBJECT-TYPE
   SYNTAX      Integer32
   UNITS       "msec"
   MAX-ACCESS  read-write
   STATUS      current
   DESCRIPTION
      "Path: ethOam.editConf.meps.qualityMonitor.delayAlarm.delayDownStat.bins.table.bin8

       unit name = msec"
   ::= {er1646v2PbbEthOamEMepsQmEntry 119557632}

er1646v2PbbEthOamEMepsQmDelayAlarmDdownsBinsTMx OBJECT-TYPE
   SYNTAX      Integer32
   UNITS       "msec"
   MAX-ACCESS  read-write
   STATUS      current
   DESCRIPTION
      "Path: ethOam.editConf.meps.qualityMonitor.delayAlarm.delayDownStat.bins.table.max

       unit name = msec"
   ::= {er1646v2PbbEthOamEMepsQmEntry 119557696}

er1646v2PbbEthOamEMepsQmAlarmMask OBJECT-TYPE
   SYNTAX      Integer32
   MAX-ACCESS  read-write
   STATUS      current
   DESCRIPTION
      "Path: ethOam.editConf.meps.qualityMonitor.alarmMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1646v2PbbEthOamEMepsQmEntry 251658240}

er1646v2PbbEthOamEMepsQmEventMask OBJECT-TYPE
   SYNTAX      Integer32
   MAX-ACCESS  read-write
   STATUS      current
   DESCRIPTION
      "Path: ethOam.editConf.meps.qualityMonitor.eventMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1646v2PbbEthOamEMepsQmEntry 268435456}

er1646v2PbbEthOamEMepsQmLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: ethOam.editConf.meps.qualityMonitor.logging

       Possibilities:
               disabled   (0)
               3min   (3)
               5min   (5)
               10min   (10)
               15min   (15)
               30min   (30)
               60min   (60)"
   ::= {er1646v2PbbEthOamEMepsQmEntry 201326592}

er1646v2PbbEthOamEMepsQmLoggingDepth OBJECT-TYPE
   SYNTAX      INTEGER
               {
               s2 (2),
               s4 (4),
               s8 (8),
               s16 (16),
               s32 (32),
               s128 (128),
               s512 (512),
               s1024 (1024)
               }
   MAX-ACCESS  read-write
   STATUS      current
   DESCRIPTION
      "Path: ethOam.editConf.meps.qualityMonitor.loggingDepth

       Possibilities:
               2   (2)
               4   (4)
               8   (8)
               16   (16)
               32   (32)
               128   (128)
               512   (512)
               1024   (1024)"
   ::= {er1646v2PbbEthOamEMepsQmEntry 503316480}

er1646v2PbbEthOamEMepsSynthLoss OBJECT-TYPE
   SYNTAX      SEQUENCE OF Er1646v2PbbEthOamEMepsSynthLossEntry
   MAX-ACCESS  not-accessible
   STATUS      current
   DESCRIPTION
      ""
   ::= {er1646v2PbbEthOamEMeps 385875968}

er1646v2PbbEthOamEMepsSynthLossEntry OBJECT-TYPE
   SYNTAX      Er1646v2PbbEthOamEMepsSynthLossEntry
   MAX-ACCESS  not-accessible
   STATUS      current
   DESCRIPTION
      ""
   INDEX      { er1646v2PbbEthOamEMepsSynthLossGlobalIx,
                er1646v2PbbEthOamEMepsTableIx,
                er1646v2PbbEthOamEMepsSynthLossTableIx }
   ::= {er1646v2PbbEthOamEMepsSynthLoss 1}

Er1646v2PbbEthOamEMepsSynthLossEntry ::=
   SEQUENCE
      {
      er1646v2PbbEthOamEMepsSynthLossActions
         VariableLengthTableActions,
      er1646v2PbbEthOamEMepsSynthLossGlobalIx
         GlobalIndex,
      er1646v2PbbEthOamEMepsSynthLossTableIx
         TableIndex,
      er1646v2PbbEthOamEMepsSynthLossName
         DisplayString,
      er1646v2PbbEthOamEMepsSynthLossDestinationMepId
         Integer32,
      er1646v2PbbEthOamEMepsSynthLossDestinationMacAddress
         OCTET STRING,
      er1646v2PbbEthOamEMepsSynthLossPriority
         Integer32,
      er1646v2PbbEthOamEMepsSynthLossState
         INTEGER,
      er1646v2PbbEthOamEMepsSynthLossType
         INTEGER,
      er1646v2PbbEthOamEMepsSynthLossNbrOfFrames
         Integer32,
      er1646v2PbbEthOamEMepsSynthLossPeriod
         INTEGER,
      er1646v2PbbEthOamEMepsSynthLossDataTlvSize
         Integer32,
      er1646v2PbbEthOamEMepsSynthLossTestInterval
         Integer32
      }

er1646v2PbbEthOamEMepsSynthLossActions OBJECT-TYPE
   SYNTAX      VariableLengthTableActions
   MAX-ACCESS  read-write
   STATUS      current
   DESCRIPTION
      "By way of this field, some manipulations
       on this table may be performed."
   ::= {er1646v2PbbEthOamEMepsSynthLossEntry 2}

er1646v2PbbEthOamEMepsSynthLossGlobalIx OBJECT-TYPE
   SYNTAX      GlobalIndex
   MAX-ACCESS  not-accessible
   STATUS      current
   DESCRIPTION
      "The value of the tlsCntTreeGlobalIndex of the MANAGED OBJECT."
   ::= {er1646v2PbbEthOamEMepsSynthLossEntry 10}

er1646v2PbbEthOamEMepsSynthLossTableIx OBJECT-TYPE
   SYNTAX      TableIndex
   MAX-ACCESS  not-accessible
   STATUS      current
   DESCRIPTION
      ""
   ::= {er1646v2PbbEthOamEMepsSynthLossEntry 11}

er1646v2PbbEthOamEMepsSynthLossName OBJECT-TYPE
   SYNTAX      DisplayString
   MAX-ACCESS  read-write
   STATUS      current
   DESCRIPTION
      "Path: ethOam.editConf.meps.synthLoss.name"
   ::= {er1646v2PbbEthOamEMepsSynthLossEntry 16777216}

er1646v2PbbEthOamEMepsSynthLossDestinationMepId OBJECT-TYPE
   SYNTAX      Integer32
   MAX-ACCESS  read-write
   STATUS      current
   DESCRIPTION
      "Path: ethOam.editConf.meps.synthLoss.destination.mepId"
   ::= {er1646v2PbbEthOamEMepsSynthLossEntry 33619968}

er1646v2PbbEthOamEMepsSynthLossDestinationMacAddress OBJECT-TYPE
   SYNTAX      OCTET STRING
   MAX-ACCESS  read-write
   STATUS      current
   DESCRIPTION
      "Path: ethOam.editConf.meps.synthLoss.destination.macAddress

       MAC address."
   ::= {er1646v2PbbEthOamEMepsSynthLossEntry 33685504}

er1646v2PbbEthOamEMepsSynthLossPriority OBJECT-TYPE
   SYNTAX      Integer32
   MAX-ACCESS  read-write
   STATUS      current
   DESCRIPTION
      "Path: ethOam.editConf.meps.synthLoss.priority"
   ::= {er1646v2PbbEthOamEMepsSynthLossEntry 50331648}

er1646v2PbbEthOamEMepsSynthLossState OBJECT-TYPE
   SYNTAX      INTEGER
               {
               singleEnded (0),
               dualEnded (1),
               dualEndedMC (2)
               }
   MAX-ACCESS  read-write
   STATUS      current
   DESCRIPTION
      "Path: ethOam.editConf.meps.synthLoss.state

       Possibilities:
               singleEnded   (0)
               dualEnded   (1)
               dualEndedMC   (2)"
   ::= {er1646v2PbbEthOamEMepsSynthLossEntry 83886080}

er1646v2PbbEthOamEMepsSynthLossType OBJECT-TYPE
   SYNTAX      INTEGER
               {
               onDemand (0),
               running (1)
               }
   MAX-ACCESS  read-write
   STATUS      current
   DESCRIPTION
      "Path: ethOam.editConf.meps.synthLoss.type

       Possibilities:
               onDemand   (0)
               running   (1)"
   ::= {er1646v2PbbEthOamEMepsSynthLossEntry 167772160}

er1646v2PbbEthOamEMepsSynthLossNbrOfFrames OBJECT-TYPE
   SYNTAX      Integer32
   MAX-ACCESS  read-write
   STATUS      current
   DESCRIPTION
      "Path: ethOam.editConf.meps.synthLoss.nbrOfFrames"
   ::= {er1646v2PbbEthOamEMepsSynthLossEntry 184549376}

er1646v2PbbEthOamEMepsSynthLossPeriod OBJECT-TYPE
   SYNTAX      INTEGER
               {
               s10ms (2),
               s100ms (3),
               s1s (4),
               s10s (5),
               s1min (6),
               s10min (7)
               }
   MAX-ACCESS  read-write
   STATUS      current
   DESCRIPTION
      "Path: ethOam.editConf.meps.synthLoss.period

       Possibilities:
               10ms   (2)
               100ms   (3)
               1s   (4)
               10s   (5)
               1min   (6)
               10min   (7)"
   ::= {er1646v2PbbEthOamEMepsSynthLossEntry 201326592}

er1646v2PbbEthOamEMepsSynthLossDataTlvSize OBJECT-TYPE
   SYNTAX      Integer32
   MAX-ACCESS  read-write
   STATUS      current
   DESCRIPTION
      "Path: ethOam.editConf.meps.synthLoss.dataTlvSize"
   ::= {er1646v2PbbEthOamEMepsSynthLossEntry 218103808}

er1646v2PbbEthOamEMepsSynthLossTestInterval OBJECT-TYPE
   SYNTAX      Integer32
   UNITS       "sec"
   MAX-ACCESS  read-write
   STATUS      current
   DESCRIPTION
      "Path: ethOam.editConf.meps.synthLoss.testInterval

       unit name = sec"
   ::= {er1646v2PbbEthOamEMepsSynthLossEntry 234881024}



sr1646v2PbbEthOamE OBJECT IDENTIFIER ::= {r1646v2PbbEthOamE 14}


sr1646v2PbbEthOamEMeps OBJECT IDENTIFIER ::= {sr1646v2PbbEthOamE 15}

sr1646v2PbbEthOamEMepsSSCTable OBJECT-TYPE
   SYNTAX      SEQUENCE OF Sr1646v2PbbEthOamEMepsEntry
   MAX-ACCESS  not-accessible
   STATUS      current
   DESCRIPTION
      "ETH OAM Mep status"
   ::= {sr1646v2PbbEthOamEMeps 1}

sr1646v2PbbEthOamEMepsEntry OBJECT-TYPE
   SYNTAX      Sr1646v2PbbEthOamEMepsEntry
   MAX-ACCESS  not-accessible
   STATUS      current
   DESCRIPTION
      ""
   INDEX      { sr1646v2PbbEthOamEMepsGlobalIx,
                sr1646v2PbbEthOamEMepsTableIx }
   ::= {sr1646v2PbbEthOamEMepsSSCTable 1}

Sr1646v2PbbEthOamEMepsEntry ::=
   SEQUENCE
      {
      sr1646v2PbbEthOamEMepsGlobalIx
         GlobalIndex,
      sr1646v2PbbEthOamEMepsTableIx
         TableIndex,
      sr1646v2PbbEthOamEMepsMepName
         DisplayString,
      sr1646v2PbbEthOamEMepsMacAddress
         OCTET STRING,
      sr1646v2PbbEthOamEMepsMegLevel
         Integer32,
      sr1646v2PbbEthOamEMepsMegIdMaintDomainName
         DisplayString,
      sr1646v2PbbEthOamEMepsMegIdShortMaName
         DisplayString,
      sr1646v2PbbEthOamEMepsMepId
         Integer32,
      sr1646v2PbbEthOamEMepsCc
         INTEGER,
      sr1646v2PbbEthOamEMepsEfd
         INTEGER,
      sr1646v2PbbEthOamEMepsTxAis
         INTEGER,
      sr1646v2PbbEthOamEMepsTxRdi
         INTEGER,
      sr1646v2PbbEthOamEMepsAlarm
         Integer32
      }

sr1646v2PbbEthOamEMepsGlobalIx OBJECT-TYPE
   SYNTAX      GlobalIndex
   MAX-ACCESS  not-accessible
   STATUS      current
   DESCRIPTION
      "The value of the tlsCntTreeGlobalIndex of the MANAGED OBJECT."
   ::= {sr1646v2PbbEthOamEMepsEntry 10}

sr1646v2PbbEthOamEMepsTableIx OBJECT-TYPE
   SYNTAX      TableIndex
   MAX-ACCESS  not-accessible
   STATUS      current
   DESCRIPTION
      ""
   ::= {sr1646v2PbbEthOamEMepsEntry 11}

sr1646v2PbbEthOamEMepsMepName OBJECT-TYPE
   SYNTAX      DisplayString
   MAX-ACCESS  read-only
   STATUS      current
   DESCRIPTION
      "Path: ethOam.status.meps.mepName"
   ::= {sr1646v2PbbEthOamEMepsEntry 16777216}

sr1646v2PbbEthOamEMepsMacAddress OBJECT-TYPE
   SYNTAX      OCTET STRING
   MAX-ACCESS  read-only
   STATUS      current
   DESCRIPTION
      "Path: ethOam.status.meps.macAddress

       MAC address."
   ::= {sr1646v2PbbEthOamEMepsEntry 33554432}

sr1646v2PbbEthOamEMepsMegLevel OBJECT-TYPE
   SYNTAX      Integer32
   MAX-ACCESS  read-only
   STATUS      current
   DESCRIPTION
      "Path: ethOam.status.meps.megLevel"
   ::= {sr1646v2PbbEthOamEMepsEntry 50331648}

sr1646v2PbbEthOamEMepsMegIdMaintDomainName OBJECT-TYPE
   SYNTAX      DisplayString
   MAX-ACCESS  read-only
   STATUS      current
   DESCRIPTION
      "Path: ethOam.status.meps.megId.maintDomainName"
   ::= {sr1646v2PbbEthOamEMepsEntry 67174400}

sr1646v2PbbEthOamEMepsMegIdShortMaName OBJECT-TYPE
   SYNTAX      DisplayString
   MAX-ACCESS  read-only
   STATUS      current
   DESCRIPTION
      "Path: ethOam.status.meps.megId.shortMaName"
   ::= {sr1646v2PbbEthOamEMepsEntry 67239936}

sr1646v2PbbEthOamEMepsMepId OBJECT-TYPE
   SYNTAX      Integer32
   MAX-ACCESS  read-only
   STATUS      current
   DESCRIPTION
      "Path: ethOam.status.meps.mepId"
   ::= {sr1646v2PbbEthOamEMepsEntry 83886080}

sr1646v2PbbEthOamEMepsCc OBJECT-TYPE
   SYNTAX      INTEGER
               {
               inactive (0),
               active (1),
               disabled (2)
               }
   MAX-ACCESS  read-only
   STATUS      current
   DESCRIPTION
      "Path: ethOam.status.meps.cc

       Possibilities:
               inactive   (0)
               active   (1)
               disabled   (2)"
   ::= {sr1646v2PbbEthOamEMepsEntry 117440512}

sr1646v2PbbEthOamEMepsEfd OBJECT-TYPE
   SYNTAX      INTEGER
               {
               disabled (0),
               idle (1),
               triggered (2),
               triggeredLfp (3)
               }
   MAX-ACCESS  read-only
   STATUS      current
   DESCRIPTION
      "Path: ethOam.status.meps.efd

       Possibilities:
               disabled   (0)
               idle   (1)
               triggered   (2)
               triggeredLfp   (3)"
   ::= {sr1646v2PbbEthOamEMepsEntry 134217728}

sr1646v2PbbEthOamEMepsTxAis OBJECT-TYPE
   SYNTAX      INTEGER
               {
               inactive (0),
               active (1),
               disabled (2)
               }
   MAX-ACCESS  read-only
   STATUS      current
   DESCRIPTION
      "Path: ethOam.status.meps.txAis

       Possibilities:
               inactive   (0)
               active   (1)
               disabled   (2)"
   ::= {sr1646v2PbbEthOamEMepsEntry 167772160}

sr1646v2PbbEthOamEMepsTxRdi OBJECT-TYPE
   SYNTAX      INTEGER
               {
               no (0),
               yes (1)
               }
   MAX-ACCESS  read-only
   STATUS      current
   DESCRIPTION
      "Path: ethOam.status.meps.txRdi

       Possibilities:
               no   (0)
               yes   (1)"
   ::= {sr1646v2PbbEthOamEMepsEntry 184549376}

sr1646v2PbbEthOamEMepsAlarm OBJECT-TYPE
   SYNTAX      Integer32
   MAX-ACCESS  read-only
   STATUS      current
   DESCRIPTION
      "Path: ethOam.status.meps.alarm

       Bit meanings:
               bit 4 = mismerge,
               bit 5 = unexpectedMep,
               bit 6 = unexpectedMegLevel,
               bit 7 = unexpectedPeriod,
               bit 8 = rdi,
               bit 9 = ais,
               bit 10 = macStatus"
   ::= {sr1646v2PbbEthOamEMepsEntry 100663296}


sr1646v2PbbEthOamEDiscoveredMeps OBJECT IDENTIFIER ::= {sr1646v2PbbEthOamE 16}

sr1646v2PbbEthOamEDiscoveredMepsSSCTable OBJECT-TYPE
   SYNTAX      SEQUENCE OF Sr1646v2PbbEthOamEDiscoveredMepsEntry
   MAX-ACCESS  not-accessible
   STATUS      current
   DESCRIPTION
      "list of discovered MEPs"
   ::= {sr1646v2PbbEthOamEDiscoveredMeps 1}

sr1646v2PbbEthOamEDiscoveredMepsEntry OBJECT-TYPE
   SYNTAX      Sr1646v2PbbEthOamEDiscoveredMepsEntry
   MAX-ACCESS  not-accessible
   STATUS      current
   DESCRIPTION
      ""
   INDEX      { sr1646v2PbbEthOamEDiscoveredMepsGlobalIx,
                sr1646v2PbbEthOamEDiscoveredMepsTableIx }
   ::= {sr1646v2PbbEthOamEDiscoveredMepsSSCTable 1}

Sr1646v2PbbEthOamEDiscoveredMepsEntry ::=
   SEQUENCE
      {
      sr1646v2PbbEthOamEDiscoveredMepsGlobalIx
         GlobalIndex,
      sr1646v2PbbEthOamEDiscoveredMepsTableIx
         TableIndex,
      sr1646v2PbbEthOamEDiscoveredMepsInterface
         DisplayString,
      sr1646v2PbbEthOamEDiscoveredMepsVid
         INTEGER,
      sr1646v2PbbEthOamEDiscoveredMepsTpid
         INTEGER,
      sr1646v2PbbEthOamEDiscoveredMepsPriority
         Integer32,
      sr1646v2PbbEthOamEDiscoveredMepsPeriod
         INTEGER,
      sr1646v2PbbEthOamEDiscoveredMepsMegLevel
         Integer32,
      sr1646v2PbbEthOamEDiscoveredMepsMegIdMaintDomainName
         DisplayString,
      sr1646v2PbbEthOamEDiscoveredMepsMegIdShortMaName
         DisplayString,
      sr1646v2PbbEthOamEDiscoveredMepsMepId
         Integer32,
      sr1646v2PbbEthOamEDiscoveredMepsMacAddress
         OCTET STRING
      }

sr1646v2PbbEthOamEDiscoveredMepsGlobalIx OBJECT-TYPE
   SYNTAX      GlobalIndex
   MAX-ACCESS  not-accessible
   STATUS      current
   DESCRIPTION
      "The value of the tlsCntTreeGlobalIndex of the MANAGED OBJECT."
   ::= {sr1646v2PbbEthOamEDiscoveredMepsEntry 10}

sr1646v2PbbEthOamEDiscoveredMepsTableIx OBJECT-TYPE
   SYNTAX      TableIndex
   MAX-ACCESS  not-accessible
   STATUS      current
   DESCRIPTION
      ""
   ::= {sr1646v2PbbEthOamEDiscoveredMepsEntry 11}

sr1646v2PbbEthOamEDiscoveredMepsInterface OBJECT-TYPE
   SYNTAX      DisplayString
   MAX-ACCESS  read-only
   STATUS      current
   DESCRIPTION
      "Path: ethOam.status.discoveredMeps.interface"
   ::= {sr1646v2PbbEthOamEDiscoveredMepsEntry 16777216}

sr1646v2PbbEthOamEDiscoveredMepsVid OBJECT-TYPE
   SYNTAX      INTEGER
               {
               untagged (0)
               }
   MAX-ACCESS  read-only
   STATUS      current
   DESCRIPTION
      "Path: ethOam.status.discoveredMeps.vid

       Possibilities:
               untagged   (0)"
   ::= {sr1646v2PbbEthOamEDiscoveredMepsEntry 33554432}

sr1646v2PbbEthOamEDiscoveredMepsTpid OBJECT-TYPE
   SYNTAX      INTEGER
               {
               slOPTg (0),
               dot1Q (33024),
               dot1ad (34984),
               s0x9100 (37120),
               s0x9200 (37376),
               s0x9300 (37632)
               }
   MAX-ACCESS  read-only
   STATUS      current
   DESCRIPTION
      "Path: ethOam.status.discoveredMeps.tpid

       Possibilities:
               <OPT>   (0)
               dot1Q   (33024)
               dot1ad   (34984)
               0x9100   (37120)
               0x9200   (37376)
               0x9300   (37632)"
   ::= {sr1646v2PbbEthOamEDiscoveredMepsEntry 150994944}

sr1646v2PbbEthOamEDiscoveredMepsPriority OBJECT-TYPE
   SYNTAX      Integer32
   MAX-ACCESS  read-only
   STATUS      current
   DESCRIPTION
      "Path: ethOam.status.discoveredMeps.priority"
   ::= {sr1646v2PbbEthOamEDiscoveredMepsEntry 50331648}

sr1646v2PbbEthOamEDiscoveredMepsPeriod OBJECT-TYPE
   SYNTAX      INTEGER
               {
               unknown (0),
               s3d33ms (1),
               s10ms (2),
               s100ms (3),
               s1s (4),
               s10s (5),
               s1min (6),
               s10min (7)
               }
   MAX-ACCESS  read-only
   STATUS      current
   DESCRIPTION
      "Path: ethOam.status.discoveredMeps.period

       Possibilities:
               unknown   (0)
               3.33ms   (1)
               10ms   (2)
               100ms   (3)
               1s   (4)
               10s   (5)
               1min   (6)
               10min   (7)"
   ::= {sr1646v2PbbEthOamEDiscoveredMepsEntry 67108864}

sr1646v2PbbEthOamEDiscoveredMepsMegLevel OBJECT-TYPE
   SYNTAX      Integer32
   MAX-ACCESS  read-only
   STATUS      current
   DESCRIPTION
      "Path: ethOam.status.discoveredMeps.megLevel"
   ::= {sr1646v2PbbEthOamEDiscoveredMepsEntry 83886080}

sr1646v2PbbEthOamEDiscoveredMepsMegIdMaintDomainName OBJECT-TYPE
   SYNTAX      DisplayString
   MAX-ACCESS  read-only
   STATUS      current
   DESCRIPTION
      "Path: ethOam.status.discoveredMeps.megId.maintDomainName"
   ::= {sr1646v2PbbEthOamEDiscoveredMepsEntry 100728832}

sr1646v2PbbEthOamEDiscoveredMepsMegIdShortMaName OBJECT-TYPE
   SYNTAX      DisplayString
   MAX-ACCESS  read-only
   STATUS      current
   DESCRIPTION
      "Path: ethOam.status.discoveredMeps.megId.shortMaName"
   ::= {sr1646v2PbbEthOamEDiscoveredMepsEntry 100794368}

sr1646v2PbbEthOamEDiscoveredMepsMepId OBJECT-TYPE
   SYNTAX      Integer32
   MAX-ACCESS  read-only
   STATUS      current
   DESCRIPTION
      "Path: ethOam.status.discoveredMeps.mepId"
   ::= {sr1646v2PbbEthOamEDiscoveredMepsEntry 117440512}

sr1646v2PbbEthOamEDiscoveredMepsMacAddress OBJECT-TYPE
   SYNTAX      OCTET STRING
   MAX-ACCESS  read-only
   STATUS      current
   DESCRIPTION
      "Path: ethOam.status.discoveredMeps.macAddress

       MAC address."
   ::= {sr1646v2PbbEthOamEDiscoveredMepsEntry 134217728}


sr1646v2PbbEthOamEManagedMeps OBJECT IDENTIFIER ::= {sr1646v2PbbEthOamE 17}

sr1646v2PbbEthOamEManagedMepsSSCTable OBJECT-TYPE
   SYNTAX      SEQUENCE OF Sr1646v2PbbEthOamEManagedMepsEntry
   MAX-ACCESS  not-accessible
   STATUS      current
   DESCRIPTION
      "list of managed MEPs"
   ::= {sr1646v2PbbEthOamEManagedMeps 1}

sr1646v2PbbEthOamEManagedMepsEntry OBJECT-TYPE
   SYNTAX      Sr1646v2PbbEthOamEManagedMepsEntry
   MAX-ACCESS  not-accessible
   STATUS      current
   DESCRIPTION
      ""
   INDEX      { sr1646v2PbbEthOamEManagedMepsGlobalIx,
                sr1646v2PbbEthOamEManagedMepsTableIx }
   ::= {sr1646v2PbbEthOamEManagedMepsSSCTable 1}

Sr1646v2PbbEthOamEManagedMepsEntry ::=
   SEQUENCE
      {
      sr1646v2PbbEthOamEManagedMepsGlobalIx
         GlobalIndex,
      sr1646v2PbbEthOamEManagedMepsTableIx
         TableIndex,
      sr1646v2PbbEthOamEManagedMepsManagedMepName
         DisplayString,
      sr1646v2PbbEthOamEManagedMepsInterface
         DisplayString,
      sr1646v2PbbEthOamEManagedMepsVid
         INTEGER,
      sr1646v2PbbEthOamEManagedMepsTpid
         INTEGER,
      sr1646v2PbbEthOamEManagedMepsPriority
         Integer32,
      sr1646v2PbbEthOamEManagedMepsPeriod
         INTEGER,
      sr1646v2PbbEthOamEManagedMepsMegLevel
         Integer32,
      sr1646v2PbbEthOamEManagedMepsMegIdMaintDomainName
         DisplayString,
      sr1646v2PbbEthOamEManagedMepsMegIdShortMaName
         DisplayString,
      sr1646v2PbbEthOamEManagedMepsMepId
         Integer32,
      sr1646v2PbbEthOamEManagedMepsMacAddress
         OCTET STRING,
      sr1646v2PbbEthOamEManagedMepsIntfStatus
         INTEGER,
      sr1646v2PbbEthOamEManagedMepsPortStatus
         INTEGER,
      sr1646v2PbbEthOamEManagedMepsAlarm
         Integer32
      }

sr1646v2PbbEthOamEManagedMepsGlobalIx OBJECT-TYPE
   SYNTAX      GlobalIndex
   MAX-ACCESS  not-accessible
   STATUS      current
   DESCRIPTION
      "The value of the tlsCntTreeGlobalIndex of the MANAGED OBJECT."
   ::= {sr1646v2PbbEthOamEManagedMepsEntry 10}

sr1646v2PbbEthOamEManagedMepsTableIx OBJECT-TYPE
   SYNTAX      TableIndex
   MAX-ACCESS  not-accessible
   STATUS      current
   DESCRIPTION
      ""
   ::= {sr1646v2PbbEthOamEManagedMepsEntry 11}

sr1646v2PbbEthOamEManagedMepsManagedMepName OBJECT-TYPE
   SYNTAX      DisplayString
   MAX-ACCESS  read-only
   STATUS      current
   DESCRIPTION
      "Path: ethOam.status.managedMeps.managedMepName"
   ::= {sr1646v2PbbEthOamEManagedMepsEntry 201326592}

sr1646v2PbbEthOamEManagedMepsInterface OBJECT-TYPE
   SYNTAX      DisplayString
   MAX-ACCESS  read-only
   STATUS      current
   DESCRIPTION
      "Path: ethOam.status.managedMeps.interface"
   ::= {sr1646v2PbbEthOamEManagedMepsEntry 16777216}

sr1646v2PbbEthOamEManagedMepsVid OBJECT-TYPE
   SYNTAX      INTEGER
               {
               untagged (0)
               }
   MAX-ACCESS  read-only
   STATUS      current
   DESCRIPTION
      "Path: ethOam.status.managedMeps.vid

       Possibilities:
               untagged   (0)"
   ::= {sr1646v2PbbEthOamEManagedMepsEntry 33554432}

sr1646v2PbbEthOamEManagedMepsTpid OBJECT-TYPE
   SYNTAX      INTEGER
               {
               slOPTg (0),
               dot1Q (33024),
               dot1ad (34984),
               s0x9100 (37120),
               s0x9200 (37376),
               s0x9300 (37632)
               }
   MAX-ACCESS  read-only
   STATUS      current
   DESCRIPTION
      "Path: ethOam.status.managedMeps.tpid

       Possibilities:
               <OPT>   (0)
               dot1Q   (33024)
               dot1ad   (34984)
               0x9100   (37120)
               0x9200   (37376)
               0x9300   (37632)"
   ::= {sr1646v2PbbEthOamEManagedMepsEntry 218103808}

sr1646v2PbbEthOamEManagedMepsPriority OBJECT-TYPE
   SYNTAX      Integer32
   MAX-ACCESS  read-only
   STATUS      current
   DESCRIPTION
      "Path: ethOam.status.managedMeps.priority"
   ::= {sr1646v2PbbEthOamEManagedMepsEntry 50331648}

sr1646v2PbbEthOamEManagedMepsPeriod OBJECT-TYPE
   SYNTAX      INTEGER
               {
               unknown (0),
               s3d33ms (1),
               s10ms (2),
               s100ms (3),
               s1s (4),
               s10s (5),
               s1min (6),
               s10min (7)
               }
   MAX-ACCESS  read-only
   STATUS      current
   DESCRIPTION
      "Path: ethOam.status.managedMeps.period

       Possibilities:
               unknown   (0)
               3.33ms   (1)
               10ms   (2)
               100ms   (3)
               1s   (4)
               10s   (5)
               1min   (6)
               10min   (7)"
   ::= {sr1646v2PbbEthOamEManagedMepsEntry 67108864}

sr1646v2PbbEthOamEManagedMepsMegLevel OBJECT-TYPE
   SYNTAX      Integer32
   MAX-ACCESS  read-only
   STATUS      current
   DESCRIPTION
      "Path: ethOam.status.managedMeps.megLevel"
   ::= {sr1646v2PbbEthOamEManagedMepsEntry 83886080}

sr1646v2PbbEthOamEManagedMepsMegIdMaintDomainName OBJECT-TYPE
   SYNTAX      DisplayString
   MAX-ACCESS  read-only
   STATUS      current
   DESCRIPTION
      "Path: ethOam.status.managedMeps.megId.maintDomainName"
   ::= {sr1646v2PbbEthOamEManagedMepsEntry 100728832}

sr1646v2PbbEthOamEManagedMepsMegIdShortMaName OBJECT-TYPE
   SYNTAX      DisplayString
   MAX-ACCESS  read-only
   STATUS      current
   DESCRIPTION
      "Path: ethOam.status.managedMeps.megId.shortMaName"
   ::= {sr1646v2PbbEthOamEManagedMepsEntry 100794368}

sr1646v2PbbEthOamEManagedMepsMepId OBJECT-TYPE
   SYNTAX      Integer32
   MAX-ACCESS  read-only
   STATUS      current
   DESCRIPTION
      "Path: ethOam.status.managedMeps.mepId"
   ::= {sr1646v2PbbEthOamEManagedMepsEntry 117440512}

sr1646v2PbbEthOamEManagedMepsMacAddress OBJECT-TYPE
   SYNTAX      OCTET STRING
   MAX-ACCESS  read-only
   STATUS      current
   DESCRIPTION
      "Path: ethOam.status.managedMeps.macAddress

       MAC address."
   ::= {sr1646v2PbbEthOamEManagedMepsEntry 134217728}

sr1646v2PbbEthOamEManagedMepsIntfStatus OBJECT-TYPE
   SYNTAX      INTEGER
               {
               noTlv (0),
               up (1),
               down (2),
               testing (3),
               unknown (4),
               dormant (5),
               notPresent (6),
               lowerLayerDown (7)
               }
   MAX-ACCESS  read-only
   STATUS      current
   DESCRIPTION
      "Path: ethOam.status.managedMeps.intfStatus

       Possibilities:
               noTlv   (0)
               up   (1)
               down   (2)
               testing   (3)
               unknown   (4)
               dormant   (5)
               notPresent   (6)
               lowerLayerDown   (7)"
   ::= {sr1646v2PbbEthOamEManagedMepsEntry 167772160}

sr1646v2PbbEthOamEManagedMepsPortStatus OBJECT-TYPE
   SYNTAX      INTEGER
               {
               noTlv (0),
               blocked (1),
               up (2)
               }
   MAX-ACCESS  read-only
   STATUS      current
   DESCRIPTION
      "Path: ethOam.status.managedMeps.portStatus

       Possibilities:
               noTlv   (0)
               blocked   (1)
               up   (2)"
   ::= {sr1646v2PbbEthOamEManagedMepsEntry 184549376}

sr1646v2PbbEthOamEManagedMepsAlarm OBJECT-TYPE
   SYNTAX      Integer32
   MAX-ACCESS  read-only
   STATUS      current
   DESCRIPTION
      "Path: ethOam.status.managedMeps.alarm

       Bit meanings:
               bit 3 = lossOfContinuity"
   ::= {sr1646v2PbbEthOamEManagedMepsEntry 150994944}


sr1646v2PbbEthOamEDefectLog OBJECT IDENTIFIER ::= {sr1646v2PbbEthOamE 18}

sr1646v2PbbEthOamEDefectLogSSCTable OBJECT-TYPE
   SYNTAX      SEQUENCE OF Sr1646v2PbbEthOamEDefectLogEntry
   MAX-ACCESS  not-accessible
   STATUS      current
   DESCRIPTION
      "ETH OAM defect log"
   ::= {sr1646v2PbbEthOamEDefectLog 1}

sr1646v2PbbEthOamEDefectLogEntry OBJECT-TYPE
   SYNTAX      Sr1646v2PbbEthOamEDefectLogEntry
   MAX-ACCESS  not-accessible
   STATUS      current
   DESCRIPTION
      ""
   INDEX      { sr1646v2PbbEthOamEDefectLogGlobalIx,
                sr1646v2PbbEthOamEDefectLogTableIx }
   ::= {sr1646v2PbbEthOamEDefectLogSSCTable 1}

Sr1646v2PbbEthOamEDefectLogEntry ::=
   SEQUENCE
      {
      sr1646v2PbbEthOamEDefectLogGlobalIx
         GlobalIndex,
      sr1646v2PbbEthOamEDefectLogTableIx
         TableIndex,
      sr1646v2PbbEthOamEDefectLogSysUpTime
         TimeTicks,
      sr1646v2PbbEthOamEDefectLogType
         INTEGER,
      sr1646v2PbbEthOamEDefectLogMode
         INTEGER,
      sr1646v2PbbEthOamEDefectLogMepName
         DisplayString,
      sr1646v2PbbEthOamEDefectLogSourceMacAddress
         OCTET STRING,
      sr1646v2PbbEthOamEDefectLogMegLevel
         Integer32,
      sr1646v2PbbEthOamEDefectLogMegIdMaintDomainName
         DisplayString,
      sr1646v2PbbEthOamEDefectLogMegIdShortMaName
         DisplayString,
      sr1646v2PbbEthOamEDefectLogMepId
         INTEGER,
      sr1646v2PbbEthOamEDefectLogPeriod
         INTEGER,
      sr1646v2PbbEthOamEDefectLogVid
         INTEGER,
      sr1646v2PbbEthOamEDefectLogTpid
         INTEGER
      }

sr1646v2PbbEthOamEDefectLogGlobalIx OBJECT-TYPE
   SYNTAX      GlobalIndex
   MAX-ACCESS  not-accessible
   STATUS      current
   DESCRIPTION
      "The value of the tlsCntTreeGlobalIndex of the MANAGED OBJECT."
   ::= {sr1646v2PbbEthOamEDefectLogEntry 10}

sr1646v2PbbEthOamEDefectLogTableIx OBJECT-TYPE
   SYNTAX      TableIndex
   MAX-ACCESS  not-accessible
   STATUS      current
   DESCRIPTION
      ""
   ::= {sr1646v2PbbEthOamEDefectLogEntry 11}

sr1646v2PbbEthOamEDefectLogSysUpTime OBJECT-TYPE
   SYNTAX      TimeTicks
   MAX-ACCESS  read-only
   STATUS      current
   DESCRIPTION
      "Path: ethOam.status.defectLog.sysUpTime

       Time in centi-second."
   ::= {sr1646v2PbbEthOamEDefectLogEntry 16777216}

sr1646v2PbbEthOamEDefectLogType OBJECT-TYPE
   SYNTAX      INTEGER
               {
               mismerge (1),
               unexpectedMep (2),
               unexpectedMegLevel (3),
               unexpectedPeriod (4),
               aisFrame (5),
               wrongMacAddress (6)
               }
   MAX-ACCESS  read-only
   STATUS      current
   DESCRIPTION
      "Path: ethOam.status.defectLog.type

       Possibilities:
               mismerge   (1)
               unexpectedMep   (2)
               unexpectedMegLevel   (3)
               unexpectedPeriod   (4)
               aisFrame   (5)
               wrongMacAddress   (6)"
   ::= {sr1646v2PbbEthOamEDefectLogEntry 33554432}

sr1646v2PbbEthOamEDefectLogMode OBJECT-TYPE
   SYNTAX      INTEGER
               {
               ym1731 (1),
               s802m1ag (2),
               unknown (4)
               }
   MAX-ACCESS  read-only
   STATUS      current
   DESCRIPTION
      "Path: ethOam.status.defectLog.mode

       Possibilities:
               y-1731   (1)
               802-1ag   (2)
               unknown   (4)"
   ::= {sr1646v2PbbEthOamEDefectLogEntry 50331648}

sr1646v2PbbEthOamEDefectLogMepName OBJECT-TYPE
   SYNTAX      DisplayString
   MAX-ACCESS  read-only
   STATUS      current
   DESCRIPTION
      "Path: ethOam.status.defectLog.mepName"
   ::= {sr1646v2PbbEthOamEDefectLogEntry 67108864}

sr1646v2PbbEthOamEDefectLogSourceMacAddress OBJECT-TYPE
   SYNTAX      OCTET STRING
   MAX-ACCESS  read-only
   STATUS      current
   DESCRIPTION
      "Path: ethOam.status.defectLog.sourceMacAddress

       MAC address."
   ::= {sr1646v2PbbEthOamEDefectLogEntry 83886080}

sr1646v2PbbEthOamEDefectLogMegLevel OBJECT-TYPE
   SYNTAX      Integer32
   MAX-ACCESS  read-only
   STATUS      current
   DESCRIPTION
      "Path: ethOam.status.defectLog.megLevel"
   ::= {sr1646v2PbbEthOamEDefectLogEntry 100663296}

sr1646v2PbbEthOamEDefectLogMegIdMaintDomainName OBJECT-TYPE
   SYNTAX      DisplayString
   MAX-ACCESS  read-only
   STATUS      current
   DESCRIPTION
      "Path: ethOam.status.defectLog.megId.maintDomainName"
   ::= {sr1646v2PbbEthOamEDefectLogEntry 117506048}

sr1646v2PbbEthOamEDefectLogMegIdShortMaName OBJECT-TYPE
   SYNTAX      DisplayString
   MAX-ACCESS  read-only
   STATUS      current
   DESCRIPTION
      "Path: ethOam.status.defectLog.megId.shortMaName"
   ::= {sr1646v2PbbEthOamEDefectLogEntry 117571584}

sr1646v2PbbEthOamEDefectLogMepId OBJECT-TYPE
   SYNTAX      INTEGER
               {
               unknown (8192)
               }
   MAX-ACCESS  read-only
   STATUS      current
   DESCRIPTION
      "Path: ethOam.status.defectLog.mepId

       Possibilities:
               unknown   (8192)"
   ::= {sr1646v2PbbEthOamEDefectLogEntry 134217728}

sr1646v2PbbEthOamEDefectLogPeriod OBJECT-TYPE
   SYNTAX      INTEGER
               {
               unknown (0),
               s3d33ms (1),
               s10ms (2),
               s100ms (3),
               s1s (4),
               s10s (5),
               s1min (6),
               s10min (7)
               }
   MAX-ACCESS  read-only
   STATUS      current
   DESCRIPTION
      "Path: ethOam.status.defectLog.period

       Possibilities:
               unknown   (0)
               3.33ms   (1)
               10ms   (2)
               100ms   (3)
               1s   (4)
               10s   (5)
               1min   (6)
               10min   (7)"
   ::= {sr1646v2PbbEthOamEDefectLogEntry 150994944}

sr1646v2PbbEthOamEDefectLogVid OBJECT-TYPE
   SYNTAX      INTEGER
               {
               untagged (0)
               }
   MAX-ACCESS  read-only
   STATUS      current
   DESCRIPTION
      "Path: ethOam.status.defectLog.vid

       Possibilities:
               untagged   (0)"
   ::= {sr1646v2PbbEthOamEDefectLogEntry 167772160}

sr1646v2PbbEthOamEDefectLogTpid OBJECT-TYPE
   SYNTAX      INTEGER
               {
               slOPTg (0),
               dot1Q (33024),
               dot1ad (34984),
               s0x9100 (37120),
               s0x9200 (37376),
               s0x9300 (37632)
               }
   MAX-ACCESS  read-only
   STATUS      current
   DESCRIPTION
      "Path: ethOam.status.defectLog.tpid

       Possibilities:
               <OPT>   (0)
               dot1Q   (33024)
               dot1ad   (34984)
               0x9100   (37120)
               0x9200   (37376)
               0x9300   (37632)"
   ::= {sr1646v2PbbEthOamEDefectLogEntry 184549376}


sr1646v2PbbEthOamEOperStatus OBJECT IDENTIFIER ::= {sr1646v2PbbEthOamE 39}

sr1646v2PbbEthOamEOperStatusTable OBJECT-TYPE
   SYNTAX      SEQUENCE OF Sr1646v2PbbEthOamEOperStatusEntry
   MAX-ACCESS  not-accessible
   STATUS      current
   DESCRIPTION
      "OAM module operating status"
   ::= {sr1646v2PbbEthOamEOperStatus 1}

sr1646v2PbbEthOamEOperStatusEntry OBJECT-TYPE
   SYNTAX      Sr1646v2PbbEthOamEOperStatusEntry
   MAX-ACCESS  not-accessible
   STATUS      current
   DESCRIPTION
      ""
   INDEX      { sr1646v2PbbEthOamEOperStatusGlobalIx }
   ::= {sr1646v2PbbEthOamEOperStatusTable 1}

Sr1646v2PbbEthOamEOperStatusEntry ::=
   SEQUENCE
      {
      sr1646v2PbbEthOamEOperStatusGlobalIx
         GlobalIndex,
      sr1646v2PbbEthOamEOperStatusValue
         INTEGER
      }

sr1646v2PbbEthOamEOperStatusGlobalIx OBJECT-TYPE
   SYNTAX      GlobalIndex
   MAX-ACCESS  not-accessible
   STATUS      current
   DESCRIPTION
      "The value of the tlsCntTreeGlobalIndex of the MANAGED OBJECT."
   ::= {sr1646v2PbbEthOamEOperStatusEntry 10}

sr1646v2PbbEthOamEOperStatusValue OBJECT-TYPE
   SYNTAX      INTEGER
               {
               booting (0),
               disabled (1),
               startDelay (2),
               enabled (3)
               }
   MAX-ACCESS  read-only
   STATUS      current
   DESCRIPTION
      "Path: ethOam.status.operStatus

       Possibilities:
               booting   (0)
               disabled   (1)
               startDelay   (2)
               enabled   (3)"
   ::= {sr1646v2PbbEthOamEOperStatusEntry 2147483648}


sr1646v2PbbEthOamESnmpIndex OBJECT IDENTIFIER ::= {sr1646v2PbbEthOamE 269}

sr1646v2PbbEthOamESnmpIndexTable OBJECT-TYPE
   SYNTAX      SEQUENCE OF Sr1646v2PbbEthOamESnmpIndexEntry
   MAX-ACCESS  not-accessible
   STATUS      current
   DESCRIPTION
      "SNMP index assigned to this object"
   ::= {sr1646v2PbbEthOamESnmpIndex 1}

sr1646v2PbbEthOamESnmpIndexEntry OBJECT-TYPE
   SYNTAX      Sr1646v2PbbEthOamESnmpIndexEntry
   MAX-ACCESS  not-accessible
   STATUS      current
   DESCRIPTION
      ""
   INDEX      { sr1646v2PbbEthOamESnmpIndexGlobalIx }
   ::= {sr1646v2PbbEthOamESnmpIndexTable 1}

Sr1646v2PbbEthOamESnmpIndexEntry ::=
   SEQUENCE
      {
      sr1646v2PbbEthOamESnmpIndexGlobalIx
         GlobalIndex,
      sr1646v2PbbEthOamESnmpIndexValue
         Integer32
      }

sr1646v2PbbEthOamESnmpIndexGlobalIx OBJECT-TYPE
   SYNTAX      GlobalIndex
   MAX-ACCESS  not-accessible
   STATUS      current
   DESCRIPTION
      "The value of the tlsCntTreeGlobalIndex of the MANAGED OBJECT."
   ::= {sr1646v2PbbEthOamESnmpIndexEntry 10}

sr1646v2PbbEthOamESnmpIndexValue OBJECT-TYPE
   SYNTAX      Integer32
   MAX-ACCESS  read-only
   STATUS      current
   DESCRIPTION
      "Path: ethOam.status.snmpIndex"
   ::= {sr1646v2PbbEthOamESnmpIndexEntry 2147483648}



pr1646v2PbbEthOamE OBJECT IDENTIFIER ::= {r1646v2PbbEthOamE 12}


pr1646v2PbbEthOamELinkTrace OBJECT IDENTIFIER ::= {pr1646v2PbbEthOamE 19}

pr1646v2PbbEthOamELinkTraceSSCTable OBJECT-TYPE
   SYNTAX      SEQUENCE OF Pr1646v2PbbEthOamELinkTraceEntry
   MAX-ACCESS  not-accessible
   STATUS      current
   DESCRIPTION
      "link trace status"
   ::= {pr1646v2PbbEthOamELinkTrace 1}

pr1646v2PbbEthOamELinkTraceEntry OBJECT-TYPE
   SYNTAX      Pr1646v2PbbEthOamELinkTraceEntry
   MAX-ACCESS  not-accessible
   STATUS      current
   DESCRIPTION
      ""
   INDEX      { pr1646v2PbbEthOamELinkTraceGlobalIx,
                pr1646v2PbbEthOamELinkTraceTableIx }
   ::= {pr1646v2PbbEthOamELinkTraceSSCTable 1}

Pr1646v2PbbEthOamELinkTraceEntry ::=
   SEQUENCE
      {
      pr1646v2PbbEthOamELinkTraceGlobalIx
         GlobalIndex,
      pr1646v2PbbEthOamELinkTraceTableIx
         TableIndex,
      pr1646v2PbbEthOamELinkTraceSourceMepName
         DisplayString,
      pr1646v2PbbEthOamELinkTraceTtl
         Integer32,
      pr1646v2PbbEthOamELinkTraceRelayAction
         INTEGER,
      pr1646v2PbbEthOamELinkTraceIngressAction
         INTEGER,
      pr1646v2PbbEthOamELinkTraceIngressMacAddress
         OCTET STRING,
      pr1646v2PbbEthOamELinkTraceEgressAction
         INTEGER,
      pr1646v2PbbEthOamELinkTraceEgressMacAddress
         OCTET STRING
      }

pr1646v2PbbEthOamELinkTraceGlobalIx OBJECT-TYPE
   SYNTAX      GlobalIndex
   MAX-ACCESS  not-accessible
   STATUS      current
   DESCRIPTION
      "The value of the tlsCntTreeGlobalIndex of the MANAGED OBJECT."
   ::= {pr1646v2PbbEthOamELinkTraceEntry 10}

pr1646v2PbbEthOamELinkTraceTableIx OBJECT-TYPE
   SYNTAX      TableIndex
   MAX-ACCESS  not-accessible
   STATUS      current
   DESCRIPTION
      ""
   ::= {pr1646v2PbbEthOamELinkTraceEntry 11}

pr1646v2PbbEthOamELinkTraceSourceMepName OBJECT-TYPE
   SYNTAX      DisplayString
   MAX-ACCESS  read-only
   STATUS      current
   DESCRIPTION
      "Path: ethOam.performance.linkTrace.sourceMepName"
   ::= {pr1646v2PbbEthOamELinkTraceEntry 16777216}

pr1646v2PbbEthOamELinkTraceTtl OBJECT-TYPE
   SYNTAX      Integer32
   MAX-ACCESS  read-only
   STATUS      current
   DESCRIPTION
      "Path: ethOam.performance.linkTrace.ttl"
   ::= {pr1646v2PbbEthOamELinkTraceEntry 33554432}

pr1646v2PbbEthOamELinkTraceRelayAction OBJECT-TYPE
   SYNTAX      INTEGER
               {
               rlyHit (1),
               rlyFdb (2),
               rlyMpdb (3)
               }
   MAX-ACCESS  read-only
   STATUS      current
   DESCRIPTION
      "Path: ethOam.performance.linkTrace.relayAction

       Possibilities:
               rlyHit   (1)
               rlyFdb   (2)
               rlyMpdb   (3)"
   ::= {pr1646v2PbbEthOamELinkTraceEntry 50331648}

pr1646v2PbbEthOamELinkTraceIngressAction OBJECT-TYPE
   SYNTAX      INTEGER
               {
               notPresent (0),
               ingOk (1),
               ingDown (2),
               ingBlocked (3),
               ingVid (4),
               ingY1731 (239)
               }
   MAX-ACCESS  read-only
   STATUS      current
   DESCRIPTION
      "Path: ethOam.performance.linkTrace.ingressAction

       Possibilities:
               notPresent   (0)
               ingOk   (1)
               ingDown   (2)
               ingBlocked   (3)
               ingVid   (4)
               ingY1731   (239)"
   ::= {pr1646v2PbbEthOamELinkTraceEntry 67108864}

pr1646v2PbbEthOamELinkTraceIngressMacAddress OBJECT-TYPE
   SYNTAX      OCTET STRING
   MAX-ACCESS  read-only
   STATUS      current
   DESCRIPTION
      "Path: ethOam.performance.linkTrace.ingressMacAddress

       MAC address."
   ::= {pr1646v2PbbEthOamELinkTraceEntry 83886080}

pr1646v2PbbEthOamELinkTraceEgressAction OBJECT-TYPE
   SYNTAX      INTEGER
               {
               notPresent (0),
               egrOk (1),
               egrDown (2),
               egrBlocked (3),
               egrVid (4),
               egrY1731 (239)
               }
   MAX-ACCESS  read-only
   STATUS      current
   DESCRIPTION
      "Path: ethOam.performance.linkTrace.egressAction

       Possibilities:
               notPresent   (0)
               egrOk   (1)
               egrDown   (2)
               egrBlocked   (3)
               egrVid   (4)
               egrY1731   (239)"
   ::= {pr1646v2PbbEthOamELinkTraceEntry 100663296}

pr1646v2PbbEthOamELinkTraceEgressMacAddress OBJECT-TYPE
   SYNTAX      OCTET STRING
   MAX-ACCESS  read-only
   STATUS      current
   DESCRIPTION
      "Path: ethOam.performance.linkTrace.egressMacAddress

       MAC address."
   ::= {pr1646v2PbbEthOamELinkTraceEntry 117440512}


pr1646v2PbbEthOamEMulticastLoopback OBJECT IDENTIFIER ::= {pr1646v2PbbEthOamE 35}

pr1646v2PbbEthOamEMulticastLoopbackSSCTable OBJECT-TYPE
   SYNTAX      SEQUENCE OF Pr1646v2PbbEthOamEMulticastLoopbackEntry
   MAX-ACCESS  not-accessible
   STATUS      current
   DESCRIPTION
      "multicast loopback status"
   ::= {pr1646v2PbbEthOamEMulticastLoopback 1}

pr1646v2PbbEthOamEMulticastLoopbackEntry OBJECT-TYPE
   SYNTAX      Pr1646v2PbbEthOamEMulticastLoopbackEntry
   MAX-ACCESS  not-accessible
   STATUS      current
   DESCRIPTION
      ""
   INDEX      { pr1646v2PbbEthOamEMulticastLoopbackGlobalIx,
                pr1646v2PbbEthOamEMulticastLoopbackTableIx }
   ::= {pr1646v2PbbEthOamEMulticastLoopbackSSCTable 1}

Pr1646v2PbbEthOamEMulticastLoopbackEntry ::=
   SEQUENCE
      {
      pr1646v2PbbEthOamEMulticastLoopbackGlobalIx
         GlobalIndex,
      pr1646v2PbbEthOamEMulticastLoopbackTableIx
         TableIndex,
      pr1646v2PbbEthOamEMulticastLoopbackSourceMepName
         DisplayString,
      pr1646v2PbbEthOamEMulticastLoopbackRemoteMacAddress
         OCTET STRING,
      pr1646v2PbbEthOamEMulticastLoopbackStatus
         INTEGER,
      pr1646v2PbbEthOamEMulticastLoopbackMepId
         INTEGER,
      pr1646v2PbbEthOamEMulticastLoopbackDelay
         Integer32
      }

pr1646v2PbbEthOamEMulticastLoopbackGlobalIx OBJECT-TYPE
   SYNTAX      GlobalIndex
   MAX-ACCESS  not-accessible
   STATUS      current
   DESCRIPTION
      "The value of the tlsCntTreeGlobalIndex of the MANAGED OBJECT."
   ::= {pr1646v2PbbEthOamEMulticastLoopbackEntry 10}

pr1646v2PbbEthOamEMulticastLoopbackTableIx OBJECT-TYPE
   SYNTAX      TableIndex
   MAX-ACCESS  not-accessible
   STATUS      current
   DESCRIPTION
      ""
   ::= {pr1646v2PbbEthOamEMulticastLoopbackEntry 11}

pr1646v2PbbEthOamEMulticastLoopbackSourceMepName OBJECT-TYPE
   SYNTAX      DisplayString
   MAX-ACCESS  read-only
   STATUS      current
   DESCRIPTION
      "Path: ethOam.performance.multicastLoopback.sourceMepName"
   ::= {pr1646v2PbbEthOamEMulticastLoopbackEntry 16777216}

pr1646v2PbbEthOamEMulticastLoopbackRemoteMacAddress OBJECT-TYPE
   SYNTAX      OCTET STRING
   MAX-ACCESS  read-only
   STATUS      current
   DESCRIPTION
      "Path: ethOam.performance.multicastLoopback.remoteMacAddress

       MAC address."
   ::= {pr1646v2PbbEthOamEMulticastLoopbackEntry 33554432}

pr1646v2PbbEthOamEMulticastLoopbackStatus OBJECT-TYPE
   SYNTAX      INTEGER
               {
               managed (0),
               discovered (1),
               unknown (2)
               }
   MAX-ACCESS  read-only
   STATUS      current
   DESCRIPTION
      "Path: ethOam.performance.multicastLoopback.status

       Possibilities:
               managed   (0)
               discovered   (1)
               unknown   (2)"
   ::= {pr1646v2PbbEthOamEMulticastLoopbackEntry 50331648}

pr1646v2PbbEthOamEMulticastLoopbackMepId OBJECT-TYPE
   SYNTAX      INTEGER
               {
               unknown (8192)
               }
   MAX-ACCESS  read-only
   STATUS      current
   DESCRIPTION
      "Path: ethOam.performance.multicastLoopback.mepId

       Possibilities:
               unknown   (8192)"
   ::= {pr1646v2PbbEthOamEMulticastLoopbackEntry 67108864}

pr1646v2PbbEthOamEMulticastLoopbackDelay OBJECT-TYPE
   SYNTAX      Integer32
   MAX-ACCESS  read-only
   STATUS      current
   DESCRIPTION
      "Path: ethOam.performance.multicastLoopback.delay

       unit name = sec
       formula = 1000 / ; 1000 *"
   ::= {pr1646v2PbbEthOamEMulticastLoopbackEntry 83886080}


pr1646v2PbbEthOamELoopback OBJECT IDENTIFIER ::= {pr1646v2PbbEthOamE 20}

pr1646v2PbbEthOamELoopbackSSCTable OBJECT-TYPE
   SYNTAX      SEQUENCE OF Pr1646v2PbbEthOamELoopbackEntry
   MAX-ACCESS  not-accessible
   STATUS      current
   DESCRIPTION
      "loopback performance table"
   ::= {pr1646v2PbbEthOamELoopback 1}

pr1646v2PbbEthOamELoopbackEntry OBJECT-TYPE
   SYNTAX      Pr1646v2PbbEthOamELoopbackEntry
   MAX-ACCESS  not-accessible
   STATUS      current
   DESCRIPTION
      ""
   INDEX      { pr1646v2PbbEthOamELoopbackGlobalIx,
                pr1646v2PbbEthOamELoopbackTableIx }
   ::= {pr1646v2PbbEthOamELoopbackSSCTable 1}

Pr1646v2PbbEthOamELoopbackEntry ::=
   SEQUENCE
      {
      pr1646v2PbbEthOamELoopbackGlobalIx
         GlobalIndex,
      pr1646v2PbbEthOamELoopbackTableIx
         TableIndex,
      pr1646v2PbbEthOamELoopbackMepName
         DisplayString,
      pr1646v2PbbEthOamELoopbackMegLevel
         Integer32,
      pr1646v2PbbEthOamELoopbackMegIdMaintDomainName
         DisplayString,
      pr1646v2PbbEthOamELoopbackMegIdShortMaName
         DisplayString,
      pr1646v2PbbEthOamELoopbackMepId
         INTEGER,
      pr1646v2PbbEthOamELoopbackMacAddress
         OCTET STRING,
      pr1646v2PbbEthOamELoopbackPriority
         Integer32,
      pr1646v2PbbEthOamELoopbackNbrOfTxFrames
         Counter32,
      pr1646v2PbbEthOamELoopbackNbrOfRxFrames
         Counter32,
      pr1646v2PbbEthOamELoopbackNbrOfOutOfSeqFrames
         Counter32,
      pr1646v2PbbEthOamELoopbackNbrOfLateFrames
         Counter32,
      pr1646v2PbbEthOamELoopbackNbrOfBadDataFrames
         Counter32
      }

pr1646v2PbbEthOamELoopbackGlobalIx OBJECT-TYPE
   SYNTAX      GlobalIndex
   MAX-ACCESS  not-accessible
   STATUS      current
   DESCRIPTION
      "The value of the tlsCntTreeGlobalIndex of the MANAGED OBJECT."
   ::= {pr1646v2PbbEthOamELoopbackEntry 10}

pr1646v2PbbEthOamELoopbackTableIx OBJECT-TYPE
   SYNTAX      TableIndex
   MAX-ACCESS  not-accessible
   STATUS      current
   DESCRIPTION
      ""
   ::= {pr1646v2PbbEthOamELoopbackEntry 11}

pr1646v2PbbEthOamELoopbackMepName OBJECT-TYPE
   SYNTAX      DisplayString
   MAX-ACCESS  read-only
   STATUS      current
   DESCRIPTION
      "Path: ethOam.performance.loopback.mepName"
   ::= {pr1646v2PbbEthOamELoopbackEntry 16777216}

pr1646v2PbbEthOamELoopbackMegLevel OBJECT-TYPE
   SYNTAX      Integer32
   MAX-ACCESS  read-only
   STATUS      current
   DESCRIPTION
      "Path: ethOam.performance.loopback.megLevel"
   ::= {pr1646v2PbbEthOamELoopbackEntry 33554432}

pr1646v2PbbEthOamELoopbackMegIdMaintDomainName OBJECT-TYPE
   SYNTAX      DisplayString
   MAX-ACCESS  read-only
   STATUS      current
   DESCRIPTION
      "Path: ethOam.performance.loopback.megId.maintDomainName"
   ::= {pr1646v2PbbEthOamELoopbackEntry 50397184}

pr1646v2PbbEthOamELoopbackMegIdShortMaName OBJECT-TYPE
   SYNTAX      DisplayString
   MAX-ACCESS  read-only
   STATUS      current
   DESCRIPTION
      "Path: ethOam.performance.loopback.megId.shortMaName"
   ::= {pr1646v2PbbEthOamELoopbackEntry 50462720}

pr1646v2PbbEthOamELoopbackMepId OBJECT-TYPE
   SYNTAX      INTEGER
               {
               unknown (8192)
               }
   MAX-ACCESS  read-only
   STATUS      current
   DESCRIPTION
      "Path: ethOam.performance.loopback.mepId

       Possibilities:
               unknown   (8192)"
   ::= {pr1646v2PbbEthOamELoopbackEntry 67108864}

pr1646v2PbbEthOamELoopbackMacAddress OBJECT-TYPE
   SYNTAX      OCTET STRING
   MAX-ACCESS  read-only
   STATUS      current
   DESCRIPTION
      "Path: ethOam.performance.loopback.macAddress

       MAC address."
   ::= {pr1646v2PbbEthOamELoopbackEntry 83886080}

pr1646v2PbbEthOamELoopbackPriority OBJECT-TYPE
   SYNTAX      Integer32
   MAX-ACCESS  read-only
   STATUS      current
   DESCRIPTION
      "Path: ethOam.performance.loopback.priority"
   ::= {pr1646v2PbbEthOamELoopbackEntry 100663296}

pr1646v2PbbEthOamELoopbackNbrOfTxFrames OBJECT-TYPE
   SYNTAX      Counter32
   MAX-ACCESS  read-only
   STATUS      current
   DESCRIPTION
      "Path: ethOam.performance.loopback.nbrOfTxFrames

       32 bit unsigned wrappable counter."
   ::= {pr1646v2PbbEthOamELoopbackEntry 117440512}

pr1646v2PbbEthOamELoopbackNbrOfRxFrames OBJECT-TYPE
   SYNTAX      Counter32
   MAX-ACCESS  read-only
   STATUS      current
   DESCRIPTION
      "Path: ethOam.performance.loopback.nbrOfRxFrames

       32 bit unsigned wrappable counter."
   ::= {pr1646v2PbbEthOamELoopbackEntry 134217728}

pr1646v2PbbEthOamELoopbackNbrOfOutOfSeqFrames OBJECT-TYPE
   SYNTAX      Counter32
   MAX-ACCESS  read-only
   STATUS      current
   DESCRIPTION
      "Path: ethOam.performance.loopback.nbrOfOutOfSeqFrames

       32 bit unsigned wrappable counter."
   ::= {pr1646v2PbbEthOamELoopbackEntry 150994944}

pr1646v2PbbEthOamELoopbackNbrOfLateFrames OBJECT-TYPE
   SYNTAX      Counter32
   MAX-ACCESS  read-only
   STATUS      current
   DESCRIPTION
      "Path: ethOam.performance.loopback.nbrOfLateFrames

       32 bit unsigned wrappable counter."
   ::= {pr1646v2PbbEthOamELoopbackEntry 167772160}

pr1646v2PbbEthOamELoopbackNbrOfBadDataFrames OBJECT-TYPE
   SYNTAX      Counter32
   MAX-ACCESS  read-only
   STATUS      current
   DESCRIPTION
      "Path: ethOam.performance.loopback.nbrOfBadDataFrames

       32 bit unsigned wrappable counter."
   ::= {pr1646v2PbbEthOamELoopbackEntry 184549376}


pr1646v2PbbEthOamEQualityMonitor OBJECT IDENTIFIER ::= {pr1646v2PbbEthOamE 37}

pr1646v2PbbEthOamEQualityMonitorSSCTable OBJECT-TYPE
   SYNTAX      SEQUENCE OF Pr1646v2PbbEthOamEQualityMonitorEntry
   MAX-ACCESS  not-accessible
   STATUS      current
   DESCRIPTION
      "OAM quality monitor"
   ::= {pr1646v2PbbEthOamEQualityMonitor 1}

pr1646v2PbbEthOamEQualityMonitorEntry OBJECT-TYPE
   SYNTAX      Pr1646v2PbbEthOamEQualityMonitorEntry
   MAX-ACCESS  not-accessible
   STATUS      current
   DESCRIPTION
      ""
   INDEX      { pr1646v2PbbEthOamEQualityMonitorGlobalIx,
                pr1646v2PbbEthOamEQualityMonitorTableIx }
   ::= {pr1646v2PbbEthOamEQualityMonitorSSCTable 1}

Pr1646v2PbbEthOamEQualityMonitorEntry ::=
   SEQUENCE
      {
      pr1646v2PbbEthOamEQualityMonitorGlobalIx
         GlobalIndex,
      pr1646v2PbbEthOamEQualityMonitorTableIx
         TableIndex,
      pr1646v2PbbEthOamEQualityMonitorName
         DisplayString,
      pr1646v2PbbEthOamEQualityMonitorStatus
         INTEGER,
      pr1646v2PbbEthOamEQualityMonitorMepName
         DisplayString,
      pr1646v2PbbEthOamEQualityMonitorMegLevel
         Integer32,
      pr1646v2PbbEthOamEQualityMonitorMegIdMaintDomainName
         DisplayString,
      pr1646v2PbbEthOamEQualityMonitorMegIdShortMaName
         DisplayString,
      pr1646v2PbbEthOamEQualityMonitorMepId
         INTEGER,
      pr1646v2PbbEthOamEQualityMonitorMacAddress
         OCTET STRING,
      pr1646v2PbbEthOamEQualityMonitorPriority
         Integer32,
      pr1646v2PbbEthOamEQualityMonitorType
         INTEGER,
      pr1646v2PbbEthOamEQualityMonitorNbrTxPckt
         Counter32,
      pr1646v2PbbEthOamEQualityMonitorNbrRxPckt
         Counter32,
      pr1646v2PbbEthOamEQualityMonitorError
         Counter32,
      pr1646v2PbbEthOamEQualityMonitorDelay
         Integer32,
      pr1646v2PbbEthOamEQualityMonitorJitter
         Integer32,
      pr1646v2PbbEthOamEQualityMonitorLoss
         Counter32,
      pr1646v2PbbEthOamEQualityMonitorLossDelay
         Counter32,
      pr1646v2PbbEthOamEQualityMonitorDelayMin
         Integer32,
      pr1646v2PbbEthOamEQualityMonitorDelayAvrg
         Integer32,
      pr1646v2PbbEthOamEQualityMonitorDelayMax
         Integer32,
      pr1646v2PbbEthOamEQualityMonitorDelayBinsType
         INTEGER,
      pr1646v2PbbEthOamEQualityMonitorDelayBinsMinMin
         Counter32,
      pr1646v2PbbEthOamEQualityMonitorDelayBinsMin
         Integer32,
      pr1646v2PbbEthOamEQualityMonitorDelayBinsMinBin1
         Counter32,
      pr1646v2PbbEthOamEQualityMonitorDelayBinsBin2
         Counter32,
      pr1646v2PbbEthOamEQualityMonitorDelayBinsBin3
         Counter32,
      pr1646v2PbbEthOamEQualityMonitorDelayBinsBin4
         Counter32,
      pr1646v2PbbEthOamEQualityMonitorDelayBinsBin5
         Counter32,
      pr1646v2PbbEthOamEQualityMonitorDelayBinsBin6
         Counter32,
      pr1646v2PbbEthOamEQualityMonitorDelayBinsBin7
         Counter32,
      pr1646v2PbbEthOamEQualityMonitorDelayBinsMaxBin8
         Counter32,
      pr1646v2PbbEthOamEQualityMonitorDelayBinsMax
         Integer32,
      pr1646v2PbbEthOamEQualityMonitorDelayBinsPlusMax
         Counter32,
      pr1646v2PbbEthOamEQualityMonitorJitterNegMax
         Integer32,
      pr1646v2PbbEthOamEQualityMonitorJitterAvrg
         Integer32,
      pr1646v2PbbEthOamEQualityMonitorJitterPosMax
         Integer32,
      pr1646v2PbbEthOamEQualityMonitorJitterBinsType
         INTEGER,
      pr1646v2PbbEthOamEQualityMonitorJitterBinsMinMin
         Counter32,
      pr1646v2PbbEthOamEQualityMonitorJitterBinsMin
         Integer32,
      pr1646v2PbbEthOamEQualityMonitorJitterBinsMinBin1
         Counter32,
      pr1646v2PbbEthOamEQualityMonitorJitterBinsBin2
         Counter32,
      pr1646v2PbbEthOamEQualityMonitorJitterBinsBin3
         Counter32,
      pr1646v2PbbEthOamEQualityMonitorJitterBinsBin4
         Counter32,
      pr1646v2PbbEthOamEQualityMonitorJitterBinsBin5
         Counter32,
      pr1646v2PbbEthOamEQualityMonitorJitterBinsBin6
         Counter32,
      pr1646v2PbbEthOamEQualityMonitorJitterBinsBin7
         Counter32,
      pr1646v2PbbEthOamEQualityMonitorJitterBinsMaxBin8
         Counter32,
      pr1646v2PbbEthOamEQualityMonitorJitterBinsMax
         Integer32,
      pr1646v2PbbEthOamEQualityMonitorJitterBinsPlusMax
         Counter32,
      pr1646v2PbbEthOamEQualityMonitorUpDownStatus
         INTEGER,
      pr1646v2PbbEthOamEQualityMonitorUpDownLossUp
         Counter32,
      pr1646v2PbbEthOamEQualityMonitorUpDownLossDelayUp
         Counter32,
      pr1646v2PbbEthOamEQualityMonitorUpDownDelayUpMin
         Integer32,
      pr1646v2PbbEthOamEQualityMonitorUpDownDelayUpAvrg
         Integer32,
      pr1646v2PbbEthOamEQualityMonitorUpDownDelayUpMax
         Integer32,
      pr1646v2PbbEthOamEQualityMonitorUpDownDelayUpBinsType
         INTEGER,
      pr1646v2PbbEthOamEQualityMonitorUpDownDelayUpBinsMinMin
         Counter32,
      pr1646v2PbbEthOamEQualityMonitorUpDownDelayUpBinsMin
         Integer32,
      pr1646v2PbbEthOamEQualityMonitorUpDownDelayUpBinsMinBin1
         Counter32,
      pr1646v2PbbEthOamEQualityMonitorUpDownDelayUpBinsBin2
         Counter32,
      pr1646v2PbbEthOamEQualityMonitorUpDownDelayUpBinsBin3
         Counter32,
      pr1646v2PbbEthOamEQualityMonitorUpDownDelayUpBinsBin4
         Counter32,
      pr1646v2PbbEthOamEQualityMonitorUpDownDelayUpBinsBin5
         Counter32,
      pr1646v2PbbEthOamEQualityMonitorUpDownDelayUpBinsBin6
         Counter32,
      pr1646v2PbbEthOamEQualityMonitorUpDownDelayUpBinsBin7
         Counter32,
      pr1646v2PbbEthOamEQualityMonitorUpDownDelayUpBinsMaxBin8
         Counter32,
      pr1646v2PbbEthOamEQualityMonitorUpDownDelayUpBinsMax
         Integer32,
      pr1646v2PbbEthOamEQualityMonitorUpDownDelayUpBinsPlusMax
         Counter32,
      pr1646v2PbbEthOamEQualityMonitorUpDownJitterUp
         Integer32,
      pr1646v2PbbEthOamEQualityMonitorUpDownJitterUpNegMax
         Integer32,
      pr1646v2PbbEthOamEQualityMonitorUpDownJitterUpAvrg
         Integer32,
      pr1646v2PbbEthOamEQualityMonitorUpDownJitterUpPosMax
         Integer32,
      pr1646v2PbbEthOamEQualityMonitorUpDownJitterUpBinsType
         INTEGER,
      pr1646v2PbbEthOamEQualityMonitorUpDownJitterUpBinsMinMin
         Counter32,
      pr1646v2PbbEthOamEQualityMonitorUpDownJitterUpBinsMin
         Integer32,
      pr1646v2PbbEthOamEQualityMonitorUpDownJitterUpBinsMinBin1
         Counter32,
      pr1646v2PbbEthOamEQualityMonitorUpDownJitterUpBinsBin2
         Counter32,
      pr1646v2PbbEthOamEQualityMonitorUpDownJitterUpBinsBin3
         Counter32,
      pr1646v2PbbEthOamEQualityMonitorUpDownJitterUpBinsBin4
         Counter32,
      pr1646v2PbbEthOamEQualityMonitorUpDownJitterUpBinsBin5
         Counter32,
      pr1646v2PbbEthOamEQualityMonitorUpDownJitterUpBinsBin6
         Counter32,
      pr1646v2PbbEthOamEQualityMonitorUpDownJitterUpBinsBin7
         Counter32,
      pr1646v2PbbEthOamEQualityMonitorUpDownJitterUpBinsMaxBin8
         Counter32,
      pr1646v2PbbEthOamEQualityMonitorUpDownJitterUpBinsMax
         Integer32,
      pr1646v2PbbEthOamEQualityMonitorUpDownJitterUpBinsPlusMax
         Counter32,
      pr1646v2PbbEthOamEQualityMonitorUpDownLossDown
         Counter32,
      pr1646v2PbbEthOamEQualityMonitorUpDownLossDelayDown
         Counter32,
      pr1646v2PbbEthOamEQualityMonitorUpDownDelayDownMin
         Integer32,
      pr1646v2PbbEthOamEQualityMonitorUpDownDelayDownAvrg
         Integer32,
      pr1646v2PbbEthOamEQualityMonitorUpDownDelayDownMax
         Integer32,
      pr1646v2PbbEthOamEQualityMonitorUpDownDelayDownBinsType
         INTEGER,
      pr1646v2PbbEthOamEQualityMonitorUpDownDelayDownBinsMinMin
         Counter32,
      pr1646v2PbbEthOamEQualityMonitorUpDownDelayDownBinsMin
         Integer32,
      pr1646v2PbbEthOamEQualityMonitorUpDownDelayDownBinsMinBin1
         Counter32,
      pr1646v2PbbEthOamEQualityMonitorUpDownDelayDownBinsBin2
         Counter32,
      pr1646v2PbbEthOamEQualityMonitorUpDownDelayDownBinsBin3
         Counter32,
      pr1646v2PbbEthOamEQualityMonitorUpDownDelayDownBinsBin4
         Counter32,
      pr1646v2PbbEthOamEQualityMonitorUpDownDelayDownBinsBin5
         Counter32,
      pr1646v2PbbEthOamEQualityMonitorUpDownDelayDownBinsBin6
         Counter32,
      pr1646v2PbbEthOamEQualityMonitorUpDownDelayDownBinsBin7
         Counter32,
      pr1646v2PbbEthOamEQualityMonitorUpDownDelayDownBinsMaxBin8
         Counter32,
      pr1646v2PbbEthOamEQualityMonitorUpDownDelayDownBinsMax
         Integer32,
      pr1646v2PbbEthOamEQualityMonitorUpDownDelayDownBinsPlusMax
         Counter32,
      pr1646v2PbbEthOamEQualityMonitorUpDownJitterDown
         Integer32,
      pr1646v2PbbEthOamEQualityMonitorUpDownJitterDownNegMax
         Integer32,
      pr1646v2PbbEthOamEQualityMonitorUpDownJitterDownAvrg
         Integer32,
      pr1646v2PbbEthOamEQualityMonitorUpDownJitterDownPosMax
         Integer32,
      pr1646v2PbbEthOamEQualityMonitorUpDownJitterDownBinsType
         INTEGER,
      pr1646v2PbbEthOamEQualityMonitorUpDownJitterDownBinsMinMin
         Counter32,
      pr1646v2PbbEthOamEQualityMonitorUpDownJitterDownBinsMin
         Integer32,
      pr1646v2PbbEthOamEQualityMonitorUpDownJitterDownBinsMinBin1
         Counter32,
      pr1646v2PbbEthOamEQualityMonitorUpDownJitterDownBinsBin2
         Counter32,
      pr1646v2PbbEthOamEQualityMonitorUpDownJitterDownBinsBin3
         Counter32,
      pr1646v2PbbEthOamEQualityMonitorUpDownJitterDownBinsBin4
         Counter32,
      pr1646v2PbbEthOamEQualityMonitorUpDownJitterDownBinsBin5
         Counter32,
      pr1646v2PbbEthOamEQualityMonitorUpDownJitterDownBinsBin6
         Counter32,
      pr1646v2PbbEthOamEQualityMonitorUpDownJitterDownBinsBin7
         Counter32,
      pr1646v2PbbEthOamEQualityMonitorUpDownJitterDownBinsMaxBin8
         Counter32,
      pr1646v2PbbEthOamEQualityMonitorUpDownJitterDownBinsMax
         Integer32,
      pr1646v2PbbEthOamEQualityMonitorUpDownJitterDownBinsPlusMax
         Counter32,
      pr1646v2PbbEthOamEQualityMonitorLastLogSysUpTime
         TimeTicks,
      pr1646v2PbbEthOamEQualityMonitorLastLogNbrTxPckt
         Counter32,
      pr1646v2PbbEthOamEQualityMonitorLastLogNbrRxPckt
         Counter32,
      pr1646v2PbbEthOamEQualityMonitorLastLogError
         Counter32,
      pr1646v2PbbEthOamEQualityMonitorLastLogLoss
         Counter32,
      pr1646v2PbbEthOamEQualityMonitorLastLogLossDelay
         Counter32,
      pr1646v2PbbEthOamEQualityMonitorLastLogDelayMin
         Integer32,
      pr1646v2PbbEthOamEQualityMonitorLastLogDelayAvrg
         Integer32,
      pr1646v2PbbEthOamEQualityMonitorLastLogDelayMax
         Integer32,
      pr1646v2PbbEthOamEQualityMonitorLastLogJitterNegMax
         Integer32,
      pr1646v2PbbEthOamEQualityMonitorLastLogJitterAvrg
         Integer32,
      pr1646v2PbbEthOamEQualityMonitorLastLogJitterPosMax
         Integer32,
      pr1646v2PbbEthOamEQualityMonitorLastLogUpDownStatus
         INTEGER,
      pr1646v2PbbEthOamEQualityMonitorLastLogUpDownLossUp
         Counter32,
      pr1646v2PbbEthOamEQualityMonitorLastLogUpDownLossDelayUp
         Counter32,
      pr1646v2PbbEthOamEQualityMonitorLastLogUpDownDelayUpMin
         Integer32,
      pr1646v2PbbEthOamEQualityMonitorLastLogUpDownDelayUpAvrg
         Integer32,
      pr1646v2PbbEthOamEQualityMonitorLastLogUpDownDelayUpMax
         Integer32,
      pr1646v2PbbEthOamEQualityMonitorLastLogUpDownJitterUpNegMax
         Integer32,
      pr1646v2PbbEthOamEQualityMonitorLastLogUpDownJitterUpAvrg
         Integer32,
      pr1646v2PbbEthOamEQualityMonitorLastLogUpDownJitterUpPosMax
         Integer32,
      pr1646v2PbbEthOamEQualityMonitorLastLogUpDownLossDown
         Counter32,
      pr1646v2PbbEthOamEQualityMonitorLastLogUpDownLossDelayDown
         Counter32,
      pr1646v2PbbEthOamEQualityMonitorLastLogUpDownDelayDownMin
         Integer32,
      pr1646v2PbbEthOamEQualityMonitorLastLogUpDownDelayDownAvrg
         Integer32,
      pr1646v2PbbEthOamEQualityMonitorLastLogUpDownDelayDownMax
         Integer32,
      pr1646v2PbbEthOamEQualityMonitorLastLogUpDownJitterDownNegMax
         Integer32,
      pr1646v2PbbEthOamEQualityMonitorLastLogUpDownJitterDownAvrg
         Integer32,
      pr1646v2PbbEthOamEQualityMonitorLastLogUpDownJitterDownPosMax
         Integer32,
      pr1646v2PbbEthOamEQualityMonitorLastLogDate
         DisplayString,
      pr1646v2PbbEthOamEQualityMonitorAlarm
         Integer32
      }

pr1646v2PbbEthOamEQualityMonitorGlobalIx OBJECT-TYPE
   SYNTAX      GlobalIndex
   MAX-ACCESS  not-accessible
   STATUS      current
   DESCRIPTION
      "The value of the tlsCntTreeGlobalIndex of the MANAGED OBJECT."
   ::= {pr1646v2PbbEthOamEQualityMonitorEntry 10}

pr1646v2PbbEthOamEQualityMonitorTableIx OBJECT-TYPE
   SYNTAX      TableIndex
   MAX-ACCESS  not-accessible
   STATUS      current
   DESCRIPTION
      ""
   ::= {pr1646v2PbbEthOamEQualityMonitorEntry 11}

pr1646v2PbbEthOamEQualityMonitorName OBJECT-TYPE
   SYNTAX      DisplayString
   MAX-ACCESS  read-only
   STATUS      current
   DESCRIPTION
      "Path: ethOam.performance.qualityMonitor.name"
   ::= {pr1646v2PbbEthOamEQualityMonitorEntry 385875968}

pr1646v2PbbEthOamEQualityMonitorStatus OBJECT-TYPE
   SYNTAX      INTEGER
               {
               run (1),
               runOnDemand (3),
               halted (2),
               cleared (6),
               disabled (8),
               runIdle (9)
               }
   MAX-ACCESS  read-only
   STATUS      current
   DESCRIPTION
      "Path: ethOam.performance.qualityMonitor.status

       Possibilities:
               run   (1)
               runOnDemand   (3)
               halted   (2)
               cleared   (6)
               disabled   (8)
               runIdle   (9)"
   ::= {pr1646v2PbbEthOamEQualityMonitorEntry 402653184}

pr1646v2PbbEthOamEQualityMonitorMepName OBJECT-TYPE
   SYNTAX      DisplayString
   MAX-ACCESS  read-only
   STATUS      current
   DESCRIPTION
      "Path: ethOam.performance.qualityMonitor.mepName"
   ::= {pr1646v2PbbEthOamEQualityMonitorEntry 16777216}

pr1646v2PbbEthOamEQualityMonitorMegLevel OBJECT-TYPE
   SYNTAX      Integer32
   MAX-ACCESS  read-only
   STATUS      current
   DESCRIPTION
      "Path: ethOam.performance.qualityMonitor.megLevel"
   ::= {pr1646v2PbbEthOamEQualityMonitorEntry 33554432}

pr1646v2PbbEthOamEQualityMonitorMegIdMaintDomainName OBJECT-TYPE
   SYNTAX      DisplayString
   MAX-ACCESS  read-only
   STATUS      current
   DESCRIPTION
      "Path: ethOam.performance.qualityMonitor.megId.maintDomainName"
   ::= {pr1646v2PbbEthOamEQualityMonitorEntry 50397184}

pr1646v2PbbEthOamEQualityMonitorMegIdShortMaName OBJECT-TYPE
   SYNTAX      DisplayString
   MAX-ACCESS  read-only
   STATUS      current
   DESCRIPTION
      "Path: ethOam.performance.qualityMonitor.megId.shortMaName"
   ::= {pr1646v2PbbEthOamEQualityMonitorEntry 50462720}

pr1646v2PbbEthOamEQualityMonitorMepId OBJECT-TYPE
   SYNTAX      INTEGER
               {
               unknown (8192)
               }
   MAX-ACCESS  read-only
   STATUS      current
   DESCRIPTION
      "Path: ethOam.performance.qualityMonitor.mepId

       Possibilities:
               unknown   (8192)"
   ::= {pr1646v2PbbEthOamEQualityMonitorEntry 67108864}

pr1646v2PbbEthOamEQualityMonitorMacAddress OBJECT-TYPE
   SYNTAX      OCTET STRING
   MAX-ACCESS  read-only
   STATUS      current
   DESCRIPTION
      "Path: ethOam.performance.qualityMonitor.macAddress

       MAC address."
   ::= {pr1646v2PbbEthOamEQualityMonitorEntry 83886080}

pr1646v2PbbEthOamEQualityMonitorPriority OBJECT-TYPE
   SYNTAX      Integer32
   MAX-ACCESS  read-only
   STATUS      current
   DESCRIPTION
      "Path: ethOam.performance.qualityMonitor.priority"
   ::= {pr1646v2PbbEthOamEQualityMonitorEntry 100663296}

pr1646v2PbbEthOamEQualityMonitorType OBJECT-TYPE
   SYNTAX      INTEGER
               {
               loopback (4),
               synthLoss (6),
               delay (7)
               }
   MAX-ACCESS  read-only
   STATUS      current
   DESCRIPTION
      "Path: ethOam.performance.qualityMonitor.type

       Possibilities:
               loopback   (4)
               synthLoss   (6)
               delay   (7)"
   ::= {pr1646v2PbbEthOamEQualityMonitorEntry 520093696}

pr1646v2PbbEthOamEQualityMonitorNbrTxPckt OBJECT-TYPE
   SYNTAX      Counter32
   MAX-ACCESS  read-only
   STATUS      current
   DESCRIPTION
      "Path: ethOam.performance.qualityMonitor.nbrOfTxPackets

       32 bit unsigned wrappable counter."
   ::= {pr1646v2PbbEthOamEQualityMonitorEntry 117440512}

pr1646v2PbbEthOamEQualityMonitorNbrRxPckt OBJECT-TYPE
   SYNTAX      Counter32
   MAX-ACCESS  read-only
   STATUS      current
   DESCRIPTION
      "Path: ethOam.performance.qualityMonitor.nbrOfRxPackets

       32 bit unsigned wrappable counter."
   ::= {pr1646v2PbbEthOamEQualityMonitorEntry 134217728}

pr1646v2PbbEthOamEQualityMonitorError OBJECT-TYPE
   SYNTAX      Counter32
   MAX-ACCESS  read-only
   STATUS      current
   DESCRIPTION
      "Path: ethOam.performance.qualityMonitor.error

       32 bit unsigned wrappable counter."
   ::= {pr1646v2PbbEthOamEQualityMonitorEntry 150994944}

pr1646v2PbbEthOamEQualityMonitorDelay OBJECT-TYPE
   SYNTAX      Integer32
   MAX-ACCESS  read-only
   STATUS      current
   DESCRIPTION
      "Path: ethOam.performance.qualityMonitor.delay

       unit name = sec
       formula = 1000 / ; 1000 *"
   ::= {pr1646v2PbbEthOamEQualityMonitorEntry 167772160}

pr1646v2PbbEthOamEQualityMonitorJitter OBJECT-TYPE
   SYNTAX      Integer32
   MAX-ACCESS  read-only
   STATUS      current
   DESCRIPTION
      "Path: ethOam.performance.qualityMonitor.jitter

       unit name = sec
       formula = 1000 / ; 1000 *"
   ::= {pr1646v2PbbEthOamEQualityMonitorEntry 184549376}

pr1646v2PbbEthOamEQualityMonitorLoss OBJECT-TYPE
   SYNTAX      Counter32
   MAX-ACCESS  read-only
   STATUS      current
   DESCRIPTION
      "Path: ethOam.performance.qualityMonitor.loss

       32 bit unsigned wrappable counter."
   ::= {pr1646v2PbbEthOamEQualityMonitorEntry 201326592}

pr1646v2PbbEthOamEQualityMonitorLossDelay OBJECT-TYPE
   SYNTAX      Counter32
   MAX-ACCESS  read-only
   STATUS      current
   DESCRIPTION
      "Path: ethOam.performance.qualityMonitor.lossDelay

       32 bit unsigned wrappable counter."
   ::= {pr1646v2PbbEthOamEQualityMonitorEntry 218103808}

pr1646v2PbbEthOamEQualityMonitorDelayMin OBJECT-TYPE
   SYNTAX      Integer32
   MAX-ACCESS  read-only
   STATUS      current
   DESCRIPTION
      "Path: ethOam.performance.qualityMonitor.delayMin

       unit name = sec
       formula = 1000 / ; 1000 *"
   ::= {pr1646v2PbbEthOamEQualityMonitorEntry 234881024}

pr1646v2PbbEthOamEQualityMonitorDelayAvrg OBJECT-TYPE
   SYNTAX      Integer32
   MAX-ACCESS  read-only
   STATUS      current
   DESCRIPTION
      "Path: ethOam.performance.qualityMonitor.delayAvrg

       unit name = sec
       formula = 1000 / ; 1000 *"
   ::= {pr1646v2PbbEthOamEQualityMonitorEntry 251658240}

pr1646v2PbbEthOamEQualityMonitorDelayMax OBJECT-TYPE
   SYNTAX      Integer32
   MAX-ACCESS  read-only
   STATUS      current
   DESCRIPTION
      "Path: ethOam.performance.qualityMonitor.delayMax

       unit name = sec
       formula = 1000 / ; 1000 *"
   ::= {pr1646v2PbbEthOamEQualityMonitorEntry 268435456}

pr1646v2PbbEthOamEQualityMonitorDelayBinsType OBJECT-TYPE
   SYNTAX      INTEGER
               {
               fd (1),
               fdr (2),
               notInUse (3),
               ifdv (4)
               }
   MAX-ACCESS  read-only
   STATUS      current
   DESCRIPTION
      "Path: ethOam.performance.qualityMonitor.delayBins.type

       Possibilities:
               fd   (1)
               fdr   (2)
               notInUse   (3)
               ifdv   (4)"
   ::= {pr1646v2PbbEthOamEQualityMonitorEntry 420937728}

pr1646v2PbbEthOamEQualityMonitorDelayBinsMinMin OBJECT-TYPE
   SYNTAX      Counter32
   MAX-ACCESS  read-only
   STATUS      current
   DESCRIPTION
      "Path: ethOam.performance.qualityMonitor.delayBins.minMin

       32 bit unsigned wrappable counter."
   ::= {pr1646v2PbbEthOamEQualityMonitorEntry 419495936}

pr1646v2PbbEthOamEQualityMonitorDelayBinsMin OBJECT-TYPE
   SYNTAX      Integer32
   MAX-ACCESS  read-only
   STATUS      current
   DESCRIPTION
      "Path: ethOam.performance.qualityMonitor.delayBins.min

       unit name = sec
       formula = 1000 / ; 1000 *"
   ::= {pr1646v2PbbEthOamEQualityMonitorEntry 420806656}

pr1646v2PbbEthOamEQualityMonitorDelayBinsMinBin1 OBJECT-TYPE
   SYNTAX      Counter32
   MAX-ACCESS  read-only
   STATUS      current
   DESCRIPTION
      "Path: ethOam.performance.qualityMonitor.delayBins.minBin1

       32 bit unsigned wrappable counter."
   ::= {pr1646v2PbbEthOamEQualityMonitorEntry 419561472}

pr1646v2PbbEthOamEQualityMonitorDelayBinsBin2 OBJECT-TYPE
   SYNTAX      Counter32
   MAX-ACCESS  read-only
   STATUS      current
   DESCRIPTION
      "Path: ethOam.performance.qualityMonitor.delayBins.bin2

       32 bit unsigned wrappable counter."
   ::= {pr1646v2PbbEthOamEQualityMonitorEntry 419627008}

pr1646v2PbbEthOamEQualityMonitorDelayBinsBin3 OBJECT-TYPE
   SYNTAX      Counter32
   MAX-ACCESS  read-only
   STATUS      current
   DESCRIPTION
      "Path: ethOam.performance.qualityMonitor.delayBins.bin3

       32 bit unsigned wrappable counter."
   ::= {pr1646v2PbbEthOamEQualityMonitorEntry 419692544}

pr1646v2PbbEthOamEQualityMonitorDelayBinsBin4 OBJECT-TYPE
   SYNTAX      Counter32
   MAX-ACCESS  read-only
   STATUS      current
   DESCRIPTION
      "Path: ethOam.performance.qualityMonitor.delayBins.bin4

       32 bit unsigned wrappable counter."
   ::= {pr1646v2PbbEthOamEQualityMonitorEntry 419758080}

pr1646v2PbbEthOamEQualityMonitorDelayBinsBin5 OBJECT-TYPE
   SYNTAX      Counter32
   MAX-ACCESS  read-only
   STATUS      current
   DESCRIPTION
      "Path: ethOam.performance.qualityMonitor.delayBins.bin5

       32 bit unsigned wrappable counter."
   ::= {pr1646v2PbbEthOamEQualityMonitorEntry 419823616}

pr1646v2PbbEthOamEQualityMonitorDelayBinsBin6 OBJECT-TYPE
   SYNTAX      Counter32
   MAX-ACCESS  read-only
   STATUS      current
   DESCRIPTION
      "Path: ethOam.performance.qualityMonitor.delayBins.bin6

       32 bit unsigned wrappable counter."
   ::= {pr1646v2PbbEthOamEQualityMonitorEntry 419889152}

pr1646v2PbbEthOamEQualityMonitorDelayBinsBin7 OBJECT-TYPE
   SYNTAX      Counter32
   MAX-ACCESS  read-only
   STATUS      current
   DESCRIPTION
      "Path: ethOam.performance.qualityMonitor.delayBins.bin7

       32 bit unsigned wrappable counter."
   ::= {pr1646v2PbbEthOamEQualityMonitorEntry 419954688}

pr1646v2PbbEthOamEQualityMonitorDelayBinsMaxBin8 OBJECT-TYPE
   SYNTAX      Counter32
   MAX-ACCESS  read-only
   STATUS      current
   DESCRIPTION
      "Path: ethOam.performance.qualityMonitor.delayBins.maxBin8

       32 bit unsigned wrappable counter."
   ::= {pr1646v2PbbEthOamEQualityMonitorEntry 420020224}

pr1646v2PbbEthOamEQualityMonitorDelayBinsMax OBJECT-TYPE
   SYNTAX      Integer32
   MAX-ACCESS  read-only
   STATUS      current
   DESCRIPTION
      "Path: ethOam.performance.qualityMonitor.delayBins.max

       unit name = sec
       formula = 1000 / ; 1000 *"
   ::= {pr1646v2PbbEthOamEQualityMonitorEntry 420872192}

pr1646v2PbbEthOamEQualityMonitorDelayBinsPlusMax OBJECT-TYPE
   SYNTAX      Counter32
   MAX-ACCESS  read-only
   STATUS      current
   DESCRIPTION
      "Path: ethOam.performance.qualityMonitor.delayBins.plusMax

       32 bit unsigned wrappable counter."
   ::= {pr1646v2PbbEthOamEQualityMonitorEntry 420085760}

pr1646v2PbbEthOamEQualityMonitorJitterNegMax OBJECT-TYPE
   SYNTAX      Integer32
   MAX-ACCESS  read-only
   STATUS      current
   DESCRIPTION
      "Path: ethOam.performance.qualityMonitor.jitterNegMax

       unit name = sec
       formula = 1000 / ; 1000 *"
   ::= {pr1646v2PbbEthOamEQualityMonitorEntry 285212672}

pr1646v2PbbEthOamEQualityMonitorJitterAvrg OBJECT-TYPE
   SYNTAX      Integer32
   MAX-ACCESS  read-only
   STATUS      current
   DESCRIPTION
      "Path: ethOam.performance.qualityMonitor.jitterAvrg

       unit name = sec
       formula = 1000 / ; 1000 *"
   ::= {pr1646v2PbbEthOamEQualityMonitorEntry 301989888}

pr1646v2PbbEthOamEQualityMonitorJitterPosMax OBJECT-TYPE
   SYNTAX      Integer32
   MAX-ACCESS  read-only
   STATUS      current
   DESCRIPTION
      "Path: ethOam.performance.qualityMonitor.jitterPosMax

       unit name = sec
       formula = 1000 / ; 1000 *"
   ::= {pr1646v2PbbEthOamEQualityMonitorEntry 318767104}

pr1646v2PbbEthOamEQualityMonitorJitterBinsType OBJECT-TYPE
   SYNTAX      INTEGER
               {
               fd (1),
               fdr (2),
               notInUse (3),
               ifdv (4)
               }
   MAX-ACCESS  read-only
   STATUS      current
   DESCRIPTION
      "Path: ethOam.performance.qualityMonitor.jitterBins.type

       Possibilities:
               fd   (1)
               fdr   (2)
               notInUse   (3)
               ifdv   (4)"
   ::= {pr1646v2PbbEthOamEQualityMonitorEntry 437714944}

pr1646v2PbbEthOamEQualityMonitorJitterBinsMinMin OBJECT-TYPE
   SYNTAX      Counter32
   MAX-ACCESS  read-only
   STATUS      current
   DESCRIPTION
      "Path: ethOam.performance.qualityMonitor.jitterBins.minMin

       32 bit unsigned wrappable counter."
   ::= {pr1646v2PbbEthOamEQualityMonitorEntry 436273152}

pr1646v2PbbEthOamEQualityMonitorJitterBinsMin OBJECT-TYPE
   SYNTAX      Integer32
   MAX-ACCESS  read-only
   STATUS      current
   DESCRIPTION
      "Path: ethOam.performance.qualityMonitor.jitterBins.min

       unit name = sec
       formula = 1000 / ; 1000 *"
   ::= {pr1646v2PbbEthOamEQualityMonitorEntry 437583872}

pr1646v2PbbEthOamEQualityMonitorJitterBinsMinBin1 OBJECT-TYPE
   SYNTAX      Counter32
   MAX-ACCESS  read-only
   STATUS      current
   DESCRIPTION
      "Path: ethOam.performance.qualityMonitor.jitterBins.minBin1

       32 bit unsigned wrappable counter."
   ::= {pr1646v2PbbEthOamEQualityMonitorEntry 436338688}

pr1646v2PbbEthOamEQualityMonitorJitterBinsBin2 OBJECT-TYPE
   SYNTAX      Counter32
   MAX-ACCESS  read-only
   STATUS      current
   DESCRIPTION
      "Path: ethOam.performance.qualityMonitor.jitterBins.bin2

       32 bit unsigned wrappable counter."
   ::= {pr1646v2PbbEthOamEQualityMonitorEntry 436404224}

pr1646v2PbbEthOamEQualityMonitorJitterBinsBin3 OBJECT-TYPE
   SYNTAX      Counter32
   MAX-ACCESS  read-only
   STATUS      current
   DESCRIPTION
      "Path: ethOam.performance.qualityMonitor.jitterBins.bin3

       32 bit unsigned wrappable counter."
   ::= {pr1646v2PbbEthOamEQualityMonitorEntry 436469760}

pr1646v2PbbEthOamEQualityMonitorJitterBinsBin4 OBJECT-TYPE
   SYNTAX      Counter32
   MAX-ACCESS  read-only
   STATUS      current
   DESCRIPTION
      "Path: ethOam.performance.qualityMonitor.jitterBins.bin4

       32 bit unsigned wrappable counter."
   ::= {pr1646v2PbbEthOamEQualityMonitorEntry 436535296}

pr1646v2PbbEthOamEQualityMonitorJitterBinsBin5 OBJECT-TYPE
   SYNTAX      Counter32
   MAX-ACCESS  read-only
   STATUS      current
   DESCRIPTION
      "Path: ethOam.performance.qualityMonitor.jitterBins.bin5

       32 bit unsigned wrappable counter."
   ::= {pr1646v2PbbEthOamEQualityMonitorEntry 436600832}

pr1646v2PbbEthOamEQualityMonitorJitterBinsBin6 OBJECT-TYPE
   SYNTAX      Counter32
   MAX-ACCESS  read-only
   STATUS      current
   DESCRIPTION
      "Path: ethOam.performance.qualityMonitor.jitterBins.bin6

       32 bit unsigned wrappable counter."
   ::= {pr1646v2PbbEthOamEQualityMonitorEntry 436666368}

pr1646v2PbbEthOamEQualityMonitorJitterBinsBin7 OBJECT-TYPE
   SYNTAX      Counter32
   MAX-ACCESS  read-only
   STATUS      current
   DESCRIPTION
      "Path: ethOam.performance.qualityMonitor.jitterBins.bin7

       32 bit unsigned wrappable counter."
   ::= {pr1646v2PbbEthOamEQualityMonitorEntry 436731904}

pr1646v2PbbEthOamEQualityMonitorJitterBinsMaxBin8 OBJECT-TYPE
   SYNTAX      Counter32
   MAX-ACCESS  read-only
   STATUS      current
   DESCRIPTION
      "Path: ethOam.performance.qualityMonitor.jitterBins.maxBin8

       32 bit unsigned wrappable counter."
   ::= {pr1646v2PbbEthOamEQualityMonitorEntry 436797440}

pr1646v2PbbEthOamEQualityMonitorJitterBinsMax OBJECT-TYPE
   SYNTAX      Integer32
   MAX-ACCESS  read-only
   STATUS      current
   DESCRIPTION
      "Path: ethOam.performance.qualityMonitor.jitterBins.max

       unit name = sec
       formula = 1000 / ; 1000 *"
   ::= {pr1646v2PbbEthOamEQualityMonitorEntry 437649408}

pr1646v2PbbEthOamEQualityMonitorJitterBinsPlusMax OBJECT-TYPE
   SYNTAX      Counter32
   MAX-ACCESS  read-only
   STATUS      current
   DESCRIPTION
      "Path: ethOam.performance.qualityMonitor.jitterBins.plusMax

       32 bit unsigned wrappable counter."
   ::= {pr1646v2PbbEthOamEQualityMonitorEntry 436862976}

pr1646v2PbbEthOamEQualityMonitorUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: ethOam.performance.qualityMonitor.upDown.status

       Possibilities:
               notInUse   (3)
               onlyJitter   (1)
               jitterAndLoss   (2)
               all   (4)
               onlyLoss   (8)"
   ::= {pr1646v2PbbEthOamEQualityMonitorEntry 504627200}

pr1646v2PbbEthOamEQualityMonitorUpDownLossUp OBJECT-TYPE
   SYNTAX      Counter32
   MAX-ACCESS  read-only
   STATUS      current
   DESCRIPTION
      "Path: ethOam.performance.qualityMonitor.upDown.lossUp

       32 bit unsigned wrappable counter."
   ::= {pr1646v2PbbEthOamEQualityMonitorEntry 503971840}

pr1646v2PbbEthOamEQualityMonitorUpDownLossDelayUp OBJECT-TYPE
   SYNTAX      Counter32
   MAX-ACCESS  read-only
   STATUS      current
   DESCRIPTION
      "Path: ethOam.performance.qualityMonitor.upDown.lossDelayUp

       32 bit unsigned wrappable counter."
   ::= {pr1646v2PbbEthOamEQualityMonitorEntry 504037376}

pr1646v2PbbEthOamEQualityMonitorUpDownDelayUpMin OBJECT-TYPE
   SYNTAX      Integer32
   MAX-ACCESS  read-only
   STATUS      current
   DESCRIPTION
      "Path: ethOam.performance.qualityMonitor.upDown.delayUpMin

       unit name = sec
       formula = 1000 / ; 1000 *"
   ::= {pr1646v2PbbEthOamEQualityMonitorEntry 505282560}

pr1646v2PbbEthOamEQualityMonitorUpDownDelayUpAvrg OBJECT-TYPE
   SYNTAX      Integer32
   MAX-ACCESS  read-only
   STATUS      current
   DESCRIPTION
      "Path: ethOam.performance.qualityMonitor.upDown.delayUpAvrg

       unit name = sec
       formula = 1000 / ; 1000 *"
   ::= {pr1646v2PbbEthOamEQualityMonitorEntry 505348096}

pr1646v2PbbEthOamEQualityMonitorUpDownDelayUpMax OBJECT-TYPE
   SYNTAX      Integer32
   MAX-ACCESS  read-only
   STATUS      current
   DESCRIPTION
      "Path: ethOam.performance.qualityMonitor.upDown.delayUpMax

       unit name = sec
       formula = 1000 / ; 1000 *"
   ::= {pr1646v2PbbEthOamEQualityMonitorEntry 505413632}

pr1646v2PbbEthOamEQualityMonitorUpDownDelayUpBinsType OBJECT-TYPE
   SYNTAX      INTEGER
               {
               fd (1),
               fdr (2),
               notInUse (3),
               ifdv (4)
               }
   MAX-ACCESS  read-only
   STATUS      current
   DESCRIPTION
      "Path: ethOam.performance.qualityMonitor.upDown.delayUpBins.type

       Possibilities:
               fd   (1)
               fdr   (2)
               notInUse   (3)
               ifdv   (4)"
   ::= {pr1646v2PbbEthOamEQualityMonitorEntry 505943808}

pr1646v2PbbEthOamEQualityMonitorUpDownDelayUpBinsMinMin OBJECT-TYPE
   SYNTAX      Counter32
   MAX-ACCESS  read-only
   STATUS      current
   DESCRIPTION
      "Path: ethOam.performance.qualityMonitor.upDown.delayUpBins.minMin

       32 bit unsigned wrappable counter."
   ::= {pr1646v2PbbEthOamEQualityMonitorEntry 505938176}

pr1646v2PbbEthOamEQualityMonitorUpDownDelayUpBinsMin OBJECT-TYPE
   SYNTAX      Integer32
   MAX-ACCESS  read-only
   STATUS      current
   DESCRIPTION
      "Path: ethOam.performance.qualityMonitor.upDown.delayUpBins.min

       unit name = sec
       formula = 1000 / ; 1000 *"
   ::= {pr1646v2PbbEthOamEQualityMonitorEntry 505943296}

pr1646v2PbbEthOamEQualityMonitorUpDownDelayUpBinsMinBin1 OBJECT-TYPE
   SYNTAX      Counter32
   MAX-ACCESS  read-only
   STATUS      current
   DESCRIPTION
      "Path: ethOam.performance.qualityMonitor.upDown.delayUpBins.minBin1

       32 bit unsigned wrappable counter."
   ::= {pr1646v2PbbEthOamEQualityMonitorEntry 505938432}

pr1646v2PbbEthOamEQualityMonitorUpDownDelayUpBinsBin2 OBJECT-TYPE
   SYNTAX      Counter32
   MAX-ACCESS  read-only
   STATUS      current
   DESCRIPTION
      "Path: ethOam.performance.qualityMonitor.upDown.delayUpBins.bin2

       32 bit unsigned wrappable counter."
   ::= {pr1646v2PbbEthOamEQualityMonitorEntry 505938688}

pr1646v2PbbEthOamEQualityMonitorUpDownDelayUpBinsBin3 OBJECT-TYPE
   SYNTAX      Counter32
   MAX-ACCESS  read-only
   STATUS      current
   DESCRIPTION
      "Path: ethOam.performance.qualityMonitor.upDown.delayUpBins.bin3

       32 bit unsigned wrappable counter."
   ::= {pr1646v2PbbEthOamEQualityMonitorEntry 505938944}

pr1646v2PbbEthOamEQualityMonitorUpDownDelayUpBinsBin4 OBJECT-TYPE
   SYNTAX      Counter32
   MAX-ACCESS  read-only
   STATUS      current
   DESCRIPTION
      "Path: ethOam.performance.qualityMonitor.upDown.delayUpBins.bin4

       32 bit unsigned wrappable counter."
   ::= {pr1646v2PbbEthOamEQualityMonitorEntry 505939200}

pr1646v2PbbEthOamEQualityMonitorUpDownDelayUpBinsBin5 OBJECT-TYPE
   SYNTAX      Counter32
   MAX-ACCESS  read-only
   STATUS      current
   DESCRIPTION
      "Path: ethOam.performance.qualityMonitor.upDown.delayUpBins.bin5

       32 bit unsigned wrappable counter."
   ::= {pr1646v2PbbEthOamEQualityMonitorEntry 505939456}

pr1646v2PbbEthOamEQualityMonitorUpDownDelayUpBinsBin6 OBJECT-TYPE
   SYNTAX      Counter32
   MAX-ACCESS  read-only
   STATUS      current
   DESCRIPTION
      "Path: ethOam.performance.qualityMonitor.upDown.delayUpBins.bin6

       32 bit unsigned wrappable counter."
   ::= {pr1646v2PbbEthOamEQualityMonitorEntry 505939712}

pr1646v2PbbEthOamEQualityMonitorUpDownDelayUpBinsBin7 OBJECT-TYPE
   SYNTAX      Counter32
   MAX-ACCESS  read-only
   STATUS      current
   DESCRIPTION
      "Path: ethOam.performance.qualityMonitor.upDown.delayUpBins.bin7

       32 bit unsigned wrappable counter."
   ::= {pr1646v2PbbEthOamEQualityMonitorEntry 505939968}

pr1646v2PbbEthOamEQualityMonitorUpDownDelayUpBinsMaxBin8 OBJECT-TYPE
   SYNTAX      Counter32
   MAX-ACCESS  read-only
   STATUS      current
   DESCRIPTION
      "Path: ethOam.performance.qualityMonitor.upDown.delayUpBins.maxBin8

       32 bit unsigned wrappable counter."
   ::= {pr1646v2PbbEthOamEQualityMonitorEntry 505940224}

pr1646v2PbbEthOamEQualityMonitorUpDownDelayUpBinsMax OBJECT-TYPE
   SYNTAX      Integer32
   MAX-ACCESS  read-only
   STATUS      current
   DESCRIPTION
      "Path: ethOam.performance.qualityMonitor.upDown.delayUpBins.max

       unit name = sec
       formula = 1000 / ; 1000 *"
   ::= {pr1646v2PbbEthOamEQualityMonitorEntry 505943552}

pr1646v2PbbEthOamEQualityMonitorUpDownDelayUpBinsPlusMax OBJECT-TYPE
   SYNTAX      Counter32
   MAX-ACCESS  read-only
   STATUS      current
   DESCRIPTION
      "Path: ethOam.performance.qualityMonitor.upDown.delayUpBins.plusMax

       32 bit unsigned wrappable counter."
   ::= {pr1646v2PbbEthOamEQualityMonitorEntry 505940480}

pr1646v2PbbEthOamEQualityMonitorUpDownJitterUp OBJECT-TYPE
   SYNTAX      Integer32
   MAX-ACCESS  read-only
   STATUS      current
   DESCRIPTION
      "Path: ethOam.performance.qualityMonitor.upDown.jitterUp

       unit name = sec
       formula = 1000 / ; 1000 *"
   ::= {pr1646v2PbbEthOamEQualityMonitorEntry 503775232}

pr1646v2PbbEthOamEQualityMonitorUpDownJitterUpNegMax OBJECT-TYPE
   SYNTAX      Integer32
   MAX-ACCESS  read-only
   STATUS      current
   DESCRIPTION
      "Path: ethOam.performance.qualityMonitor.upDown.jitterUpNegMax

       unit name = sec
       formula = 1000 / ; 1000 *"
   ::= {pr1646v2PbbEthOamEQualityMonitorEntry 503382016}

pr1646v2PbbEthOamEQualityMonitorUpDownJitterUpAvrg OBJECT-TYPE
   SYNTAX      Integer32
   MAX-ACCESS  read-only
   STATUS      current
   DESCRIPTION
      "Path: ethOam.performance.qualityMonitor.upDown.jitterUpAvrg

       unit name = sec
       formula = 1000 / ; 1000 *"
   ::= {pr1646v2PbbEthOamEQualityMonitorEntry 503447552}

pr1646v2PbbEthOamEQualityMonitorUpDownJitterUpPosMax OBJECT-TYPE
   SYNTAX      Integer32
   MAX-ACCESS  read-only
   STATUS      current
   DESCRIPTION
      "Path: ethOam.performance.qualityMonitor.upDown.jitterUpPosMax

       unit name = sec
       formula = 1000 / ; 1000 *"
   ::= {pr1646v2PbbEthOamEQualityMonitorEntry 503513088}

pr1646v2PbbEthOamEQualityMonitorUpDownJitterUpBinsType OBJECT-TYPE
   SYNTAX      INTEGER
               {
               fd (1),
               fdr (2),
               notInUse (3),
               ifdv (4)
               }
   MAX-ACCESS  read-only
   STATUS      current
   DESCRIPTION
      "Path: ethOam.performance.qualityMonitor.upDown.jitterUpBins.type

       Possibilities:
               fd   (1)
               fdr   (2)
               notInUse   (3)
               ifdv   (4)"
   ::= {pr1646v2PbbEthOamEQualityMonitorEntry 506074880}

pr1646v2PbbEthOamEQualityMonitorUpDownJitterUpBinsMinMin OBJECT-TYPE
   SYNTAX      Counter32
   MAX-ACCESS  read-only
   STATUS      current
   DESCRIPTION
      "Path: ethOam.performance.qualityMonitor.upDown.jitterUpBins.minMin

       32 bit unsigned wrappable counter."
   ::= {pr1646v2PbbEthOamEQualityMonitorEntry 506069248}

pr1646v2PbbEthOamEQualityMonitorUpDownJitterUpBinsMin OBJECT-TYPE
   SYNTAX      Integer32
   MAX-ACCESS  read-only
   STATUS      current
   DESCRIPTION
      "Path: ethOam.performance.qualityMonitor.upDown.jitterUpBins.min

       unit name = sec
       formula = 1000 / ; 1000 *"
   ::= {pr1646v2PbbEthOamEQualityMonitorEntry 506074368}

pr1646v2PbbEthOamEQualityMonitorUpDownJitterUpBinsMinBin1 OBJECT-TYPE
   SYNTAX      Counter32
   MAX-ACCESS  read-only
   STATUS      current
   DESCRIPTION
      "Path: ethOam.performance.qualityMonitor.upDown.jitterUpBins.minBin1

       32 bit unsigned wrappable counter."
   ::= {pr1646v2PbbEthOamEQualityMonitorEntry 506069504}

pr1646v2PbbEthOamEQualityMonitorUpDownJitterUpBinsBin2 OBJECT-TYPE
   SYNTAX      Counter32
   MAX-ACCESS  read-only
   STATUS      current
   DESCRIPTION
      "Path: ethOam.performance.qualityMonitor.upDown.jitterUpBins.bin2

       32 bit unsigned wrappable counter."
   ::= {pr1646v2PbbEthOamEQualityMonitorEntry 506069760}

pr1646v2PbbEthOamEQualityMonitorUpDownJitterUpBinsBin3 OBJECT-TYPE
   SYNTAX      Counter32
   MAX-ACCESS  read-only
   STATUS      current
   DESCRIPTION
      "Path: ethOam.performance.qualityMonitor.upDown.jitterUpBins.bin3

       32 bit unsigned wrappable counter."
   ::= {pr1646v2PbbEthOamEQualityMonitorEntry 506070016}

pr1646v2PbbEthOamEQualityMonitorUpDownJitterUpBinsBin4 OBJECT-TYPE
   SYNTAX      Counter32
   MAX-ACCESS  read-only
   STATUS      current
   DESCRIPTION
      "Path: ethOam.performance.qualityMonitor.upDown.jitterUpBins.bin4

       32 bit unsigned wrappable counter."
   ::= {pr1646v2PbbEthOamEQualityMonitorEntry 506070272}

pr1646v2PbbEthOamEQualityMonitorUpDownJitterUpBinsBin5 OBJECT-TYPE
   SYNTAX      Counter32
   MAX-ACCESS  read-only
   STATUS      current
   DESCRIPTION
      "Path: ethOam.performance.qualityMonitor.upDown.jitterUpBins.bin5

       32 bit unsigned wrappable counter."
   ::= {pr1646v2PbbEthOamEQualityMonitorEntry 506070528}

pr1646v2PbbEthOamEQualityMonitorUpDownJitterUpBinsBin6 OBJECT-TYPE
   SYNTAX      Counter32
   MAX-ACCESS  read-only
   STATUS      current
   DESCRIPTION
      "Path: ethOam.performance.qualityMonitor.upDown.jitterUpBins.bin6

       32 bit unsigned wrappable counter."
   ::= {pr1646v2PbbEthOamEQualityMonitorEntry 506070784}

pr1646v2PbbEthOamEQualityMonitorUpDownJitterUpBinsBin7 OBJECT-TYPE
   SYNTAX      Counter32
   MAX-ACCESS  read-only
   STATUS      current
   DESCRIPTION
      "Path: ethOam.performance.qualityMonitor.upDown.jitterUpBins.bin7

       32 bit unsigned wrappable counter."
   ::= {pr1646v2PbbEthOamEQualityMonitorEntry 506071040}

pr1646v2PbbEthOamEQualityMonitorUpDownJitterUpBinsMaxBin8 OBJECT-TYPE
   SYNTAX      Counter32
   MAX-ACCESS  read-only
   STATUS      current
   DESCRIPTION
      "Path: ethOam.performance.qualityMonitor.upDown.jitterUpBins.maxBin8

       32 bit unsigned wrappable counter."
   ::= {pr1646v2PbbEthOamEQualityMonitorEntry 506071296}

pr1646v2PbbEthOamEQualityMonitorUpDownJitterUpBinsMax OBJECT-TYPE
   SYNTAX      Integer32
   MAX-ACCESS  read-only
   STATUS      current
   DESCRIPTION
      "Path: ethOam.performance.qualityMonitor.upDown.jitterUpBins.max

       unit name = sec
       formula = 1000 / ; 1000 *"
   ::= {pr1646v2PbbEthOamEQualityMonitorEntry 506074624}

pr1646v2PbbEthOamEQualityMonitorUpDownJitterUpBinsPlusMax OBJECT-TYPE
   SYNTAX      Counter32
   MAX-ACCESS  read-only
   STATUS      current
   DESCRIPTION
      "Path: ethOam.performance.qualityMonitor.upDown.jitterUpBins.plusMax

       32 bit unsigned wrappable counter."
   ::= {pr1646v2PbbEthOamEQualityMonitorEntry 506071552}

pr1646v2PbbEthOamEQualityMonitorUpDownLossDown OBJECT-TYPE
   SYNTAX      Counter32
   MAX-ACCESS  read-only
   STATUS      current
   DESCRIPTION
      "Path: ethOam.performance.qualityMonitor.upDown.lossDown

       32 bit unsigned wrappable counter."
   ::= {pr1646v2PbbEthOamEQualityMonitorEntry 504102912}

pr1646v2PbbEthOamEQualityMonitorUpDownLossDelayDown OBJECT-TYPE
   SYNTAX      Counter32
   MAX-ACCESS  read-only
   STATUS      current
   DESCRIPTION
      "Path: ethOam.performance.qualityMonitor.upDown.lossDelayDown

       32 bit unsigned wrappable counter."
   ::= {pr1646v2PbbEthOamEQualityMonitorEntry 504168448}

pr1646v2PbbEthOamEQualityMonitorUpDownDelayDownMin OBJECT-TYPE
   SYNTAX      Integer32
   MAX-ACCESS  read-only
   STATUS      current
   DESCRIPTION
      "Path: ethOam.performance.qualityMonitor.upDown.delayDownMin

       unit name = sec
       formula = 1000 / ; 1000 *"
   ::= {pr1646v2PbbEthOamEQualityMonitorEntry 505610240}

pr1646v2PbbEthOamEQualityMonitorUpDownDelayDownAvrg OBJECT-TYPE
   SYNTAX      Integer32
   MAX-ACCESS  read-only
   STATUS      current
   DESCRIPTION
      "Path: ethOam.performance.qualityMonitor.upDown.delayDownAvrg

       unit name = sec
       formula = 1000 / ; 1000 *"
   ::= {pr1646v2PbbEthOamEQualityMonitorEntry 505675776}

pr1646v2PbbEthOamEQualityMonitorUpDownDelayDownMax OBJECT-TYPE
   SYNTAX      Integer32
   MAX-ACCESS  read-only
   STATUS      current
   DESCRIPTION
      "Path: ethOam.performance.qualityMonitor.upDown.delayDownMax

       unit name = sec
       formula = 1000 / ; 1000 *"
   ::= {pr1646v2PbbEthOamEQualityMonitorEntry 505741312}

pr1646v2PbbEthOamEQualityMonitorUpDownDelayDownBinsType OBJECT-TYPE
   SYNTAX      INTEGER
               {
               fd (1),
               fdr (2),
               notInUse (3),
               ifdv (4)
               }
   MAX-ACCESS  read-only
   STATUS      current
   DESCRIPTION
      "Path: ethOam.performance.qualityMonitor.upDown.delayDownBins.type

       Possibilities:
               fd   (1)
               fdr   (2)
               notInUse   (3)
               ifdv   (4)"
   ::= {pr1646v2PbbEthOamEQualityMonitorEntry 506009344}

pr1646v2PbbEthOamEQualityMonitorUpDownDelayDownBinsMinMin OBJECT-TYPE
   SYNTAX      Counter32
   MAX-ACCESS  read-only
   STATUS      current
   DESCRIPTION
      "Path: ethOam.performance.qualityMonitor.upDown.delayDownBins.minMin

       32 bit unsigned wrappable counter."
   ::= {pr1646v2PbbEthOamEQualityMonitorEntry 506003712}

pr1646v2PbbEthOamEQualityMonitorUpDownDelayDownBinsMin OBJECT-TYPE
   SYNTAX      Integer32
   MAX-ACCESS  read-only
   STATUS      current
   DESCRIPTION
      "Path: ethOam.performance.qualityMonitor.upDown.delayDownBins.min

       unit name = sec
       formula = 1000 / ; 1000 *"
   ::= {pr1646v2PbbEthOamEQualityMonitorEntry 506008832}

pr1646v2PbbEthOamEQualityMonitorUpDownDelayDownBinsMinBin1 OBJECT-TYPE
   SYNTAX      Counter32
   MAX-ACCESS  read-only
   STATUS      current
   DESCRIPTION
      "Path: ethOam.performance.qualityMonitor.upDown.delayDownBins.minBin1

       32 bit unsigned wrappable counter."
   ::= {pr1646v2PbbEthOamEQualityMonitorEntry 506003968}

pr1646v2PbbEthOamEQualityMonitorUpDownDelayDownBinsBin2 OBJECT-TYPE
   SYNTAX      Counter32
   MAX-ACCESS  read-only
   STATUS      current
   DESCRIPTION
      "Path: ethOam.performance.qualityMonitor.upDown.delayDownBins.bin2

       32 bit unsigned wrappable counter."
   ::= {pr1646v2PbbEthOamEQualityMonitorEntry 506004224}

pr1646v2PbbEthOamEQualityMonitorUpDownDelayDownBinsBin3 OBJECT-TYPE
   SYNTAX      Counter32
   MAX-ACCESS  read-only
   STATUS      current
   DESCRIPTION
      "Path: ethOam.performance.qualityMonitor.upDown.delayDownBins.bin3

       32 bit unsigned wrappable counter."
   ::= {pr1646v2PbbEthOamEQualityMonitorEntry 506004480}

pr1646v2PbbEthOamEQualityMonitorUpDownDelayDownBinsBin4 OBJECT-TYPE
   SYNTAX      Counter32
   MAX-ACCESS  read-only
   STATUS      current
   DESCRIPTION
      "Path: ethOam.performance.qualityMonitor.upDown.delayDownBins.bin4

       32 bit unsigned wrappable counter."
   ::= {pr1646v2PbbEthOamEQualityMonitorEntry 506004736}

pr1646v2PbbEthOamEQualityMonitorUpDownDelayDownBinsBin5 OBJECT-TYPE
   SYNTAX      Counter32
   MAX-ACCESS  read-only
   STATUS      current
   DESCRIPTION
      "Path: ethOam.performance.qualityMonitor.upDown.delayDownBins.bin5

       32 bit unsigned wrappable counter."
   ::= {pr1646v2PbbEthOamEQualityMonitorEntry 506004992}

pr1646v2PbbEthOamEQualityMonitorUpDownDelayDownBinsBin6 OBJECT-TYPE
   SYNTAX      Counter32
   MAX-ACCESS  read-only
   STATUS      current
   DESCRIPTION
      "Path: ethOam.performance.qualityMonitor.upDown.delayDownBins.bin6

       32 bit unsigned wrappable counter."
   ::= {pr1646v2PbbEthOamEQualityMonitorEntry 506005248}

pr1646v2PbbEthOamEQualityMonitorUpDownDelayDownBinsBin7 OBJECT-TYPE
   SYNTAX      Counter32
   MAX-ACCESS  read-only
   STATUS      current
   DESCRIPTION
      "Path: ethOam.performance.qualityMonitor.upDown.delayDownBins.bin7

       32 bit unsigned wrappable counter."
   ::= {pr1646v2PbbEthOamEQualityMonitorEntry 506005504}

pr1646v2PbbEthOamEQualityMonitorUpDownDelayDownBinsMaxBin8 OBJECT-TYPE
   SYNTAX      Counter32
   MAX-ACCESS  read-only
   STATUS      current
   DESCRIPTION
      "Path: ethOam.performance.qualityMonitor.upDown.delayDownBins.maxBin8

       32 bit unsigned wrappable counter."
   ::= {pr1646v2PbbEthOamEQualityMonitorEntry 506005760}

pr1646v2PbbEthOamEQualityMonitorUpDownDelayDownBinsMax OBJECT-TYPE
   SYNTAX      Integer32
   MAX-ACCESS  read-only
   STATUS      current
   DESCRIPTION
      "Path: ethOam.performance.qualityMonitor.upDown.delayDownBins.max

       unit name = sec
       formula = 1000 / ; 1000 *"
   ::= {pr1646v2PbbEthOamEQualityMonitorEntry 506009088}

pr1646v2PbbEthOamEQualityMonitorUpDownDelayDownBinsPlusMax OBJECT-TYPE
   SYNTAX      Counter32
   MAX-ACCESS  read-only
   STATUS      current
   DESCRIPTION
      "Path: ethOam.performance.qualityMonitor.upDown.delayDownBins.plusMax

       32 bit unsigned wrappable counter."
   ::= {pr1646v2PbbEthOamEQualityMonitorEntry 506006016}

pr1646v2PbbEthOamEQualityMonitorUpDownJitterDown OBJECT-TYPE
   SYNTAX      Integer32
   MAX-ACCESS  read-only
   STATUS      current
   DESCRIPTION
      "Path: ethOam.performance.qualityMonitor.upDown.jitterDown

       unit name = sec
       formula = 1000 / ; 1000 *"
   ::= {pr1646v2PbbEthOamEQualityMonitorEntry 503840768}

pr1646v2PbbEthOamEQualityMonitorUpDownJitterDownNegMax OBJECT-TYPE
   SYNTAX      Integer32
   MAX-ACCESS  read-only
   STATUS      current
   DESCRIPTION
      "Path: ethOam.performance.qualityMonitor.upDown.jitterDownNegMax

       unit name = sec
       formula = 1000 / ; 1000 *"
   ::= {pr1646v2PbbEthOamEQualityMonitorEntry 503578624}

pr1646v2PbbEthOamEQualityMonitorUpDownJitterDownAvrg OBJECT-TYPE
   SYNTAX      Integer32
   MAX-ACCESS  read-only
   STATUS      current
   DESCRIPTION
      "Path: ethOam.performance.qualityMonitor.upDown.jitterDownAvrg

       unit name = sec
       formula = 1000 / ; 1000 *"
   ::= {pr1646v2PbbEthOamEQualityMonitorEntry 503644160}

pr1646v2PbbEthOamEQualityMonitorUpDownJitterDownPosMax OBJECT-TYPE
   SYNTAX      Integer32
   MAX-ACCESS  read-only
   STATUS      current
   DESCRIPTION
      "Path: ethOam.performance.qualityMonitor.upDown.jitterDownPosMax

       unit name = sec
       formula = 1000 / ; 1000 *"
   ::= {pr1646v2PbbEthOamEQualityMonitorEntry 503709696}

pr1646v2PbbEthOamEQualityMonitorUpDownJitterDownBinsType OBJECT-TYPE
   SYNTAX      INTEGER
               {
               fd (1),
               fdr (2),
               notInUse (3),
               ifdv (4)
               }
   MAX-ACCESS  read-only
   STATUS      current
   DESCRIPTION
      "Path: ethOam.performance.qualityMonitor.upDown.jitterDownBins.type

       Possibilities:
               fd   (1)
               fdr   (2)
               notInUse   (3)
               ifdv   (4)"
   ::= {pr1646v2PbbEthOamEQualityMonitorEntry 506205952}

pr1646v2PbbEthOamEQualityMonitorUpDownJitterDownBinsMinMin OBJECT-TYPE
   SYNTAX      Counter32
   MAX-ACCESS  read-only
   STATUS      current
   DESCRIPTION
      "Path: ethOam.performance.qualityMonitor.upDown.jitterDownBins.minMin

       32 bit unsigned wrappable counter."
   ::= {pr1646v2PbbEthOamEQualityMonitorEntry 506200320}

pr1646v2PbbEthOamEQualityMonitorUpDownJitterDownBinsMin OBJECT-TYPE
   SYNTAX      Integer32
   MAX-ACCESS  read-only
   STATUS      current
   DESCRIPTION
      "Path: ethOam.performance.qualityMonitor.upDown.jitterDownBins.min

       unit name = sec
       formula = 1000 / ; 1000 *"
   ::= {pr1646v2PbbEthOamEQualityMonitorEntry 506205440}

pr1646v2PbbEthOamEQualityMonitorUpDownJitterDownBinsMinBin1 OBJECT-TYPE
   SYNTAX      Counter32
   MAX-ACCESS  read-only
   STATUS      current
   DESCRIPTION
      "Path: ethOam.performance.qualityMonitor.upDown.jitterDownBins.minBin1

       32 bit unsigned wrappable counter."
   ::= {pr1646v2PbbEthOamEQualityMonitorEntry 506200576}

pr1646v2PbbEthOamEQualityMonitorUpDownJitterDownBinsBin2 OBJECT-TYPE
   SYNTAX      Counter32
   MAX-ACCESS  read-only
   STATUS      current
   DESCRIPTION
      "Path: ethOam.performance.qualityMonitor.upDown.jitterDownBins.bin2

       32 bit unsigned wrappable counter."
   ::= {pr1646v2PbbEthOamEQualityMonitorEntry 506200832}

pr1646v2PbbEthOamEQualityMonitorUpDownJitterDownBinsBin3 OBJECT-TYPE
   SYNTAX      Counter32
   MAX-ACCESS  read-only
   STATUS      current
   DESCRIPTION
      "Path: ethOam.performance.qualityMonitor.upDown.jitterDownBins.bin3

       32 bit unsigned wrappable counter."
   ::= {pr1646v2PbbEthOamEQualityMonitorEntry 506201088}

pr1646v2PbbEthOamEQualityMonitorUpDownJitterDownBinsBin4 OBJECT-TYPE
   SYNTAX      Counter32
   MAX-ACCESS  read-only
   STATUS      current
   DESCRIPTION
      "Path: ethOam.performance.qualityMonitor.upDown.jitterDownBins.bin4

       32 bit unsigned wrappable counter."
   ::= {pr1646v2PbbEthOamEQualityMonitorEntry 506201344}

pr1646v2PbbEthOamEQualityMonitorUpDownJitterDownBinsBin5 OBJECT-TYPE
   SYNTAX      Counter32
   MAX-ACCESS  read-only
   STATUS      current
   DESCRIPTION
      "Path: ethOam.performance.qualityMonitor.upDown.jitterDownBins.bin5

       32 bit unsigned wrappable counter."
   ::= {pr1646v2PbbEthOamEQualityMonitorEntry 506201600}

pr1646v2PbbEthOamEQualityMonitorUpDownJitterDownBinsBin6 OBJECT-TYPE
   SYNTAX      Counter32
   MAX-ACCESS  read-only
   STATUS      current
   DESCRIPTION
      "Path: ethOam.performance.qualityMonitor.upDown.jitterDownBins.bin6

       32 bit unsigned wrappable counter."
   ::= {pr1646v2PbbEthOamEQualityMonitorEntry 506201856}

pr1646v2PbbEthOamEQualityMonitorUpDownJitterDownBinsBin7 OBJECT-TYPE
   SYNTAX      Counter32
   MAX-ACCESS  read-only
   STATUS      current
   DESCRIPTION
      "Path: ethOam.performance.qualityMonitor.upDown.jitterDownBins.bin7

       32 bit unsigned wrappable counter."
   ::= {pr1646v2PbbEthOamEQualityMonitorEntry 506202112}

pr1646v2PbbEthOamEQualityMonitorUpDownJitterDownBinsMaxBin8 OBJECT-TYPE
   SYNTAX      Counter32
   MAX-ACCESS  read-only
   STATUS      current
   DESCRIPTION
      "Path: ethOam.performance.qualityMonitor.upDown.jitterDownBins.maxBin8

       32 bit unsigned wrappable counter."
   ::= {pr1646v2PbbEthOamEQualityMonitorEntry 506202368}

pr1646v2PbbEthOamEQualityMonitorUpDownJitterDownBinsMax OBJECT-TYPE
   SYNTAX      Integer32
   MAX-ACCESS  read-only
   STATUS      current
   DESCRIPTION
      "Path: ethOam.performance.qualityMonitor.upDown.jitterDownBins.max

       unit name = sec
       formula = 1000 / ; 1000 *"
   ::= {pr1646v2PbbEthOamEQualityMonitorEntry 506205696}

pr1646v2PbbEthOamEQualityMonitorUpDownJitterDownBinsPlusMax OBJECT-TYPE
   SYNTAX      Counter32
   MAX-ACCESS  read-only
   STATUS      current
   DESCRIPTION
      "Path: ethOam.performance.qualityMonitor.upDown.jitterDownBins.plusMax

       32 bit unsigned wrappable counter."
   ::= {pr1646v2PbbEthOamEQualityMonitorEntry 506202624}

pr1646v2PbbEthOamEQualityMonitorLastLogSysUpTime OBJECT-TYPE
   SYNTAX      TimeTicks
   MAX-ACCESS  read-only
   STATUS      current
   DESCRIPTION
      "Path: ethOam.performance.qualityMonitor.lastLog.sysUpTime

       Time in centi-second."
   ::= {pr1646v2PbbEthOamEQualityMonitorEntry 671154176}

pr1646v2PbbEthOamEQualityMonitorLastLogNbrTxPckt OBJECT-TYPE
   SYNTAX      Counter32
   MAX-ACCESS  read-only
   STATUS      current
   DESCRIPTION
      "Path: ethOam.performance.qualityMonitor.lastLog.nbrOfTxPackets

       32 bit unsigned wrappable counter."
   ::= {pr1646v2PbbEthOamEQualityMonitorEntry 671285248}

pr1646v2PbbEthOamEQualityMonitorLastLogNbrRxPckt OBJECT-TYPE
   SYNTAX      Counter32
   MAX-ACCESS  read-only
   STATUS      current
   DESCRIPTION
      "Path: ethOam.performance.qualityMonitor.lastLog.nbrOfRxPackets

       32 bit unsigned wrappable counter."
   ::= {pr1646v2PbbEthOamEQualityMonitorEntry 671350784}

pr1646v2PbbEthOamEQualityMonitorLastLogError OBJECT-TYPE
   SYNTAX      Counter32
   MAX-ACCESS  read-only
   STATUS      current
   DESCRIPTION
      "Path: ethOam.performance.qualityMonitor.lastLog.error

       32 bit unsigned wrappable counter."
   ::= {pr1646v2PbbEthOamEQualityMonitorEntry 672202752}

pr1646v2PbbEthOamEQualityMonitorLastLogLoss OBJECT-TYPE
   SYNTAX      Counter32
   MAX-ACCESS  read-only
   STATUS      current
   DESCRIPTION
      "Path: ethOam.performance.qualityMonitor.lastLog.loss

       32 bit unsigned wrappable counter."
   ::= {pr1646v2PbbEthOamEQualityMonitorEntry 671481856}

pr1646v2PbbEthOamEQualityMonitorLastLogLossDelay OBJECT-TYPE
   SYNTAX      Counter32
   MAX-ACCESS  read-only
   STATUS      current
   DESCRIPTION
      "Path: ethOam.performance.qualityMonitor.lastLog.lossDelay

       32 bit unsigned wrappable counter."
   ::= {pr1646v2PbbEthOamEQualityMonitorEntry 672137216}

pr1646v2PbbEthOamEQualityMonitorLastLogDelayMin OBJECT-TYPE
   SYNTAX      Integer32
   MAX-ACCESS  read-only
   STATUS      current
   DESCRIPTION
      "Path: ethOam.performance.qualityMonitor.lastLog.delayMin

       unit name = sec
       formula = 1000 / ; 1000 *"
   ::= {pr1646v2PbbEthOamEQualityMonitorEntry 671809536}

pr1646v2PbbEthOamEQualityMonitorLastLogDelayAvrg OBJECT-TYPE
   SYNTAX      Integer32
   MAX-ACCESS  read-only
   STATUS      current
   DESCRIPTION
      "Path: ethOam.performance.qualityMonitor.lastLog.delayAvrg

       unit name = sec
       formula = 1000 / ; 1000 *"
   ::= {pr1646v2PbbEthOamEQualityMonitorEntry 671547392}

pr1646v2PbbEthOamEQualityMonitorLastLogDelayMax OBJECT-TYPE
   SYNTAX      Integer32
   MAX-ACCESS  read-only
   STATUS      current
   DESCRIPTION
      "Path: ethOam.performance.qualityMonitor.lastLog.delayMax

       unit name = sec
       formula = 1000 / ; 1000 *"
   ::= {pr1646v2PbbEthOamEQualityMonitorEntry 671612928}

pr1646v2PbbEthOamEQualityMonitorLastLogJitterNegMax OBJECT-TYPE
   SYNTAX      Integer32
   MAX-ACCESS  read-only
   STATUS      current
   DESCRIPTION
      "Path: ethOam.performance.qualityMonitor.lastLog.jitterNegMax

       unit name = sec
       formula = 1000 / ; 1000 *"
   ::= {pr1646v2PbbEthOamEQualityMonitorEntry 672006144}

pr1646v2PbbEthOamEQualityMonitorLastLogJitterAvrg OBJECT-TYPE
   SYNTAX      Integer32
   MAX-ACCESS  read-only
   STATUS      current
   DESCRIPTION
      "Path: ethOam.performance.qualityMonitor.lastLog.jitterAvrg

       unit name = sec
       formula = 1000 / ; 1000 *"
   ::= {pr1646v2PbbEthOamEQualityMonitorEntry 671678464}

pr1646v2PbbEthOamEQualityMonitorLastLogJitterPosMax OBJECT-TYPE
   SYNTAX      Integer32
   MAX-ACCESS  read-only
   STATUS      current
   DESCRIPTION
      "Path: ethOam.performance.qualityMonitor.lastLog.jitterPosMax

       unit name = sec
       formula = 1000 / ; 1000 *"
   ::= {pr1646v2PbbEthOamEQualityMonitorEntry 671744000}

pr1646v2PbbEthOamEQualityMonitorLastLogUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: ethOam.performance.qualityMonitor.lastLog.upDown.status

       Possibilities:
               notInUse   (3)
               onlyJitter   (1)
               jitterAndLoss   (2)
               all   (4)
               onlyLoss   (8)"
   ::= {pr1646v2PbbEthOamEQualityMonitorEntry 673059840}

pr1646v2PbbEthOamEQualityMonitorLastLogUpDownLossUp OBJECT-TYPE
   SYNTAX      Counter32
   MAX-ACCESS  read-only
   STATUS      current
   DESCRIPTION
      "Path: ethOam.performance.qualityMonitor.lastLog.upDown.lossUp

       32 bit unsigned wrappable counter."
   ::= {pr1646v2PbbEthOamEQualityMonitorEntry 673057280}

pr1646v2PbbEthOamEQualityMonitorLastLogUpDownLossDelayUp OBJECT-TYPE
   SYNTAX      Counter32
   MAX-ACCESS  read-only
   STATUS      current
   DESCRIPTION
      "Path: ethOam.performance.qualityMonitor.lastLog.upDown.lossDelayUp

       32 bit unsigned wrappable counter."
   ::= {pr1646v2PbbEthOamEQualityMonitorEntry 673057536}

pr1646v2PbbEthOamEQualityMonitorLastLogUpDownDelayUpMin OBJECT-TYPE
   SYNTAX      Integer32
   MAX-ACCESS  read-only
   STATUS      current
   DESCRIPTION
      "Path: ethOam.performance.qualityMonitor.lastLog.upDown.delayUpMin

       unit name = sec
       formula = 1000 / ; 1000 *"
   ::= {pr1646v2PbbEthOamEQualityMonitorEntry 673062400}

pr1646v2PbbEthOamEQualityMonitorLastLogUpDownDelayUpAvrg OBJECT-TYPE
   SYNTAX      Integer32
   MAX-ACCESS  read-only
   STATUS      current
   DESCRIPTION
      "Path: ethOam.performance.qualityMonitor.lastLog.upDown.delayUpAvrg

       unit name = sec
       formula = 1000 / ; 1000 *"
   ::= {pr1646v2PbbEthOamEQualityMonitorEntry 673062656}

pr1646v2PbbEthOamEQualityMonitorLastLogUpDownDelayUpMax OBJECT-TYPE
   SYNTAX      Integer32
   MAX-ACCESS  read-only
   STATUS      current
   DESCRIPTION
      "Path: ethOam.performance.qualityMonitor.lastLog.upDown.delayUpMax

       unit name = sec
       formula = 1000 / ; 1000 *"
   ::= {pr1646v2PbbEthOamEQualityMonitorEntry 673062912}

pr1646v2PbbEthOamEQualityMonitorLastLogUpDownJitterUpNegMax OBJECT-TYPE
   SYNTAX      Integer32
   MAX-ACCESS  read-only
   STATUS      current
   DESCRIPTION
      "Path: ethOam.performance.qualityMonitor.lastLog.upDown.jitterUpNegMax

       unit name = sec
       formula = 1000 / ; 1000 *"
   ::= {pr1646v2PbbEthOamEQualityMonitorEntry 673054976}

pr1646v2PbbEthOamEQualityMonitorLastLogUpDownJitterUpAvrg OBJECT-TYPE
   SYNTAX      Integer32
   MAX-ACCESS  read-only
   STATUS      current
   DESCRIPTION
      "Path: ethOam.performance.qualityMonitor.lastLog.upDown.jitterUpAvrg

       unit name = sec
       formula = 1000 / ; 1000 *"
   ::= {pr1646v2PbbEthOamEQualityMonitorEntry 673055232}

pr1646v2PbbEthOamEQualityMonitorLastLogUpDownJitterUpPosMax OBJECT-TYPE
   SYNTAX      Integer32
   MAX-ACCESS  read-only
   STATUS      current
   DESCRIPTION
      "Path: ethOam.performance.qualityMonitor.lastLog.upDown.jitterUpPosMax

       unit name = sec
       formula = 1000 / ; 1000 *"
   ::= {pr1646v2PbbEthOamEQualityMonitorEntry 673055488}

pr1646v2PbbEthOamEQualityMonitorLastLogUpDownLossDown OBJECT-TYPE
   SYNTAX      Counter32
   MAX-ACCESS  read-only
   STATUS      current
   DESCRIPTION
      "Path: ethOam.performance.qualityMonitor.lastLog.upDown.lossDown

       32 bit unsigned wrappable counter."
   ::= {pr1646v2PbbEthOamEQualityMonitorEntry 673057792}

pr1646v2PbbEthOamEQualityMonitorLastLogUpDownLossDelayDown OBJECT-TYPE
   SYNTAX      Counter32
   MAX-ACCESS  read-only
   STATUS      current
   DESCRIPTION
      "Path: ethOam.performance.qualityMonitor.lastLog.upDown.lossDelayDown

       32 bit unsigned wrappable counter."
   ::= {pr1646v2PbbEthOamEQualityMonitorEntry 673058048}

pr1646v2PbbEthOamEQualityMonitorLastLogUpDownDelayDownMin OBJECT-TYPE
   SYNTAX      Integer32
   MAX-ACCESS  read-only
   STATUS      current
   DESCRIPTION
      "Path: ethOam.performance.qualityMonitor.lastLog.upDown.delayDownMin

       unit name = sec
       formula = 1000 / ; 1000 *"
   ::= {pr1646v2PbbEthOamEQualityMonitorEntry 673063680}

pr1646v2PbbEthOamEQualityMonitorLastLogUpDownDelayDownAvrg OBJECT-TYPE
   SYNTAX      Integer32
   MAX-ACCESS  read-only
   STATUS      current
   DESCRIPTION
      "Path: ethOam.performance.qualityMonitor.lastLog.upDown.delayDownAvrg

       unit name = sec
       formula = 1000 / ; 1000 *"
   ::= {pr1646v2PbbEthOamEQualityMonitorEntry 673063936}

pr1646v2PbbEthOamEQualityMonitorLastLogUpDownDelayDownMax OBJECT-TYPE
   SYNTAX      Integer32
   MAX-ACCESS  read-only
   STATUS      current
   DESCRIPTION
      "Path: ethOam.performance.qualityMonitor.lastLog.upDown.delayDownMax

       unit name = sec
       formula = 1000 / ; 1000 *"
   ::= {pr1646v2PbbEthOamEQualityMonitorEntry 673064192}

pr1646v2PbbEthOamEQualityMonitorLastLogUpDownJitterDownNegMax OBJECT-TYPE
   SYNTAX      Integer32
   MAX-ACCESS  read-only
   STATUS      current
   DESCRIPTION
      "Path: ethOam.performance.qualityMonitor.lastLog.upDown.jitterDownNegMax

       unit name = sec
       formula = 1000 / ; 1000 *"
   ::= {pr1646v2PbbEthOamEQualityMonitorEntry 673055744}

pr1646v2PbbEthOamEQualityMonitorLastLogUpDownJitterDownAvrg OBJECT-TYPE
   SYNTAX      Integer32
   MAX-ACCESS  read-only
   STATUS      current
   DESCRIPTION
      "Path: ethOam.performance.qualityMonitor.lastLog.upDown.jitterDownAvrg

       unit name = sec
       formula = 1000 / ; 1000 *"
   ::= {pr1646v2PbbEthOamEQualityMonitorEntry 673056000}

pr1646v2PbbEthOamEQualityMonitorLastLogUpDownJitterDownPosMax OBJECT-TYPE
   SYNTAX      Integer32
   MAX-ACCESS  read-only
   STATUS      current
   DESCRIPTION
      "Path: ethOam.performance.qualityMonitor.lastLog.upDown.jitterDownPosMax

       unit name = sec
       formula = 1000 / ; 1000 *"
   ::= {pr1646v2PbbEthOamEQualityMonitorEntry 673056256}

pr1646v2PbbEthOamEQualityMonitorLastLogDate OBJECT-TYPE
   SYNTAX      DisplayString
   MAX-ACCESS  read-only
   STATUS      current
   DESCRIPTION
      "Path: ethOam.performance.qualityMonitor.lastLog.date"
   ::= {pr1646v2PbbEthOamEQualityMonitorEntry 673120256}

pr1646v2PbbEthOamEQualityMonitorAlarm OBJECT-TYPE
   SYNTAX      Integer32
   MAX-ACCESS  read-only
   STATUS      current
   DESCRIPTION
      "Path: ethOam.performance.qualityMonitor.alarm

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {pr1646v2PbbEthOamEQualityMonitorEntry 369098752}

pr1646v2PbbEthOamEQualityMonitorLogging OBJECT-TYPE
   SYNTAX      SEQUENCE OF Pr1646v2PbbEthOamEQualityMonitorLoggingEntry
   MAX-ACCESS  not-accessible
   STATUS      current
   DESCRIPTION
      ""
   ::= {pr1646v2PbbEthOamEQualityMonitor 335544320}

pr1646v2PbbEthOamEQualityMonitorLoggingEntry OBJECT-TYPE
   SYNTAX      Pr1646v2PbbEthOamEQualityMonitorLoggingEntry
   MAX-ACCESS  not-accessible
   STATUS      current
   DESCRIPTION
      ""
   INDEX      { pr1646v2PbbEthOamEQualityMonitorLoggingGlobalIx,
                pr1646v2PbbEthOamEQualityMonitorTableIx,
                pr1646v2PbbEthOamEQualityMonitorLoggingTableIx }
   ::= {pr1646v2PbbEthOamEQualityMonitorLogging 1}

Pr1646v2PbbEthOamEQualityMonitorLoggingEntry ::=
   SEQUENCE
      {
      pr1646v2PbbEthOamEQualityMonitorLoggingGlobalIx
         GlobalIndex,
      pr1646v2PbbEthOamEQualityMonitorLoggingTableIx
         TableIndex,
      pr1646v2PbbEthOamEQualityMonitorLoggingSysUpTime
         TimeTicks,
      pr1646v2PbbEthOamEQualityMonitorLoggingNbrTxPckt
         Counter32,
      pr1646v2PbbEthOamEQualityMonitorLoggingNbrRxPckt
         Counter32,
      pr1646v2PbbEthOamEQualityMonitorLoggingError
         Counter32,
      pr1646v2PbbEthOamEQualityMonitorLoggingLoss
         Counter32,
      pr1646v2PbbEthOamEQualityMonitorLoggingLossDelay
         Counter32,
      pr1646v2PbbEthOamEQualityMonitorLoggingDelayMin
         Integer32,
      pr1646v2PbbEthOamEQualityMonitorLoggingDelayAvrg
         Integer32,
      pr1646v2PbbEthOamEQualityMonitorLoggingDelayMax
         Integer32,
      pr1646v2PbbEthOamEQualityMonitorLoggingJitterNegMax
         Integer32,
      pr1646v2PbbEthOamEQualityMonitorLoggingJitterAvrg
         Integer32,
      pr1646v2PbbEthOamEQualityMonitorLoggingJitterPosMax
         Integer32,
      pr1646v2PbbEthOamEQualityMonitorLoggingUpDownStatus
         INTEGER,
      pr1646v2PbbEthOamEQualityMonitorLoggingUpDownLossUp
         Counter32,
      pr1646v2PbbEthOamEQualityMonitorLoggingUpDownLossDelayUp
         Counter32,
      pr1646v2PbbEthOamEQualityMonitorLoggingUpDownDelayUpMin
         Integer32,
      pr1646v2PbbEthOamEQualityMonitorLoggingUpDownDelayUpAvrg
         Integer32,
      pr1646v2PbbEthOamEQualityMonitorLoggingUpDownDelayUpMax
         Integer32,
      pr1646v2PbbEthOamEQualityMonitorLoggingUpDownJitterUpNegMax
         Integer32,
      pr1646v2PbbEthOamEQualityMonitorLoggingUpDownJitterUpAvrg
         Integer32,
      pr1646v2PbbEthOamEQualityMonitorLoggingUpDownJitterUpPosMax
         Integer32,
      pr1646v2PbbEthOamEQualityMonitorLoggingUpDownLossDown
         Counter32,
      pr1646v2PbbEthOamEQualityMonitorLoggingUpDownLossDelayDown
         Counter32,
      pr1646v2PbbEthOamEQualityMonitorLoggingUpDownDelayDownMin
         Integer32,
      pr1646v2PbbEthOamEQualityMonitorLoggingUpDownDelayDownAvrg
         Integer32,
      pr1646v2PbbEthOamEQualityMonitorLoggingUpDownDelayDownMax
         Integer32,
      pr1646v2PbbEthOamEQualityMonitorLoggingUpDownJitterDownNegMax
         Integer32,
      pr1646v2PbbEthOamEQualityMonitorLoggingUpDownJitterDownAvrg
         Integer32,
      pr1646v2PbbEthOamEQualityMonitorLoggingUpDownJitterDownPosMax
         Integer32,
      pr1646v2PbbEthOamEQualityMonitorLoggingDate
         DisplayString
      }

pr1646v2PbbEthOamEQualityMonitorLoggingGlobalIx OBJECT-TYPE
   SYNTAX      GlobalIndex
   MAX-ACCESS  not-accessible
   STATUS      current
   DESCRIPTION
      "The value of the tlsCntTreeGlobalIndex of the MANAGED OBJECT."
   ::= {pr1646v2PbbEthOamEQualityMonitorLoggingEntry 10}

pr1646v2PbbEthOamEQualityMonitorLoggingTableIx OBJECT-TYPE
   SYNTAX      TableIndex
   MAX-ACCESS  not-accessible
   STATUS      current
   DESCRIPTION
      ""
   ::= {pr1646v2PbbEthOamEQualityMonitorLoggingEntry 11}

pr1646v2PbbEthOamEQualityMonitorLoggingSysUpTime OBJECT-TYPE
   SYNTAX      TimeTicks
   MAX-ACCESS  read-only
   STATUS      current
   DESCRIPTION
      "Path: ethOam.performance.qualityMonitor.logging.sysUpTime

       Time in centi-second."
   ::= {pr1646v2PbbEthOamEQualityMonitorLoggingEntry 16777216}

pr1646v2PbbEthOamEQualityMonitorLoggingNbrTxPckt OBJECT-TYPE
   SYNTAX      Counter32
   MAX-ACCESS  read-only
   STATUS      current
   DESCRIPTION
      "Path: ethOam.performance.qualityMonitor.logging.nbrOfTxPackets

       32 bit unsigned wrappable counter."
   ::= {pr1646v2PbbEthOamEQualityMonitorLoggingEntry 50331648}

pr1646v2PbbEthOamEQualityMonitorLoggingNbrRxPckt OBJECT-TYPE
   SYNTAX      Counter32
   MAX-ACCESS  read-only
   STATUS      current
   DESCRIPTION
      "Path: ethOam.performance.qualityMonitor.logging.nbrOfRxPackets

       32 bit unsigned wrappable counter."
   ::= {pr1646v2PbbEthOamEQualityMonitorLoggingEntry 67108864}

pr1646v2PbbEthOamEQualityMonitorLoggingError OBJECT-TYPE
   SYNTAX      Counter32
   MAX-ACCESS  read-only
   STATUS      current
   DESCRIPTION
      "Path: ethOam.performance.qualityMonitor.logging.error

       32 bit unsigned wrappable counter."
   ::= {pr1646v2PbbEthOamEQualityMonitorLoggingEntry 285212672}

pr1646v2PbbEthOamEQualityMonitorLoggingLoss OBJECT-TYPE
   SYNTAX      Counter32
   MAX-ACCESS  read-only
   STATUS      current
   DESCRIPTION
      "Path: ethOam.performance.qualityMonitor.logging.loss

       32 bit unsigned wrappable counter."
   ::= {pr1646v2PbbEthOamEQualityMonitorLoggingEntry 100663296}

pr1646v2PbbEthOamEQualityMonitorLoggingLossDelay OBJECT-TYPE
   SYNTAX      Counter32
   MAX-ACCESS  read-only
   STATUS      current
   DESCRIPTION
      "Path: ethOam.performance.qualityMonitor.logging.lossDelay

       32 bit unsigned wrappable counter."
   ::= {pr1646v2PbbEthOamEQualityMonitorLoggingEntry 268435456}

pr1646v2PbbEthOamEQualityMonitorLoggingDelayMin OBJECT-TYPE
   SYNTAX      Integer32
   MAX-ACCESS  read-only
   STATUS      current
   DESCRIPTION
      "Path: ethOam.performance.qualityMonitor.logging.delayMin

       unit name = sec
       formula = 1000 / ; 1000 *"
   ::= {pr1646v2PbbEthOamEQualityMonitorLoggingEntry 184549376}

pr1646v2PbbEthOamEQualityMonitorLoggingDelayAvrg OBJECT-TYPE
   SYNTAX      Integer32
   MAX-ACCESS  read-only
   STATUS      current
   DESCRIPTION
      "Path: ethOam.performance.qualityMonitor.logging.delayAvrg

       unit name = sec
       formula = 1000 / ; 1000 *"
   ::= {pr1646v2PbbEthOamEQualityMonitorLoggingEntry 117440512}

pr1646v2PbbEthOamEQualityMonitorLoggingDelayMax OBJECT-TYPE
   SYNTAX      Integer32
   MAX-ACCESS  read-only
   STATUS      current
   DESCRIPTION
      "Path: ethOam.performance.qualityMonitor.logging.delayMax

       unit name = sec
       formula = 1000 / ; 1000 *"
   ::= {pr1646v2PbbEthOamEQualityMonitorLoggingEntry 134217728}

pr1646v2PbbEthOamEQualityMonitorLoggingJitterNegMax OBJECT-TYPE
   SYNTAX      Integer32
   MAX-ACCESS  read-only
   STATUS      current
   DESCRIPTION
      "Path: ethOam.performance.qualityMonitor.logging.jitterNegMax

       unit name = sec
       formula = 1000 / ; 1000 *"
   ::= {pr1646v2PbbEthOamEQualityMonitorLoggingEntry 234881024}

pr1646v2PbbEthOamEQualityMonitorLoggingJitterAvrg OBJECT-TYPE
   SYNTAX      Integer32
   MAX-ACCESS  read-only
   STATUS      current
   DESCRIPTION
      "Path: ethOam.performance.qualityMonitor.logging.jitterAvrg

       unit name = sec
       formula = 1000 / ; 1000 *"
   ::= {pr1646v2PbbEthOamEQualityMonitorLoggingEntry 150994944}

pr1646v2PbbEthOamEQualityMonitorLoggingJitterPosMax OBJECT-TYPE
   SYNTAX      Integer32
   MAX-ACCESS  read-only
   STATUS      current
   DESCRIPTION
      "Path: ethOam.performance.qualityMonitor.logging.jitterPosMax

       unit name = sec
       formula = 1000 / ; 1000 *"
   ::= {pr1646v2PbbEthOamEQualityMonitorLoggingEntry 167772160}

pr1646v2PbbEthOamEQualityMonitorLoggingUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: ethOam.performance.qualityMonitor.logging.upDown.status

       Possibilities:
               notInUse   (3)
               onlyJitter   (1)
               jitterAndLoss   (2)
               all   (4)
               onlyLoss   (8)"
   ::= {pr1646v2PbbEthOamEQualityMonitorLoggingEntry 504627200}

pr1646v2PbbEthOamEQualityMonitorLoggingUpDownLossUp OBJECT-TYPE
   SYNTAX      Counter32
   MAX-ACCESS  read-only
   STATUS      current
   DESCRIPTION
      "Path: ethOam.performance.qualityMonitor.logging.upDown.lossUp

       32 bit unsigned wrappable counter."
   ::= {pr1646v2PbbEthOamEQualityMonitorLoggingEntry 503971840}

pr1646v2PbbEthOamEQualityMonitorLoggingUpDownLossDelayUp OBJECT-TYPE
   SYNTAX      Counter32
   MAX-ACCESS  read-only
   STATUS      current
   DESCRIPTION
      "Path: ethOam.performance.qualityMonitor.logging.upDown.lossDelayUp

       32 bit unsigned wrappable counter."
   ::= {pr1646v2PbbEthOamEQualityMonitorLoggingEntry 504037376}

pr1646v2PbbEthOamEQualityMonitorLoggingUpDownDelayUpMin OBJECT-TYPE
   SYNTAX      Integer32
   MAX-ACCESS  read-only
   STATUS      current
   DESCRIPTION
      "Path: ethOam.performance.qualityMonitor.logging.upDown.delayUpMin

       unit name = sec
       formula = 1000 / ; 1000 *"
   ::= {pr1646v2PbbEthOamEQualityMonitorLoggingEntry 505282560}

pr1646v2PbbEthOamEQualityMonitorLoggingUpDownDelayUpAvrg OBJECT-TYPE
   SYNTAX      Integer32
   MAX-ACCESS  read-only
   STATUS      current
   DESCRIPTION
      "Path: ethOam.performance.qualityMonitor.logging.upDown.delayUpAvrg

       unit name = sec
       formula = 1000 / ; 1000 *"
   ::= {pr1646v2PbbEthOamEQualityMonitorLoggingEntry 505348096}

pr1646v2PbbEthOamEQualityMonitorLoggingUpDownDelayUpMax OBJECT-TYPE
   SYNTAX      Integer32
   MAX-ACCESS  read-only
   STATUS      current
   DESCRIPTION
      "Path: ethOam.performance.qualityMonitor.logging.upDown.delayUpMax

       unit name = sec
       formula = 1000 / ; 1000 *"
   ::= {pr1646v2PbbEthOamEQualityMonitorLoggingEntry 505413632}

pr1646v2PbbEthOamEQualityMonitorLoggingUpDownJitterUpNegMax OBJECT-TYPE
   SYNTAX      Integer32
   MAX-ACCESS  read-only
   STATUS      current
   DESCRIPTION
      "Path: ethOam.performance.qualityMonitor.logging.upDown.jitterUpNegMax

       unit name = sec
       formula = 1000 / ; 1000 *"
   ::= {pr1646v2PbbEthOamEQualityMonitorLoggingEntry 503382016}

pr1646v2PbbEthOamEQualityMonitorLoggingUpDownJitterUpAvrg OBJECT-TYPE
   SYNTAX      Integer32
   MAX-ACCESS  read-only
   STATUS      current
   DESCRIPTION
      "Path: ethOam.performance.qualityMonitor.logging.upDown.jitterUpAvrg

       unit name = sec
       formula = 1000 / ; 1000 *"
   ::= {pr1646v2PbbEthOamEQualityMonitorLoggingEntry 503447552}

pr1646v2PbbEthOamEQualityMonitorLoggingUpDownJitterUpPosMax OBJECT-TYPE
   SYNTAX      Integer32
   MAX-ACCESS  read-only
   STATUS      current
   DESCRIPTION
      "Path: ethOam.performance.qualityMonitor.logging.upDown.jitterUpPosMax

       unit name = sec
       formula = 1000 / ; 1000 *"
   ::= {pr1646v2PbbEthOamEQualityMonitorLoggingEntry 503513088}

pr1646v2PbbEthOamEQualityMonitorLoggingUpDownLossDown OBJECT-TYPE
   SYNTAX      Counter32
   MAX-ACCESS  read-only
   STATUS      current
   DESCRIPTION
      "Path: ethOam.performance.qualityMonitor.logging.upDown.lossDown

       32 bit unsigned wrappable counter."
   ::= {pr1646v2PbbEthOamEQualityMonitorLoggingEntry 504102912}

pr1646v2PbbEthOamEQualityMonitorLoggingUpDownLossDelayDown OBJECT-TYPE
   SYNTAX      Counter32
   MAX-ACCESS  read-only
   STATUS      current
   DESCRIPTION
      "Path: ethOam.performance.qualityMonitor.logging.upDown.lossDelayDown

       32 bit unsigned wrappable counter."
   ::= {pr1646v2PbbEthOamEQualityMonitorLoggingEntry 504168448}

pr1646v2PbbEthOamEQualityMonitorLoggingUpDownDelayDownMin OBJECT-TYPE
   SYNTAX      Integer32
   MAX-ACCESS  read-only
   STATUS      current
   DESCRIPTION
      "Path: ethOam.performance.qualityMonitor.logging.upDown.delayDownMin

       unit name = sec
       formula = 1000 / ; 1000 *"
   ::= {pr1646v2PbbEthOamEQualityMonitorLoggingEntry 505610240}

pr1646v2PbbEthOamEQualityMonitorLoggingUpDownDelayDownAvrg OBJECT-TYPE
   SYNTAX      Integer32
   MAX-ACCESS  read-only
   STATUS      current
   DESCRIPTION
      "Path: ethOam.performance.qualityMonitor.logging.upDown.delayDownAvrg

       unit name = sec
       formula = 1000 / ; 1000 *"
   ::= {pr1646v2PbbEthOamEQualityMonitorLoggingEntry 505675776}

pr1646v2PbbEthOamEQualityMonitorLoggingUpDownDelayDownMax OBJECT-TYPE
   SYNTAX      Integer32
   MAX-ACCESS  read-only
   STATUS      current
   DESCRIPTION
      "Path: ethOam.performance.qualityMonitor.logging.upDown.delayDownMax

       unit name = sec
       formula = 1000 / ; 1000 *"
   ::= {pr1646v2PbbEthOamEQualityMonitorLoggingEntry 505741312}

pr1646v2PbbEthOamEQualityMonitorLoggingUpDownJitterDownNegMax OBJECT-TYPE
   SYNTAX      Integer32
   MAX-ACCESS  read-only
   STATUS      current
   DESCRIPTION
      "Path: ethOam.performance.qualityMonitor.logging.upDown.jitterDownNegMax

       unit name = sec
       formula = 1000 / ; 1000 *"
   ::= {pr1646v2PbbEthOamEQualityMonitorLoggingEntry 503578624}

pr1646v2PbbEthOamEQualityMonitorLoggingUpDownJitterDownAvrg OBJECT-TYPE
   SYNTAX      Integer32
   MAX-ACCESS  read-only
   STATUS      current
   DESCRIPTION
      "Path: ethOam.performance.qualityMonitor.logging.upDown.jitterDownAvrg

       unit name = sec
       formula = 1000 / ; 1000 *"
   ::= {pr1646v2PbbEthOamEQualityMonitorLoggingEntry 503644160}

pr1646v2PbbEthOamEQualityMonitorLoggingUpDownJitterDownPosMax OBJECT-TYPE
   SYNTAX      Integer32
   MAX-ACCESS  read-only
   STATUS      current
   DESCRIPTION
      "Path: ethOam.performance.qualityMonitor.logging.upDown.jitterDownPosMax

       unit name = sec
       formula = 1000 / ; 1000 *"
   ::= {pr1646v2PbbEthOamEQualityMonitorLoggingEntry 503709696}

pr1646v2PbbEthOamEQualityMonitorLoggingDate OBJECT-TYPE
   SYNTAX      DisplayString
   MAX-ACCESS  read-only
   STATUS      current
   DESCRIPTION
      "Path: ethOam.performance.qualityMonitor.logging.date"
   ::= {pr1646v2PbbEthOamEQualityMonitorLoggingEntry 520093696}

pr1646v2PbbEthOamEQualityMonitorLoggingBin OBJECT-TYPE
   SYNTAX      SEQUENCE OF Pr1646v2PbbEthOamEQualityMonitorLoggingBinEntry
   MAX-ACCESS  not-accessible
   STATUS      current
   DESCRIPTION
      ""
   ::= {pr1646v2PbbEthOamEQualityMonitor 337641472}

pr1646v2PbbEthOamEQualityMonitorLoggingBinEntry OBJECT-TYPE
   SYNTAX      Pr1646v2PbbEthOamEQualityMonitorLoggingBinEntry
   MAX-ACCESS  not-accessible
   STATUS      current
   DESCRIPTION
      ""
   INDEX      { pr1646v2PbbEthOamEQualityMonitorLoggingBinGlobalIx,
                pr1646v2PbbEthOamEQualityMonitorTableIx,
                pr1646v2PbbEthOamEQualityMonitorLoggingTableIx,
                pr1646v2PbbEthOamEQualityMonitorLoggingBinTableIx }
   ::= {pr1646v2PbbEthOamEQualityMonitorLoggingBin 1}

Pr1646v2PbbEthOamEQualityMonitorLoggingBinEntry ::=
   SEQUENCE
      {
      pr1646v2PbbEthOamEQualityMonitorLoggingBinGlobalIx
         GlobalIndex,
      pr1646v2PbbEthOamEQualityMonitorLoggingBinTableIx
         TableIndex,
      pr1646v2PbbEthOamEQualityMonitorLoggingBinName
         INTEGER,
      pr1646v2PbbEthOamEQualityMonitorLoggingBinType
         INTEGER,
      pr1646v2PbbEthOamEQualityMonitorLoggingBinMinMin
         Counter32,
      pr1646v2PbbEthOamEQualityMonitorLoggingBinMin
         Integer32,
      pr1646v2PbbEthOamEQualityMonitorLoggingBinMinBin1
         Counter32,
      pr1646v2PbbEthOamEQualityMonitorLoggingBinBin2
         Counter32,
      pr1646v2PbbEthOamEQualityMonitorLoggingBinBin3
         Counter32,
      pr1646v2PbbEthOamEQualityMonitorLoggingBinBin4
         Counter32,
      pr1646v2PbbEthOamEQualityMonitorLoggingBinBin5
         Counter32,
      pr1646v2PbbEthOamEQualityMonitorLoggingBinBin6
         Counter32,
      pr1646v2PbbEthOamEQualityMonitorLoggingBinBin7
         Counter32,
      pr1646v2PbbEthOamEQualityMonitorLoggingBinMaxBin8
         Counter32,
      pr1646v2PbbEthOamEQualityMonitorLoggingBinMax
         Integer32,
      pr1646v2PbbEthOamEQualityMonitorLoggingBinPlusMax
         Counter32
      }

pr1646v2PbbEthOamEQualityMonitorLoggingBinGlobalIx OBJECT-TYPE
   SYNTAX      GlobalIndex
   MAX-ACCESS  not-accessible
   STATUS      current
   DESCRIPTION
      "The value of the tlsCntTreeGlobalIndex of the MANAGED OBJECT."
   ::= {pr1646v2PbbEthOamEQualityMonitorLoggingBinEntry 10}

pr1646v2PbbEthOamEQualityMonitorLoggingBinTableIx OBJECT-TYPE
   SYNTAX      TableIndex
   MAX-ACCESS  not-accessible
   STATUS      current
   DESCRIPTION
      ""
   ::= {pr1646v2PbbEthOamEQualityMonitorLoggingBinEntry 11}

pr1646v2PbbEthOamEQualityMonitorLoggingBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: ethOam.performance.qualityMonitor.logging.bin.name

       Possibilities:
               delay   (1)
               delayUp   (2)
               delayDown   (3)
               jitter   (4)
               jitterUp   (5)
               jitterDown   (6)"
   ::= {pr1646v2PbbEthOamEQualityMonitorLoggingBinEntry 503316480}

pr1646v2PbbEthOamEQualityMonitorLoggingBinType OBJECT-TYPE
   SYNTAX      INTEGER
               {
               fd (1),
               fdr (2),
               notInUse (3),
               ifdv (4)
               }
   MAX-ACCESS  read-only
   STATUS      current
   DESCRIPTION
      "Path: ethOam.performance.qualityMonitor.logging.bin.type

       Possibilities:
               fd   (1)
               fdr   (2)
               notInUse   (3)
               ifdv   (4)"
   ::= {pr1646v2PbbEthOamEQualityMonitorLoggingBinEntry 520093696}

pr1646v2PbbEthOamEQualityMonitorLoggingBinMinMin OBJECT-TYPE
   SYNTAX      Counter32
   MAX-ACCESS  read-only
   STATUS      current
   DESCRIPTION
      "Path: ethOam.performance.qualityMonitor.logging.bin.minMin

       32 bit unsigned wrappable counter."
   ::= {pr1646v2PbbEthOamEQualityMonitorLoggingBinEntry 16777216}

pr1646v2PbbEthOamEQualityMonitorLoggingBinMin OBJECT-TYPE
   SYNTAX      Integer32
   MAX-ACCESS  read-only
   STATUS      current
   DESCRIPTION
      "Path: ethOam.performance.qualityMonitor.logging.bin.min

       unit name = sec
       formula = 1000 / ; 1000 *"
   ::= {pr1646v2PbbEthOamEQualityMonitorLoggingBinEntry 352321536}

pr1646v2PbbEthOamEQualityMonitorLoggingBinMinBin1 OBJECT-TYPE
   SYNTAX      Counter32
   MAX-ACCESS  read-only
   STATUS      current
   DESCRIPTION
      "Path: ethOam.performance.qualityMonitor.logging.bin.minBin1

       32 bit unsigned wrappable counter."
   ::= {pr1646v2PbbEthOamEQualityMonitorLoggingBinEntry 33554432}

pr1646v2PbbEthOamEQualityMonitorLoggingBinBin2 OBJECT-TYPE
   SYNTAX      Counter32
   MAX-ACCESS  read-only
   STATUS      current
   DESCRIPTION
      "Path: ethOam.performance.qualityMonitor.logging.bin.bin2

       32 bit unsigned wrappable counter."
   ::= {pr1646v2PbbEthOamEQualityMonitorLoggingBinEntry 50331648}

pr1646v2PbbEthOamEQualityMonitorLoggingBinBin3 OBJECT-TYPE
   SYNTAX      Counter32
   MAX-ACCESS  read-only
   STATUS      current
   DESCRIPTION
      "Path: ethOam.performance.qualityMonitor.logging.bin.bin3

       32 bit unsigned wrappable counter."
   ::= {pr1646v2PbbEthOamEQualityMonitorLoggingBinEntry 67108864}

pr1646v2PbbEthOamEQualityMonitorLoggingBinBin4 OBJECT-TYPE
   SYNTAX      Counter32
   MAX-ACCESS  read-only
   STATUS      current
   DESCRIPTION
      "Path: ethOam.performance.qualityMonitor.logging.bin.bin4

       32 bit unsigned wrappable counter."
   ::= {pr1646v2PbbEthOamEQualityMonitorLoggingBinEntry 83886080}

pr1646v2PbbEthOamEQualityMonitorLoggingBinBin5 OBJECT-TYPE
   SYNTAX      Counter32
   MAX-ACCESS  read-only
   STATUS      current
   DESCRIPTION
      "Path: ethOam.performance.qualityMonitor.logging.bin.bin5

       32 bit unsigned wrappable counter."
   ::= {pr1646v2PbbEthOamEQualityMonitorLoggingBinEntry 100663296}

pr1646v2PbbEthOamEQualityMonitorLoggingBinBin6 OBJECT-TYPE
   SYNTAX      Counter32
   MAX-ACCESS  read-only
   STATUS      current
   DESCRIPTION
      "Path: ethOam.performance.qualityMonitor.logging.bin.bin6

       32 bit unsigned wrappable counter."
   ::= {pr1646v2PbbEthOamEQualityMonitorLoggingBinEntry 117440512}

pr1646v2PbbEthOamEQualityMonitorLoggingBinBin7 OBJECT-TYPE
   SYNTAX      Counter32
   MAX-ACCESS  read-only
   STATUS      current
   DESCRIPTION
      "Path: ethOam.performance.qualityMonitor.logging.bin.bin7

       32 bit unsigned wrappable counter."
   ::= {pr1646v2PbbEthOamEQualityMonitorLoggingBinEntry 134217728}

pr1646v2PbbEthOamEQualityMonitorLoggingBinMaxBin8 OBJECT-TYPE
   SYNTAX      Counter32
   MAX-ACCESS  read-only
   STATUS      current
   DESCRIPTION
      "Path: ethOam.performance.qualityMonitor.logging.bin.maxBin8

       32 bit unsigned wrappable counter."
   ::= {pr1646v2PbbEthOamEQualityMonitorLoggingBinEntry 150994944}

pr1646v2PbbEthOamEQualityMonitorLoggingBinMax OBJECT-TYPE
   SYNTAX      Integer32
   MAX-ACCESS  read-only
   STATUS      current
   DESCRIPTION
      "Path: ethOam.performance.qualityMonitor.logging.bin.max

       unit name = sec
       formula = 1000 / ; 1000 *"
   ::= {pr1646v2PbbEthOamEQualityMonitorLoggingBinEntry 369098752}

pr1646v2PbbEthOamEQualityMonitorLoggingBinPlusMax OBJECT-TYPE
   SYNTAX      Counter32
   MAX-ACCESS  read-only
   STATUS      current
   DESCRIPTION
      "Path: ethOam.performance.qualityMonitor.logging.bin.plusMax

       32 bit unsigned wrappable counter."
   ::= {pr1646v2PbbEthOamEQualityMonitorLoggingBinEntry 167772160}

pr1646v2PbbEthOamEQualityMonitorLastLogBin OBJECT-TYPE
   SYNTAX      SEQUENCE OF Pr1646v2PbbEthOamEQualityMonitorLastLogBinEntry
   MAX-ACCESS  not-accessible
   STATUS      current
   DESCRIPTION
      ""
   ::= {pr1646v2PbbEthOamEQualityMonitor 673185792}

pr1646v2PbbEthOamEQualityMonitorLastLogBinEntry OBJECT-TYPE
   SYNTAX      Pr1646v2PbbEthOamEQualityMonitorLastLogBinEntry
   MAX-ACCESS  not-accessible
   STATUS      current
   DESCRIPTION
      ""
   INDEX      { pr1646v2PbbEthOamEQualityMonitorLastLogBinGlobalIx,
                pr1646v2PbbEthOamEQualityMonitorTableIx,
                pr1646v2PbbEthOamEQualityMonitorLastLogBinTableIx }
   ::= {pr1646v2PbbEthOamEQualityMonitorLastLogBin 1}

Pr1646v2PbbEthOamEQualityMonitorLastLogBinEntry ::=
   SEQUENCE
      {
      pr1646v2PbbEthOamEQualityMonitorLastLogBinGlobalIx
         GlobalIndex,
      pr1646v2PbbEthOamEQualityMonitorLastLogBinTableIx
         TableIndex,
      pr1646v2PbbEthOamEQualityMonitorLastLogBinName
         INTEGER,
      pr1646v2PbbEthOamEQualityMonitorLastLogBinType
         INTEGER,
      pr1646v2PbbEthOamEQualityMonitorLastLogBinMinMin
         Counter32,
      pr1646v2PbbEthOamEQualityMonitorLastLogBinMin
         Integer32,
      pr1646v2PbbEthOamEQualityMonitorLastLogBinMinBin1
         Counter32,
      pr1646v2PbbEthOamEQualityMonitorLastLogBinBin2
         Counter32,
      pr1646v2PbbEthOamEQualityMonitorLastLogBinBin3
         Counter32,
      pr1646v2PbbEthOamEQualityMonitorLastLogBinBin4
         Counter32,
      pr1646v2PbbEthOamEQualityMonitorLastLogBinBin5
         Counter32,
      pr1646v2PbbEthOamEQualityMonitorLastLogBinBin6
         Counter32,
      pr1646v2PbbEthOamEQualityMonitorLastLogBinBin7
         Counter32,
      pr1646v2PbbEthOamEQualityMonitorLastLogBinMaxBin8
         Counter32,
      pr1646v2PbbEthOamEQualityMonitorLastLogBinMax
         Integer32,
      pr1646v2PbbEthOamEQualityMonitorLastLogBinPlusMax
         Counter32
      }

pr1646v2PbbEthOamEQualityMonitorLastLogBinGlobalIx OBJECT-TYPE
   SYNTAX      GlobalIndex
   MAX-ACCESS  not-accessible
   STATUS      current
   DESCRIPTION
      "The value of the tlsCntTreeGlobalIndex of the MANAGED OBJECT."
   ::= {pr1646v2PbbEthOamEQualityMonitorLastLogBinEntry 10}

pr1646v2PbbEthOamEQualityMonitorLastLogBinTableIx OBJECT-TYPE
   SYNTAX      TableIndex
   MAX-ACCESS  not-accessible
   STATUS      current
   DESCRIPTION
      ""
   ::= {pr1646v2PbbEthOamEQualityMonitorLastLogBinEntry 11}

pr1646v2PbbEthOamEQualityMonitorLastLogBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: ethOam.performance.qualityMonitor.lastLog.bin.name

       Possibilities:
               delay   (1)
               delayUp   (2)
               delayDown   (3)
               jitter   (4)
               jitterUp   (5)
               jitterDown   (6)"
   ::= {pr1646v2PbbEthOamEQualityMonitorLastLogBinEntry 503316480}

pr1646v2PbbEthOamEQualityMonitorLastLogBinType OBJECT-TYPE
   SYNTAX      INTEGER
               {
               fd (1),
               fdr (2),
               notInUse (3),
               ifdv (4)
               }
   MAX-ACCESS  read-only
   STATUS      current
   DESCRIPTION
      "Path: ethOam.performance.qualityMonitor.lastLog.bin.type

       Possibilities:
               fd   (1)
               fdr   (2)
               notInUse   (3)
               ifdv   (4)"
   ::= {pr1646v2PbbEthOamEQualityMonitorLastLogBinEntry 520093696}

pr1646v2PbbEthOamEQualityMonitorLastLogBinMinMin OBJECT-TYPE
   SYNTAX      Counter32
   MAX-ACCESS  read-only
   STATUS      current
   DESCRIPTION
      "Path: ethOam.performance.qualityMonitor.lastLog.bin.minMin

       32 bit unsigned wrappable counter."
   ::= {pr1646v2PbbEthOamEQualityMonitorLastLogBinEntry 16777216}

pr1646v2PbbEthOamEQualityMonitorLastLogBinMin OBJECT-TYPE
   SYNTAX      Integer32
   MAX-ACCESS  read-only
   STATUS      current
   DESCRIPTION
      "Path: ethOam.performance.qualityMonitor.lastLog.bin.min

       unit name = sec
       formula = 1000 / ; 1000 *"
   ::= {pr1646v2PbbEthOamEQualityMonitorLastLogBinEntry 352321536}

pr1646v2PbbEthOamEQualityMonitorLastLogBinMinBin1 OBJECT-TYPE
   SYNTAX      Counter32
   MAX-ACCESS  read-only
   STATUS      current
   DESCRIPTION
      "Path: ethOam.performance.qualityMonitor.lastLog.bin.minBin1

       32 bit unsigned wrappable counter."
   ::= {pr1646v2PbbEthOamEQualityMonitorLastLogBinEntry 33554432}

pr1646v2PbbEthOamEQualityMonitorLastLogBinBin2 OBJECT-TYPE
   SYNTAX      Counter32
   MAX-ACCESS  read-only
   STATUS      current
   DESCRIPTION
      "Path: ethOam.performance.qualityMonitor.lastLog.bin.bin2

       32 bit unsigned wrappable counter."
   ::= {pr1646v2PbbEthOamEQualityMonitorLastLogBinEntry 50331648}

pr1646v2PbbEthOamEQualityMonitorLastLogBinBin3 OBJECT-TYPE
   SYNTAX      Counter32
   MAX-ACCESS  read-only
   STATUS      current
   DESCRIPTION
      "Path: ethOam.performance.qualityMonitor.lastLog.bin.bin3

       32 bit unsigned wrappable counter."
   ::= {pr1646v2PbbEthOamEQualityMonitorLastLogBinEntry 67108864}

pr1646v2PbbEthOamEQualityMonitorLastLogBinBin4 OBJECT-TYPE
   SYNTAX      Counter32
   MAX-ACCESS  read-only
   STATUS      current
   DESCRIPTION
      "Path: ethOam.performance.qualityMonitor.lastLog.bin.bin4

       32 bit unsigned wrappable counter."
   ::= {pr1646v2PbbEthOamEQualityMonitorLastLogBinEntry 83886080}

pr1646v2PbbEthOamEQualityMonitorLastLogBinBin5 OBJECT-TYPE
   SYNTAX      Counter32
   MAX-ACCESS  read-only
   STATUS      current
   DESCRIPTION
      "Path: ethOam.performance.qualityMonitor.lastLog.bin.bin5

       32 bit unsigned wrappable counter."
   ::= {pr1646v2PbbEthOamEQualityMonitorLastLogBinEntry 100663296}

pr1646v2PbbEthOamEQualityMonitorLastLogBinBin6 OBJECT-TYPE
   SYNTAX      Counter32
   MAX-ACCESS  read-only
   STATUS      current
   DESCRIPTION
      "Path: ethOam.performance.qualityMonitor.lastLog.bin.bin6

       32 bit unsigned wrappable counter."
   ::= {pr1646v2PbbEthOamEQualityMonitorLastLogBinEntry 117440512}

pr1646v2PbbEthOamEQualityMonitorLastLogBinBin7 OBJECT-TYPE
   SYNTAX      Counter32
   MAX-ACCESS  read-only
   STATUS      current
   DESCRIPTION
      "Path: ethOam.performance.qualityMonitor.lastLog.bin.bin7

       32 bit unsigned wrappable counter."
   ::= {pr1646v2PbbEthOamEQualityMonitorLastLogBinEntry 134217728}

pr1646v2PbbEthOamEQualityMonitorLastLogBinMaxBin8 OBJECT-TYPE
   SYNTAX      Counter32
   MAX-ACCESS  read-only
   STATUS      current
   DESCRIPTION
      "Path: ethOam.performance.qualityMonitor.lastLog.bin.maxBin8

       32 bit unsigned wrappable counter."
   ::= {pr1646v2PbbEthOamEQualityMonitorLastLogBinEntry 150994944}

pr1646v2PbbEthOamEQualityMonitorLastLogBinMax OBJECT-TYPE
   SYNTAX      Integer32
   MAX-ACCESS  read-only
   STATUS      current
   DESCRIPTION
      "Path: ethOam.performance.qualityMonitor.lastLog.bin.max

       unit name = sec
       formula = 1000 / ; 1000 *"
   ::= {pr1646v2PbbEthOamEQualityMonitorLastLogBinEntry 369098752}

pr1646v2PbbEthOamEQualityMonitorLastLogBinPlusMax OBJECT-TYPE
   SYNTAX      Counter32
   MAX-ACCESS  read-only
   STATUS      current
   DESCRIPTION
      "Path: ethOam.performance.qualityMonitor.lastLog.bin.plusMax

       32 bit unsigned wrappable counter."
   ::= {pr1646v2PbbEthOamEQualityMonitorLastLogBinEntry 167772160}


pr1646v2PbbEthOamELoss OBJECT IDENTIFIER ::= {pr1646v2PbbEthOamE 21}

pr1646v2PbbEthOamELossSSCTable OBJECT-TYPE
   SYNTAX      SEQUENCE OF Pr1646v2PbbEthOamELossEntry
   MAX-ACCESS  not-accessible
   STATUS      current
   DESCRIPTION
      "frame loss performance table"
   ::= {pr1646v2PbbEthOamELoss 1}

pr1646v2PbbEthOamELossEntry OBJECT-TYPE
   SYNTAX      Pr1646v2PbbEthOamELossEntry
   MAX-ACCESS  not-accessible
   STATUS      current
   DESCRIPTION
      ""
   INDEX      { pr1646v2PbbEthOamELossGlobalIx,
                pr1646v2PbbEthOamELossTableIx }
   ::= {pr1646v2PbbEthOamELossSSCTable 1}

Pr1646v2PbbEthOamELossEntry ::=
   SEQUENCE
      {
      pr1646v2PbbEthOamELossGlobalIx
         GlobalIndex,
      pr1646v2PbbEthOamELossTableIx
         TableIndex,
      pr1646v2PbbEthOamELossMepName
         DisplayString,
      pr1646v2PbbEthOamELossMegLevel
         Integer32,
      pr1646v2PbbEthOamELossMegIdMaintDomainName
         DisplayString,
      pr1646v2PbbEthOamELossMegIdShortMaName
         DisplayString,
      pr1646v2PbbEthOamELossMepId
         INTEGER,
      pr1646v2PbbEthOamELossMacAddress
         OCTET STRING,
      pr1646v2PbbEthOamELossPriority
         Integer32,
      pr1646v2PbbEthOamELossNbrOfTxFrames
         Counter32,
      pr1646v2PbbEthOamELossNbrOfRxFrames
         Counter32,
      pr1646v2PbbEthOamELossLoss
         Counter32,
      pr1646v2PbbEthOamELossNearEndDrops
         Integer32,
      pr1646v2PbbEthOamELossFarEndDrops
         Integer32
      }

pr1646v2PbbEthOamELossGlobalIx OBJECT-TYPE
   SYNTAX      GlobalIndex
   MAX-ACCESS  not-accessible
   STATUS      current
   DESCRIPTION
      "The value of the tlsCntTreeGlobalIndex of the MANAGED OBJECT."
   ::= {pr1646v2PbbEthOamELossEntry 10}

pr1646v2PbbEthOamELossTableIx OBJECT-TYPE
   SYNTAX      TableIndex
   MAX-ACCESS  not-accessible
   STATUS      current
   DESCRIPTION
      ""
   ::= {pr1646v2PbbEthOamELossEntry 11}

pr1646v2PbbEthOamELossMepName OBJECT-TYPE
   SYNTAX      DisplayString
   MAX-ACCESS  read-only
   STATUS      current
   DESCRIPTION
      "Path: ethOam.performance.loss.mepName"
   ::= {pr1646v2PbbEthOamELossEntry 16777216}

pr1646v2PbbEthOamELossMegLevel OBJECT-TYPE
   SYNTAX      Integer32
   MAX-ACCESS  read-only
   STATUS      current
   DESCRIPTION
      "Path: ethOam.performance.loss.megLevel"
   ::= {pr1646v2PbbEthOamELossEntry 33554432}

pr1646v2PbbEthOamELossMegIdMaintDomainName OBJECT-TYPE
   SYNTAX      DisplayString
   MAX-ACCESS  read-only
   STATUS      current
   DESCRIPTION
      "Path: ethOam.performance.loss.megId.maintDomainName"
   ::= {pr1646v2PbbEthOamELossEntry 50397184}

pr1646v2PbbEthOamELossMegIdShortMaName OBJECT-TYPE
   SYNTAX      DisplayString
   MAX-ACCESS  read-only
   STATUS      current
   DESCRIPTION
      "Path: ethOam.performance.loss.megId.shortMaName"
   ::= {pr1646v2PbbEthOamELossEntry 50462720}

pr1646v2PbbEthOamELossMepId OBJECT-TYPE
   SYNTAX      INTEGER
               {
               unknown (8192)
               }
   MAX-ACCESS  read-only
   STATUS      current
   DESCRIPTION
      "Path: ethOam.performance.loss.mepId

       Possibilities:
               unknown   (8192)"
   ::= {pr1646v2PbbEthOamELossEntry 67108864}

pr1646v2PbbEthOamELossMacAddress OBJECT-TYPE
   SYNTAX      OCTET STRING
   MAX-ACCESS  read-only
   STATUS      current
   DESCRIPTION
      "Path: ethOam.performance.loss.macAddress

       MAC address."
   ::= {pr1646v2PbbEthOamELossEntry 83886080}

pr1646v2PbbEthOamELossPriority OBJECT-TYPE
   SYNTAX      Integer32
   MAX-ACCESS  read-only
   STATUS      current
   DESCRIPTION
      "Path: ethOam.performance.loss.priority"
   ::= {pr1646v2PbbEthOamELossEntry 100663296}

pr1646v2PbbEthOamELossNbrOfTxFrames OBJECT-TYPE
   SYNTAX      Counter32
   MAX-ACCESS  read-only
   STATUS      current
   DESCRIPTION
      "Path: ethOam.performance.loss.nbrOfTxFrames

       32 bit unsigned wrappable counter."
   ::= {pr1646v2PbbEthOamELossEntry 117440512}

pr1646v2PbbEthOamELossNbrOfRxFrames OBJECT-TYPE
   SYNTAX      Counter32
   MAX-ACCESS  read-only
   STATUS      current
   DESCRIPTION
      "Path: ethOam.performance.loss.nbrOfRxFrames

       32 bit unsigned wrappable counter."
   ::= {pr1646v2PbbEthOamELossEntry 134217728}

pr1646v2PbbEthOamELossLoss OBJECT-TYPE
   SYNTAX      Counter32
   MAX-ACCESS  read-only
   STATUS      current
   DESCRIPTION
      "Path: ethOam.performance.loss.loss

       32 bit unsigned wrappable counter."
   ::= {pr1646v2PbbEthOamELossEntry 201326592}

pr1646v2PbbEthOamELossNearEndDrops OBJECT-TYPE
   SYNTAX      Integer32
   MAX-ACCESS  read-only
   STATUS      current
   DESCRIPTION
      "Path: ethOam.performance.loss.nearEndDrops"
   ::= {pr1646v2PbbEthOamELossEntry 150994944}

pr1646v2PbbEthOamELossFarEndDrops OBJECT-TYPE
   SYNTAX      Integer32
   MAX-ACCESS  read-only
   STATUS      current
   DESCRIPTION
      "Path: ethOam.performance.loss.farEndDrops"
   ::= {pr1646v2PbbEthOamELossEntry 167772160}

pr1646v2PbbEthOamELossLogging OBJECT-TYPE
   SYNTAX      SEQUENCE OF Pr1646v2PbbEthOamELossLoggingEntry
   MAX-ACCESS  not-accessible
   STATUS      current
   DESCRIPTION
      ""
   ::= {pr1646v2PbbEthOamELoss 184549376}

pr1646v2PbbEthOamELossLoggingEntry OBJECT-TYPE
   SYNTAX      Pr1646v2PbbEthOamELossLoggingEntry
   MAX-ACCESS  not-accessible
   STATUS      current
   DESCRIPTION
      ""
   INDEX      { pr1646v2PbbEthOamELossLoggingGlobalIx,
                pr1646v2PbbEthOamELossTableIx,
                pr1646v2PbbEthOamELossLoggingTableIx }
   ::= {pr1646v2PbbEthOamELossLogging 1}

Pr1646v2PbbEthOamELossLoggingEntry ::=
   SEQUENCE
      {
      pr1646v2PbbEthOamELossLoggingGlobalIx
         GlobalIndex,
      pr1646v2PbbEthOamELossLoggingTableIx
         TableIndex,
      pr1646v2PbbEthOamELossLoggingSysUpTime
         TimeTicks,
      pr1646v2PbbEthOamELossLoggingNbrTxFrm
         Counter32,
      pr1646v2PbbEthOamELossLoggingNbrRxFrm
         Counter32,
      pr1646v2PbbEthOamELossLoggingLoss
         Counter32,
      pr1646v2PbbEthOamELossLoggingNearEndDrops
         Integer32,
      pr1646v2PbbEthOamELossLoggingFarEndDrops
         Integer32
      }

pr1646v2PbbEthOamELossLoggingGlobalIx OBJECT-TYPE
   SYNTAX      GlobalIndex
   MAX-ACCESS  not-accessible
   STATUS      current
   DESCRIPTION
      "The value of the tlsCntTreeGlobalIndex of the MANAGED OBJECT."
   ::= {pr1646v2PbbEthOamELossLoggingEntry 10}

pr1646v2PbbEthOamELossLoggingTableIx OBJECT-TYPE
   SYNTAX      TableIndex
   MAX-ACCESS  not-accessible
   STATUS      current
   DESCRIPTION
      ""
   ::= {pr1646v2PbbEthOamELossLoggingEntry 11}

pr1646v2PbbEthOamELossLoggingSysUpTime OBJECT-TYPE
   SYNTAX      TimeTicks
   MAX-ACCESS  read-only
   STATUS      current
   DESCRIPTION
      "Path: ethOam.performance.loss.logging.sysUpTime

       Time in centi-second."
   ::= {pr1646v2PbbEthOamELossLoggingEntry 16777216}

pr1646v2PbbEthOamELossLoggingNbrTxFrm OBJECT-TYPE
   SYNTAX      Counter32
   MAX-ACCESS  read-only
   STATUS      current
   DESCRIPTION
      "Path: ethOam.performance.loss.logging.nbrOfTxFrames

       32 bit unsigned wrappable counter."
   ::= {pr1646v2PbbEthOamELossLoggingEntry 33554432}

pr1646v2PbbEthOamELossLoggingNbrRxFrm OBJECT-TYPE
   SYNTAX      Counter32
   MAX-ACCESS  read-only
   STATUS      current
   DESCRIPTION
      "Path: ethOam.performance.loss.logging.nbrOfRxFrames

       32 bit unsigned wrappable counter."
   ::= {pr1646v2PbbEthOamELossLoggingEntry 50331648}

pr1646v2PbbEthOamELossLoggingLoss OBJECT-TYPE
   SYNTAX      Counter32
   MAX-ACCESS  read-only
   STATUS      current
   DESCRIPTION
      "Path: ethOam.performance.loss.logging.loss

       32 bit unsigned wrappable counter."
   ::= {pr1646v2PbbEthOamELossLoggingEntry 67108864}

pr1646v2PbbEthOamELossLoggingNearEndDrops OBJECT-TYPE
   SYNTAX      Integer32
   MAX-ACCESS  read-only
   STATUS      current
   DESCRIPTION
      "Path: ethOam.performance.loss.logging.nearEndDrops"
   ::= {pr1646v2PbbEthOamELossLoggingEntry 150994944}

pr1646v2PbbEthOamELossLoggingFarEndDrops OBJECT-TYPE
   SYNTAX      Integer32
   MAX-ACCESS  read-only
   STATUS      current
   DESCRIPTION
      "Path: ethOam.performance.loss.logging.farEndDrops"
   ::= {pr1646v2PbbEthOamELossLoggingEntry 167772160}


pr1646v2PbbEthOamEDelay OBJECT IDENTIFIER ::= {pr1646v2PbbEthOamE 22}

pr1646v2PbbEthOamEDelaySSCTable OBJECT-TYPE
   SYNTAX      SEQUENCE OF Pr1646v2PbbEthOamEDelayEntry
   MAX-ACCESS  not-accessible
   STATUS      current
   DESCRIPTION
      "frame delay performance table"
   ::= {pr1646v2PbbEthOamEDelay 1}

pr1646v2PbbEthOamEDelayEntry OBJECT-TYPE
   SYNTAX      Pr1646v2PbbEthOamEDelayEntry
   MAX-ACCESS  not-accessible
   STATUS      current
   DESCRIPTION
      ""
   INDEX      { pr1646v2PbbEthOamEDelayGlobalIx,
                pr1646v2PbbEthOamEDelayTableIx }
   ::= {pr1646v2PbbEthOamEDelaySSCTable 1}

Pr1646v2PbbEthOamEDelayEntry ::=
   SEQUENCE
      {
      pr1646v2PbbEthOamEDelayGlobalIx
         GlobalIndex,
      pr1646v2PbbEthOamEDelayTableIx
         TableIndex,
      pr1646v2PbbEthOamEDelayMepName
         DisplayString,
      pr1646v2PbbEthOamEDelayMegLevel
         Integer32,
      pr1646v2PbbEthOamEDelayMegIdMaintDomainName
         DisplayString,
      pr1646v2PbbEthOamEDelayMegIdShortMaName
         DisplayString,
      pr1646v2PbbEthOamEDelayMepId
         INTEGER,
      pr1646v2PbbEthOamEDelayMacAddress
         OCTET STRING,
      pr1646v2PbbEthOamEDelayPriority
         Integer32,
      pr1646v2PbbEthOamEDelayNbrOfTxFrames
         Counter32,
      pr1646v2PbbEthOamEDelayNbrOfRxFrames
         Counter32,
      pr1646v2PbbEthOamEDelayLoss
         Counter32,
      pr1646v2PbbEthOamEDelayDelayMin
         Integer32,
      pr1646v2PbbEthOamEDelayDelayAvrg
         Integer32,
      pr1646v2PbbEthOamEDelayDelayMax
         Integer32,
      pr1646v2PbbEthOamEDelayJitterNegMax
         Integer32,
      pr1646v2PbbEthOamEDelayJitterAvrg
         Integer32,
      pr1646v2PbbEthOamEDelayJitterPosMax
         Integer32
      }

pr1646v2PbbEthOamEDelayGlobalIx OBJECT-TYPE
   SYNTAX      GlobalIndex
   MAX-ACCESS  not-accessible
   STATUS      current
   DESCRIPTION
      "The value of the tlsCntTreeGlobalIndex of the MANAGED OBJECT."
   ::= {pr1646v2PbbEthOamEDelayEntry 10}

pr1646v2PbbEthOamEDelayTableIx OBJECT-TYPE
   SYNTAX      TableIndex
   MAX-ACCESS  not-accessible
   STATUS      current
   DESCRIPTION
      ""
   ::= {pr1646v2PbbEthOamEDelayEntry 11}

pr1646v2PbbEthOamEDelayMepName OBJECT-TYPE
   SYNTAX      DisplayString
   MAX-ACCESS  read-only
   STATUS      current
   DESCRIPTION
      "Path: ethOam.performance.delay.mepName"
   ::= {pr1646v2PbbEthOamEDelayEntry 16777216}

pr1646v2PbbEthOamEDelayMegLevel OBJECT-TYPE
   SYNTAX      Integer32
   MAX-ACCESS  read-only
   STATUS      current
   DESCRIPTION
      "Path: ethOam.performance.delay.megLevel"
   ::= {pr1646v2PbbEthOamEDelayEntry 33554432}

pr1646v2PbbEthOamEDelayMegIdMaintDomainName OBJECT-TYPE
   SYNTAX      DisplayString
   MAX-ACCESS  read-only
   STATUS      current
   DESCRIPTION
      "Path: ethOam.performance.delay.megId.maintDomainName"
   ::= {pr1646v2PbbEthOamEDelayEntry 50397184}

pr1646v2PbbEthOamEDelayMegIdShortMaName OBJECT-TYPE
   SYNTAX      DisplayString
   MAX-ACCESS  read-only
   STATUS      current
   DESCRIPTION
      "Path: ethOam.performance.delay.megId.shortMaName"
   ::= {pr1646v2PbbEthOamEDelayEntry 50462720}

pr1646v2PbbEthOamEDelayMepId OBJECT-TYPE
   SYNTAX      INTEGER
               {
               unknown (8192)
               }
   MAX-ACCESS  read-only
   STATUS      current
   DESCRIPTION
      "Path: ethOam.performance.delay.mepId

       Possibilities:
               unknown   (8192)"
   ::= {pr1646v2PbbEthOamEDelayEntry 67108864}

pr1646v2PbbEthOamEDelayMacAddress OBJECT-TYPE
   SYNTAX      OCTET STRING
   MAX-ACCESS  read-only
   STATUS      current
   DESCRIPTION
      "Path: ethOam.performance.delay.macAddress

       MAC address."
   ::= {pr1646v2PbbEthOamEDelayEntry 83886080}

pr1646v2PbbEthOamEDelayPriority OBJECT-TYPE
   SYNTAX      Integer32
   MAX-ACCESS  read-only
   STATUS      current
   DESCRIPTION
      "Path: ethOam.performance.delay.priority"
   ::= {pr1646v2PbbEthOamEDelayEntry 100663296}

pr1646v2PbbEthOamEDelayNbrOfTxFrames OBJECT-TYPE
   SYNTAX      Counter32
   MAX-ACCESS  read-only
   STATUS      current
   DESCRIPTION
      "Path: ethOam.performance.delay.nbrOfTxFrames

       32 bit unsigned wrappable counter."
   ::= {pr1646v2PbbEthOamEDelayEntry 117440512}

pr1646v2PbbEthOamEDelayNbrOfRxFrames OBJECT-TYPE
   SYNTAX      Counter32
   MAX-ACCESS  read-only
   STATUS      current
   DESCRIPTION
      "Path: ethOam.performance.delay.nbrOfRxFrames

       32 bit unsigned wrappable counter."
   ::= {pr1646v2PbbEthOamEDelayEntry 134217728}

pr1646v2PbbEthOamEDelayLoss OBJECT-TYPE
   SYNTAX      Counter32
   MAX-ACCESS  read-only
   STATUS      current
   DESCRIPTION
      "Path: ethOam.performance.delay.loss

       32 bit unsigned wrappable counter."
   ::= {pr1646v2PbbEthOamEDelayEntry 150994944}

pr1646v2PbbEthOamEDelayDelayMin OBJECT-TYPE
   SYNTAX      Integer32
   MAX-ACCESS  read-only
   STATUS      current
   DESCRIPTION
      "Path: ethOam.performance.delay.delayMin

       unit name = sec
       formula = 1000 / ; 1000 *"
   ::= {pr1646v2PbbEthOamEDelayEntry 184549376}

pr1646v2PbbEthOamEDelayDelayAvrg OBJECT-TYPE
   SYNTAX      Integer32
   MAX-ACCESS  read-only
   STATUS      current
   DESCRIPTION
      "Path: ethOam.performance.delay.delayAvrg

       unit name = sec
       formula = 1000 / ; 1000 *"
   ::= {pr1646v2PbbEthOamEDelayEntry 201326592}

pr1646v2PbbEthOamEDelayDelayMax OBJECT-TYPE
   SYNTAX      Integer32
   MAX-ACCESS  read-only
   STATUS      current
   DESCRIPTION
      "Path: ethOam.performance.delay.delayMax

       unit name = sec
       formula = 1000 / ; 1000 *"
   ::= {pr1646v2PbbEthOamEDelayEntry 218103808}

pr1646v2PbbEthOamEDelayJitterNegMax OBJECT-TYPE
   SYNTAX      Integer32
   MAX-ACCESS  read-only
   STATUS      current
   DESCRIPTION
      "Path: ethOam.performance.delay.jitterNegMax

       unit name = sec
       formula = 1000 / ; 1000 *"
   ::= {pr1646v2PbbEthOamEDelayEntry 234881024}

pr1646v2PbbEthOamEDelayJitterAvrg OBJECT-TYPE
   SYNTAX      Integer32
   MAX-ACCESS  read-only
   STATUS      current
   DESCRIPTION
      "Path: ethOam.performance.delay.jitterAvrg

       unit name = sec
       formula = 1000 / ; 1000 *"
   ::= {pr1646v2PbbEthOamEDelayEntry 251658240}

pr1646v2PbbEthOamEDelayJitterPosMax OBJECT-TYPE
   SYNTAX      Integer32
   MAX-ACCESS  read-only
   STATUS      current
   DESCRIPTION
      "Path: ethOam.performance.delay.jitterPosMax

       unit name = sec
       formula = 1000 / ; 1000 *"
   ::= {pr1646v2PbbEthOamEDelayEntry 268435456}

pr1646v2PbbEthOamEDelayLogging OBJECT-TYPE
   SYNTAX      SEQUENCE OF Pr1646v2PbbEthOamEDelayLoggingEntry
   MAX-ACCESS  not-accessible
   STATUS      current
   DESCRIPTION
      ""
   ::= {pr1646v2PbbEthOamEDelay 285212672}

pr1646v2PbbEthOamEDelayLoggingEntry OBJECT-TYPE
   SYNTAX      Pr1646v2PbbEthOamEDelayLoggingEntry
   MAX-ACCESS  not-accessible
   STATUS      current
   DESCRIPTION
      ""
   INDEX      { pr1646v2PbbEthOamEDelayLoggingGlobalIx,
                pr1646v2PbbEthOamEDelayTableIx,
                pr1646v2PbbEthOamEDelayLoggingTableIx }
   ::= {pr1646v2PbbEthOamEDelayLogging 1}

Pr1646v2PbbEthOamEDelayLoggingEntry ::=
   SEQUENCE
      {
      pr1646v2PbbEthOamEDelayLoggingGlobalIx
         GlobalIndex,
      pr1646v2PbbEthOamEDelayLoggingTableIx
         TableIndex,
      pr1646v2PbbEthOamEDelayLoggingSysUpTime
         TimeTicks,
      pr1646v2PbbEthOamEDelayLoggingNbrTxFrm
         Counter32,
      pr1646v2PbbEthOamEDelayLoggingNbrRxFrm
         Counter32,
      pr1646v2PbbEthOamEDelayLoggingLoss
         Counter32,
      pr1646v2PbbEthOamEDelayLoggingDelayMin
         Integer32,
      pr1646v2PbbEthOamEDelayLoggingDelayAvrg
         Integer32,
      pr1646v2PbbEthOamEDelayLoggingDelayMax
         Integer32,
      pr1646v2PbbEthOamEDelayLoggingJitterNegMax
         Integer32,
      pr1646v2PbbEthOamEDelayLoggingJitterAvrg
         Integer32,
      pr1646v2PbbEthOamEDelayLoggingJitterPosMax
         Integer32
      }

pr1646v2PbbEthOamEDelayLoggingGlobalIx OBJECT-TYPE
   SYNTAX      GlobalIndex
   MAX-ACCESS  not-accessible
   STATUS      current
   DESCRIPTION
      "The value of the tlsCntTreeGlobalIndex of the MANAGED OBJECT."
   ::= {pr1646v2PbbEthOamEDelayLoggingEntry 10}

pr1646v2PbbEthOamEDelayLoggingTableIx OBJECT-TYPE
   SYNTAX      TableIndex
   MAX-ACCESS  not-accessible
   STATUS      current
   DESCRIPTION
      ""
   ::= {pr1646v2PbbEthOamEDelayLoggingEntry 11}

pr1646v2PbbEthOamEDelayLoggingSysUpTime OBJECT-TYPE
   SYNTAX      TimeTicks
   MAX-ACCESS  read-only
   STATUS      current
   DESCRIPTION
      "Path: ethOam.performance.delay.logging.sysUpTime

       Time in centi-second."
   ::= {pr1646v2PbbEthOamEDelayLoggingEntry 16777216}

pr1646v2PbbEthOamEDelayLoggingNbrTxFrm OBJECT-TYPE
   SYNTAX      Counter32
   MAX-ACCESS  read-only
   STATUS      current
   DESCRIPTION
      "Path: ethOam.performance.delay.logging.nbrOfTxFrames

       32 bit unsigned wrappable counter."
   ::= {pr1646v2PbbEthOamEDelayLoggingEntry 33554432}

pr1646v2PbbEthOamEDelayLoggingNbrRxFrm OBJECT-TYPE
   SYNTAX      Counter32
   MAX-ACCESS  read-only
   STATUS      current
   DESCRIPTION
      "Path: ethOam.performance.delay.logging.nbrOfRxFrames

       32 bit unsigned wrappable counter."
   ::= {pr1646v2PbbEthOamEDelayLoggingEntry 50331648}

pr1646v2PbbEthOamEDelayLoggingLoss OBJECT-TYPE
   SYNTAX      Counter32
   MAX-ACCESS  read-only
   STATUS      current
   DESCRIPTION
      "Path: ethOam.performance.delay.logging.loss

       32 bit unsigned wrappable counter."
   ::= {pr1646v2PbbEthOamEDelayLoggingEntry 67108864}

pr1646v2PbbEthOamEDelayLoggingDelayMin OBJECT-TYPE
   SYNTAX      Integer32
   MAX-ACCESS  read-only
   STATUS      current
   DESCRIPTION
      "Path: ethOam.performance.delay.logging.delayMin

       unit name = sec
       formula = 1000 / ; 1000 *"
   ::= {pr1646v2PbbEthOamEDelayLoggingEntry 100663296}

pr1646v2PbbEthOamEDelayLoggingDelayAvrg OBJECT-TYPE
   SYNTAX      Integer32
   MAX-ACCESS  read-only
   STATUS      current
   DESCRIPTION
      "Path: ethOam.performance.delay.logging.delayAvrg

       unit name = sec
       formula = 1000 / ; 1000 *"
   ::= {pr1646v2PbbEthOamEDelayLoggingEntry 117440512}

pr1646v2PbbEthOamEDelayLoggingDelayMax OBJECT-TYPE
   SYNTAX      Integer32
   MAX-ACCESS  read-only
   STATUS      current
   DESCRIPTION
      "Path: ethOam.performance.delay.logging.delayMax

       unit name = sec
       formula = 1000 / ; 1000 *"
   ::= {pr1646v2PbbEthOamEDelayLoggingEntry 134217728}

pr1646v2PbbEthOamEDelayLoggingJitterNegMax OBJECT-TYPE
   SYNTAX      Integer32
   MAX-ACCESS  read-only
   STATUS      current
   DESCRIPTION
      "Path: ethOam.performance.delay.logging.jitterNegMax

       unit name = sec
       formula = 1000 / ; 1000 *"
   ::= {pr1646v2PbbEthOamEDelayLoggingEntry 150994944}

pr1646v2PbbEthOamEDelayLoggingJitterAvrg OBJECT-TYPE
   SYNTAX      Integer32
   MAX-ACCESS  read-only
   STATUS      current
   DESCRIPTION
      "Path: ethOam.performance.delay.logging.jitterAvrg

       unit name = sec
       formula = 1000 / ; 1000 *"
   ::= {pr1646v2PbbEthOamEDelayLoggingEntry 167772160}

pr1646v2PbbEthOamEDelayLoggingJitterPosMax OBJECT-TYPE
   SYNTAX      Integer32
   MAX-ACCESS  read-only
   STATUS      current
   DESCRIPTION
      "Path: ethOam.performance.delay.logging.jitterPosMax

       unit name = sec
       formula = 1000 / ; 1000 *"
   ::= {pr1646v2PbbEthOamEDelayLoggingEntry 184549376}


pr1646v2PbbEthOamESlmPerf OBJECT IDENTIFIER ::= {pr1646v2PbbEthOamE 41}

pr1646v2PbbEthOamESlmPerfSSCTable OBJECT-TYPE
   SYNTAX      SEQUENCE OF Pr1646v2PbbEthOamESlmPerfEntry
   MAX-ACCESS  not-accessible
   STATUS      current
   DESCRIPTION
      "synthetic loss performance table"
   ::= {pr1646v2PbbEthOamESlmPerf 1}

pr1646v2PbbEthOamESlmPerfEntry OBJECT-TYPE
   SYNTAX      Pr1646v2PbbEthOamESlmPerfEntry
   MAX-ACCESS  not-accessible
   STATUS      current
   DESCRIPTION
      ""
   INDEX      { pr1646v2PbbEthOamESlmPerfGlobalIx,
                pr1646v2PbbEthOamESlmPerfTableIx }
   ::= {pr1646v2PbbEthOamESlmPerfSSCTable 1}

Pr1646v2PbbEthOamESlmPerfEntry ::=
   SEQUENCE
      {
      pr1646v2PbbEthOamESlmPerfGlobalIx
         GlobalIndex,
      pr1646v2PbbEthOamESlmPerfTableIx
         TableIndex,
      pr1646v2PbbEthOamESlmPerfName
         DisplayString,
      pr1646v2PbbEthOamESlmPerfStatus
         INTEGER,
      pr1646v2PbbEthOamESlmPerfMepName
         DisplayString,
      pr1646v2PbbEthOamESlmPerfMegLevel
         Integer32,
      pr1646v2PbbEthOamESlmPerfMegIdMaintDomainName
         DisplayString,
      pr1646v2PbbEthOamESlmPerfMegIdShortMaName
         DisplayString,
      pr1646v2PbbEthOamESlmPerfMepId
         INTEGER,
      pr1646v2PbbEthOamESlmPerfMacAddress
         OCTET STRING,
      pr1646v2PbbEthOamESlmPerfPriority
         Integer32,
      pr1646v2PbbEthOamESlmPerfRsltSingleCurrentTx
         Counter32,
      pr1646v2PbbEthOamESlmPerfRsltSingleCurrentRx
         Counter32,
      pr1646v2PbbEthOamESlmPerfRsltSingleCurrentBad
         Counter32,
      pr1646v2PbbEthOamESlmPerfRsltSingleCurrentLate
         Counter32,
      pr1646v2PbbEthOamESlmPerfRsltSingleCurrentTxfcf
         Counter32,
      pr1646v2PbbEthOamESlmPerfRsltSingleCurrentDupslm
         Counter32,
      pr1646v2PbbEthOamESlmPerfRsltSingleCurrentDupslr
         Counter32,
      pr1646v2PbbEthOamESlmPerfRsltSingleCurrentSeqslm
         Counter32,
      pr1646v2PbbEthOamESlmPerfRsltSingleCurrentSeqslr
         Counter32,
      pr1646v2PbbEthOamESlmPerfRsltSingleCurrentNeLoss
         INTEGER,
      pr1646v2PbbEthOamESlmPerfRsltSingleCurrentFeLoss
         INTEGER,
      pr1646v2PbbEthOamESlmPerfRsltSingleOverallTx
         Counter32,
      pr1646v2PbbEthOamESlmPerfRsltSingleOverallRx
         Counter32,
      pr1646v2PbbEthOamESlmPerfRsltSingleOverallBad
         Counter32,
      pr1646v2PbbEthOamESlmPerfRsltSingleOverallLate
         Counter32,
      pr1646v2PbbEthOamESlmPerfRsltSingleOverallTxfcf
         Counter32,
      pr1646v2PbbEthOamESlmPerfRsltSingleOverallDupslm
         Counter32,
      pr1646v2PbbEthOamESlmPerfRsltSingleOverallDupslr
         Counter32,
      pr1646v2PbbEthOamESlmPerfRsltSingleOverallSeqslm
         Counter32,
      pr1646v2PbbEthOamESlmPerfRsltSingleOverallSeqslr
         Counter32,
      pr1646v2PbbEthOamESlmPerfRsltSingleOverallFail
         Counter32,
      pr1646v2PbbEthOamESlmPerfRsltSingleOverallNeLoss
         INTEGER,
      pr1646v2PbbEthOamESlmPerfRsltSingleOverallFeLoss
         INTEGER,
      pr1646v2PbbEthOamESlmPerfRsltDualNbrOfTxFrames
         Counter32,
      pr1646v2PbbEthOamESlmPerfRsltDualNbrOfTxFramesOverall
         Counter32
      }

pr1646v2PbbEthOamESlmPerfGlobalIx OBJECT-TYPE
   SYNTAX      GlobalIndex
   MAX-ACCESS  not-accessible
   STATUS      current
   DESCRIPTION
      "The value of the tlsCntTreeGlobalIndex of the MANAGED OBJECT."
   ::= {pr1646v2PbbEthOamESlmPerfEntry 10}

pr1646v2PbbEthOamESlmPerfTableIx OBJECT-TYPE
   SYNTAX      TableIndex
   MAX-ACCESS  not-accessible
   STATUS      current
   DESCRIPTION
      ""
   ::= {pr1646v2PbbEthOamESlmPerfEntry 11}

pr1646v2PbbEthOamESlmPerfName OBJECT-TYPE
   SYNTAX      DisplayString
   MAX-ACCESS  read-only
   STATUS      current
   DESCRIPTION
      "Path: ethOam.performance.synthLoss.name"
   ::= {pr1646v2PbbEthOamESlmPerfEntry 134217728}

pr1646v2PbbEthOamESlmPerfStatus OBJECT-TYPE
   SYNTAX      INTEGER
               {
               running (1),
               notRunning (2),
               waiting (3)
               }
   MAX-ACCESS  read-only
   STATUS      current
   DESCRIPTION
      "Path: ethOam.performance.synthLoss.status

       Possibilities:
               running   (1)
               notRunning   (2)
               waiting   (3)"
   ::= {pr1646v2PbbEthOamESlmPerfEntry 150994944}

pr1646v2PbbEthOamESlmPerfMepName OBJECT-TYPE
   SYNTAX      DisplayString
   MAX-ACCESS  read-only
   STATUS      current
   DESCRIPTION
      "Path: ethOam.performance.synthLoss.mepName"
   ::= {pr1646v2PbbEthOamESlmPerfEntry 16777216}

pr1646v2PbbEthOamESlmPerfMegLevel OBJECT-TYPE
   SYNTAX      Integer32
   MAX-ACCESS  read-only
   STATUS      current
   DESCRIPTION
      "Path: ethOam.performance.synthLoss.megLevel"
   ::= {pr1646v2PbbEthOamESlmPerfEntry 33554432}

pr1646v2PbbEthOamESlmPerfMegIdMaintDomainName OBJECT-TYPE
   SYNTAX      DisplayString
   MAX-ACCESS  read-only
   STATUS      current
   DESCRIPTION
      "Path: ethOam.performance.synthLoss.megId.maintDomainName"
   ::= {pr1646v2PbbEthOamESlmPerfEntry 50397184}

pr1646v2PbbEthOamESlmPerfMegIdShortMaName OBJECT-TYPE
   SYNTAX      DisplayString
   MAX-ACCESS  read-only
   STATUS      current
   DESCRIPTION
      "Path: ethOam.performance.synthLoss.megId.shortMaName"
   ::= {pr1646v2PbbEthOamESlmPerfEntry 50462720}

pr1646v2PbbEthOamESlmPerfMepId OBJECT-TYPE
   SYNTAX      INTEGER
               {
               unknown (8192)
               }
   MAX-ACCESS  read-only
   STATUS      current
   DESCRIPTION
      "Path: ethOam.performance.synthLoss.mepId

       Possibilities:
               unknown   (8192)"
   ::= {pr1646v2PbbEthOamESlmPerfEntry 67108864}

pr1646v2PbbEthOamESlmPerfMacAddress OBJECT-TYPE
   SYNTAX      OCTET STRING
   MAX-ACCESS  read-only
   STATUS      current
   DESCRIPTION
      "Path: ethOam.performance.synthLoss.macAddress

       MAC address."
   ::= {pr1646v2PbbEthOamESlmPerfEntry 83886080}

pr1646v2PbbEthOamESlmPerfPriority OBJECT-TYPE
   SYNTAX      Integer32
   MAX-ACCESS  read-only
   STATUS      current
   DESCRIPTION
      "Path: ethOam.performance.synthLoss.priority"
   ::= {pr1646v2PbbEthOamESlmPerfEntry 100663296}

pr1646v2PbbEthOamESlmPerfRsltSingleCurrentTx OBJECT-TYPE
   SYNTAX      Counter32
   MAX-ACCESS  read-only
   STATUS      current
   DESCRIPTION
      "Path: ethOam.performance.synthLoss.result.singleEnded.current.nbrOfTxFrames

       32 bit unsigned wrappable counter."
   ::= {pr1646v2PbbEthOamESlmPerfEntry 117506305}

pr1646v2PbbEthOamESlmPerfRsltSingleCurrentRx OBJECT-TYPE
   SYNTAX      Counter32
   MAX-ACCESS  read-only
   STATUS      current
   DESCRIPTION
      "Path: ethOam.performance.synthLoss.result.singleEnded.current.nbrOfRxFrames

       32 bit unsigned wrappable counter."
   ::= {pr1646v2PbbEthOamESlmPerfEntry 117506306}

pr1646v2PbbEthOamESlmPerfRsltSingleCurrentBad OBJECT-TYPE
   SYNTAX      Counter32
   MAX-ACCESS  read-only
   STATUS      current
   DESCRIPTION
      "Path: ethOam.performance.synthLoss.result.singleEnded.current.nbrOfBadDataFrames

       32 bit unsigned wrappable counter."
   ::= {pr1646v2PbbEthOamESlmPerfEntry 117506307}

pr1646v2PbbEthOamESlmPerfRsltSingleCurrentLate OBJECT-TYPE
   SYNTAX      Counter32
   MAX-ACCESS  read-only
   STATUS      current
   DESCRIPTION
      "Path: ethOam.performance.synthLoss.result.singleEnded.current.nbrOfLateFrames

       32 bit unsigned wrappable counter."
   ::= {pr1646v2PbbEthOamESlmPerfEntry 117506308}

pr1646v2PbbEthOamESlmPerfRsltSingleCurrentTxfcf OBJECT-TYPE
   SYNTAX      Counter32
   MAX-ACCESS  read-only
   STATUS      current
   DESCRIPTION
      "Path: ethOam.performance.synthLoss.result.singleEnded.current.nbrOfOutOfRangeFrames

       32 bit unsigned wrappable counter."
   ::= {pr1646v2PbbEthOamESlmPerfEntry 117506312}

pr1646v2PbbEthOamESlmPerfRsltSingleCurrentDupslm OBJECT-TYPE
   SYNTAX      Counter32
   MAX-ACCESS  read-only
   STATUS      current
   DESCRIPTION
      "Path: ethOam.performance.synthLoss.result.singleEnded.current.nbrOfDuplicateSlm

       32 bit unsigned wrappable counter."
   ::= {pr1646v2PbbEthOamESlmPerfEntry 117506313}

pr1646v2PbbEthOamESlmPerfRsltSingleCurrentDupslr OBJECT-TYPE
   SYNTAX      Counter32
   MAX-ACCESS  read-only
   STATUS      current
   DESCRIPTION
      "Path: ethOam.performance.synthLoss.result.singleEnded.current.nbrOfDuplicateSlr

       32 bit unsigned wrappable counter."
   ::= {pr1646v2PbbEthOamESlmPerfEntry 117506314}

pr1646v2PbbEthOamESlmPerfRsltSingleCurrentSeqslm OBJECT-TYPE
   SYNTAX      Counter32
   MAX-ACCESS  read-only
   STATUS      current
   DESCRIPTION
      "Path: ethOam.performance.synthLoss.result.singleEnded.current.nbrOfSlmSeqError

       32 bit unsigned wrappable counter."
   ::= {pr1646v2PbbEthOamESlmPerfEntry 117506315}

pr1646v2PbbEthOamESlmPerfRsltSingleCurrentSeqslr OBJECT-TYPE
   SYNTAX      Counter32
   MAX-ACCESS  read-only
   STATUS      current
   DESCRIPTION
      "Path: ethOam.performance.synthLoss.result.singleEnded.current.nbrOfSlrSeqError

       32 bit unsigned wrappable counter."
   ::= {pr1646v2PbbEthOamESlmPerfEntry 117506316}

pr1646v2PbbEthOamESlmPerfRsltSingleCurrentNeLoss OBJECT-TYPE
   SYNTAX      INTEGER
               {
               invalid (2147483647)
               }
   MAX-ACCESS  read-only
   STATUS      current
   DESCRIPTION
      "Path: ethOam.performance.synthLoss.result.singleEnded.current.nearEndLoss

       Possibilities:
               invalid   (2147483647)"
   ::= {pr1646v2PbbEthOamESlmPerfEntry 117506310}

pr1646v2PbbEthOamESlmPerfRsltSingleCurrentFeLoss OBJECT-TYPE
   SYNTAX      INTEGER
               {
               invalid (2147483647)
               }
   MAX-ACCESS  read-only
   STATUS      current
   DESCRIPTION
      "Path: ethOam.performance.synthLoss.result.singleEnded.current.farEndLoss

       Possibilities:
               invalid   (2147483647)"
   ::= {pr1646v2PbbEthOamESlmPerfEntry 117506311}

pr1646v2PbbEthOamESlmPerfRsltSingleOverallTx OBJECT-TYPE
   SYNTAX      Counter32
   MAX-ACCESS  read-only
   STATUS      current
   DESCRIPTION
      "Path: ethOam.performance.synthLoss.result.singleEnded.overall.nbrOfTxFrames

       32 bit unsigned wrappable counter."
   ::= {pr1646v2PbbEthOamESlmPerfEntry 117506561}

pr1646v2PbbEthOamESlmPerfRsltSingleOverallRx OBJECT-TYPE
   SYNTAX      Counter32
   MAX-ACCESS  read-only
   STATUS      current
   DESCRIPTION
      "Path: ethOam.performance.synthLoss.result.singleEnded.overall.nbrOfRxFrames

       32 bit unsigned wrappable counter."
   ::= {pr1646v2PbbEthOamESlmPerfEntry 117506562}

pr1646v2PbbEthOamESlmPerfRsltSingleOverallBad OBJECT-TYPE
   SYNTAX      Counter32
   MAX-ACCESS  read-only
   STATUS      current
   DESCRIPTION
      "Path: ethOam.performance.synthLoss.result.singleEnded.overall.nbrOfBadDataFrames

       32 bit unsigned wrappable counter."
   ::= {pr1646v2PbbEthOamESlmPerfEntry 117506563}

pr1646v2PbbEthOamESlmPerfRsltSingleOverallLate OBJECT-TYPE
   SYNTAX      Counter32
   MAX-ACCESS  read-only
   STATUS      current
   DESCRIPTION
      "Path: ethOam.performance.synthLoss.result.singleEnded.overall.nbrOfLateFrames

       32 bit unsigned wrappable counter."
   ::= {pr1646v2PbbEthOamESlmPerfEntry 117506564}

pr1646v2PbbEthOamESlmPerfRsltSingleOverallTxfcf OBJECT-TYPE
   SYNTAX      Counter32
   MAX-ACCESS  read-only
   STATUS      current
   DESCRIPTION
      "Path: ethOam.performance.synthLoss.result.singleEnded.overall.nbrOfOutOfRangeFrames

       32 bit unsigned wrappable counter."
   ::= {pr1646v2PbbEthOamESlmPerfEntry 117506568}

pr1646v2PbbEthOamESlmPerfRsltSingleOverallDupslm OBJECT-TYPE
   SYNTAX      Counter32
   MAX-ACCESS  read-only
   STATUS      current
   DESCRIPTION
      "Path: ethOam.performance.synthLoss.result.singleEnded.overall.nbrOfDuplicateSlm

       32 bit unsigned wrappable counter."
   ::= {pr1646v2PbbEthOamESlmPerfEntry 117506569}

pr1646v2PbbEthOamESlmPerfRsltSingleOverallDupslr OBJECT-TYPE
   SYNTAX      Counter32
   MAX-ACCESS  read-only
   STATUS      current
   DESCRIPTION
      "Path: ethOam.performance.synthLoss.result.singleEnded.overall.nbrOfDuplicateSlr

       32 bit unsigned wrappable counter."
   ::= {pr1646v2PbbEthOamESlmPerfEntry 117506570}

pr1646v2PbbEthOamESlmPerfRsltSingleOverallSeqslm OBJECT-TYPE
   SYNTAX      Counter32
   MAX-ACCESS  read-only
   STATUS      current
   DESCRIPTION
      "Path: ethOam.performance.synthLoss.result.singleEnded.overall.nbrOfSlmSeqError

       32 bit unsigned wrappable counter."
   ::= {pr1646v2PbbEthOamESlmPerfEntry 117506571}

pr1646v2PbbEthOamESlmPerfRsltSingleOverallSeqslr OBJECT-TYPE
   SYNTAX      Counter32
   MAX-ACCESS  read-only
   STATUS      current
   DESCRIPTION
      "Path: ethOam.performance.synthLoss.result.singleEnded.overall.nbrOfSlrSeqError

       32 bit unsigned wrappable counter."
   ::= {pr1646v2PbbEthOamESlmPerfEntry 117506572}

pr1646v2PbbEthOamESlmPerfRsltSingleOverallFail OBJECT-TYPE
   SYNTAX      Counter32
   MAX-ACCESS  read-only
   STATUS      current
   DESCRIPTION
      "Path: ethOam.performance.synthLoss.result.singleEnded.overall.nbrFailedTests

       32 bit unsigned wrappable counter."
   ::= {pr1646v2PbbEthOamESlmPerfEntry 117506565}

pr1646v2PbbEthOamESlmPerfRsltSingleOverallNeLoss OBJECT-TYPE
   SYNTAX      INTEGER
               {
               invalid (2147483647)
               }
   MAX-ACCESS  read-only
   STATUS      current
   DESCRIPTION
      "Path: ethOam.performance.synthLoss.result.singleEnded.overall.nearEndLoss

       Possibilities:
               invalid   (2147483647)"
   ::= {pr1646v2PbbEthOamESlmPerfEntry 117506566}

pr1646v2PbbEthOamESlmPerfRsltSingleOverallFeLoss OBJECT-TYPE
   SYNTAX      INTEGER
               {
               invalid (2147483647)
               }
   MAX-ACCESS  read-only
   STATUS      current
   DESCRIPTION
      "Path: ethOam.performance.synthLoss.result.singleEnded.overall.farEndLoss

       Possibilities:
               invalid   (2147483647)"
   ::= {pr1646v2PbbEthOamESlmPerfEntry 117506567}

pr1646v2PbbEthOamESlmPerfRsltDualNbrOfTxFrames OBJECT-TYPE
   SYNTAX      Counter32
   MAX-ACCESS  read-only
   STATUS      current
   DESCRIPTION
      "Path: ethOam.performance.synthLoss.result.dualEnded.nbrOfTxFrames

       32 bit unsigned wrappable counter."
   ::= {pr1646v2PbbEthOamESlmPerfEntry 117571840}

pr1646v2PbbEthOamESlmPerfRsltDualNbrOfTxFramesOverall OBJECT-TYPE
   SYNTAX      Counter32
   MAX-ACCESS  read-only
   STATUS      current
   DESCRIPTION
      "Path: ethOam.performance.synthLoss.result.dualEnded.nbrOfTxFramesOverall

       32 bit unsigned wrappable counter."
   ::= {pr1646v2PbbEthOamESlmPerfEntry 117572096}

pr1646v2PbbEthOamESlmPerfRsltSingleErrorLog OBJECT-TYPE
   SYNTAX      SEQUENCE OF Pr1646v2PbbEthOamESlmPerfRsltSingleErrorLogEntry
   MAX-ACCESS  not-accessible
   STATUS      current
   DESCRIPTION
      ""
   ::= {pr1646v2PbbEthOamESlmPerf 117506816}

pr1646v2PbbEthOamESlmPerfRsltSingleErrorLogEntry OBJECT-TYPE
   SYNTAX      Pr1646v2PbbEthOamESlmPerfRsltSingleErrorLogEntry
   MAX-ACCESS  not-accessible
   STATUS      current
   DESCRIPTION
      ""
   INDEX      { pr1646v2PbbEthOamESlmPerfRsltSingleErrorLogGlobalIx,
                pr1646v2PbbEthOamESlmPerfTableIx,
                pr1646v2PbbEthOamESlmPerfRsltSingleErrorLogTableIx }
   ::= {pr1646v2PbbEthOamESlmPerfRsltSingleErrorLog 1}

Pr1646v2PbbEthOamESlmPerfRsltSingleErrorLogEntry ::=
   SEQUENCE
      {
      pr1646v2PbbEthOamESlmPerfRsltSingleErrorLogGlobalIx
         GlobalIndex,
      pr1646v2PbbEthOamESlmPerfRsltSingleErrorLogTableIx
         TableIndex,
      pr1646v2PbbEthOamESlmPerfRsltSingleErrorLogTimeStamp
         DisplayString,
      pr1646v2PbbEthOamESlmPerfRsltSingleErrorLogSysUpTime
         TimeTicks,
      pr1646v2PbbEthOamESlmPerfRsltSingleErrorLogNbrOfTxFrames
         Counter32,
      pr1646v2PbbEthOamESlmPerfRsltSingleErrorLogNbrOfRxFrames
         Counter32,
      pr1646v2PbbEthOamESlmPerfRsltSingleErrorLogNbrOfBadDataFrames
         Counter32,
      pr1646v2PbbEthOamESlmPerfRsltSingleErrorLogNbrOfLateFrames
         Counter32,
      pr1646v2PbbEthOamESlmPerfRsltSingleErrorLogNbrOfDuplicateSlm
         Counter32,
      pr1646v2PbbEthOamESlmPerfRsltSingleErrorLogNbrOfDuplicateSlr
         Counter32,
      pr1646v2PbbEthOamESlmPerfRsltSingleErrorLogNbrOfSlmSeqError
         Counter32,
      pr1646v2PbbEthOamESlmPerfRsltSingleErrorLogNbrOfSlrSeqError
         Counter32,
      pr1646v2PbbEthOamESlmPerfRsltSingleErrorLogNearEndLoss
         INTEGER,
      pr1646v2PbbEthOamESlmPerfRsltSingleErrorLogFarEndLoss
         INTEGER
      }

pr1646v2PbbEthOamESlmPerfRsltSingleErrorLogGlobalIx OBJECT-TYPE
   SYNTAX      GlobalIndex
   MAX-ACCESS  not-accessible
   STATUS      current
   DESCRIPTION
      "The value of the tlsCntTreeGlobalIndex of the MANAGED OBJECT."
   ::= {pr1646v2PbbEthOamESlmPerfRsltSingleErrorLogEntry 10}

pr1646v2PbbEthOamESlmPerfRsltSingleErrorLogTableIx OBJECT-TYPE
   SYNTAX      TableIndex
   MAX-ACCESS  not-accessible
   STATUS      current
   DESCRIPTION
      ""
   ::= {pr1646v2PbbEthOamESlmPerfRsltSingleErrorLogEntry 11}

pr1646v2PbbEthOamESlmPerfRsltSingleErrorLogTimeStamp OBJECT-TYPE
   SYNTAX      DisplayString
   MAX-ACCESS  read-only
   STATUS      current
   DESCRIPTION
      "Path: ethOam.performance.synthLoss.result.singleEnded.errorLog.timeStamp"
   ::= {pr1646v2PbbEthOamESlmPerfRsltSingleErrorLogEntry 134217728}

pr1646v2PbbEthOamESlmPerfRsltSingleErrorLogSysUpTime OBJECT-TYPE
   SYNTAX      TimeTicks
   MAX-ACCESS  read-only
   STATUS      current
   DESCRIPTION
      "Path: ethOam.performance.synthLoss.result.singleEnded.errorLog.sysUpTime

       Time in centi-second."
   ::= {pr1646v2PbbEthOamESlmPerfRsltSingleErrorLogEntry 16777216}

pr1646v2PbbEthOamESlmPerfRsltSingleErrorLogNbrOfTxFrames OBJECT-TYPE
   SYNTAX      Counter32
   MAX-ACCESS  read-only
   STATUS      current
   DESCRIPTION
      "Path: ethOam.performance.synthLoss.result.singleEnded.errorLog.nbrOfTxFrames

       32 bit unsigned wrappable counter."
   ::= {pr1646v2PbbEthOamESlmPerfRsltSingleErrorLogEntry 33554432}

pr1646v2PbbEthOamESlmPerfRsltSingleErrorLogNbrOfRxFrames OBJECT-TYPE
   SYNTAX      Counter32
   MAX-ACCESS  read-only
   STATUS      current
   DESCRIPTION
      "Path: ethOam.performance.synthLoss.result.singleEnded.errorLog.nbrOfRxFrames

       32 bit unsigned wrappable counter."
   ::= {pr1646v2PbbEthOamESlmPerfRsltSingleErrorLogEntry 50331648}

pr1646v2PbbEthOamESlmPerfRsltSingleErrorLogNbrOfBadDataFrames OBJECT-TYPE
   SYNTAX      Counter32
   MAX-ACCESS  read-only
   STATUS      current
   DESCRIPTION
      "Path: ethOam.performance.synthLoss.result.singleEnded.errorLog.nbrOfBadDataFrames

       32 bit unsigned wrappable counter."
   ::= {pr1646v2PbbEthOamESlmPerfRsltSingleErrorLogEntry 67108864}

pr1646v2PbbEthOamESlmPerfRsltSingleErrorLogNbrOfLateFrames OBJECT-TYPE
   SYNTAX      Counter32
   MAX-ACCESS  read-only
   STATUS      current
   DESCRIPTION
      "Path: ethOam.performance.synthLoss.result.singleEnded.errorLog.nbrOfLateFrames

       32 bit unsigned wrappable counter."
   ::= {pr1646v2PbbEthOamESlmPerfRsltSingleErrorLogEntry 83886080}

pr1646v2PbbEthOamESlmPerfRsltSingleErrorLogNbrOfDuplicateSlm OBJECT-TYPE
   SYNTAX      Counter32
   MAX-ACCESS  read-only
   STATUS      current
   DESCRIPTION
      "Path: ethOam.performance.synthLoss.result.singleEnded.errorLog.nbrOfDuplicateSlm

       32 bit unsigned wrappable counter."
   ::= {pr1646v2PbbEthOamESlmPerfRsltSingleErrorLogEntry 150994944}

pr1646v2PbbEthOamESlmPerfRsltSingleErrorLogNbrOfDuplicateSlr OBJECT-TYPE
   SYNTAX      Counter32
   MAX-ACCESS  read-only
   STATUS      current
   DESCRIPTION
      "Path: ethOam.performance.synthLoss.result.singleEnded.errorLog.nbrOfDuplicateSlr

       32 bit unsigned wrappable counter."
   ::= {pr1646v2PbbEthOamESlmPerfRsltSingleErrorLogEntry 167772160}

pr1646v2PbbEthOamESlmPerfRsltSingleErrorLogNbrOfSlmSeqError OBJECT-TYPE
   SYNTAX      Counter32
   MAX-ACCESS  read-only
   STATUS      current
   DESCRIPTION
      "Path: ethOam.performance.synthLoss.result.singleEnded.errorLog.nbrOfSlmSeqError

       32 bit unsigned wrappable counter."
   ::= {pr1646v2PbbEthOamESlmPerfRsltSingleErrorLogEntry 184549376}

pr1646v2PbbEthOamESlmPerfRsltSingleErrorLogNbrOfSlrSeqError OBJECT-TYPE
   SYNTAX      Counter32
   MAX-ACCESS  read-only
   STATUS      current
   DESCRIPTION
      "Path: ethOam.performance.synthLoss.result.singleEnded.errorLog.nbrOfSlrSeqError

       32 bit unsigned wrappable counter."
   ::= {pr1646v2PbbEthOamESlmPerfRsltSingleErrorLogEntry 201326592}

pr1646v2PbbEthOamESlmPerfRsltSingleErrorLogNearEndLoss OBJECT-TYPE
   SYNTAX      INTEGER
               {
               invalid (2147483647)
               }
   MAX-ACCESS  read-only
   STATUS      current
   DESCRIPTION
      "Path: ethOam.performance.synthLoss.result.singleEnded.errorLog.nearEndLoss

       Possibilities:
               invalid   (2147483647)"
   ::= {pr1646v2PbbEthOamESlmPerfRsltSingleErrorLogEntry 100663296}

pr1646v2PbbEthOamESlmPerfRsltSingleErrorLogFarEndLoss OBJECT-TYPE
   SYNTAX      INTEGER
               {
               invalid (2147483647)
               }
   MAX-ACCESS  read-only
   STATUS      current
   DESCRIPTION
      "Path: ethOam.performance.synthLoss.result.singleEnded.errorLog.farEndLoss

       Possibilities:
               invalid   (2147483647)"
   ::= {pr1646v2PbbEthOamESlmPerfRsltSingleErrorLogEntry 117440512}


pr1646v2PbbEthOamEMeps OBJECT IDENTIFIER ::= {pr1646v2PbbEthOamE 27}

pr1646v2PbbEthOamEMepsSSCTable OBJECT-TYPE
   SYNTAX      SEQUENCE OF Pr1646v2PbbEthOamEMepsEntry
   MAX-ACCESS  not-accessible
   STATUS      current
   DESCRIPTION
      "ETH OAM MEP statistics"
   ::= {pr1646v2PbbEthOamEMeps 1}

pr1646v2PbbEthOamEMepsEntry OBJECT-TYPE
   SYNTAX      Pr1646v2PbbEthOamEMepsEntry
   MAX-ACCESS  not-accessible
   STATUS      current
   DESCRIPTION
      ""
   INDEX      { pr1646v2PbbEthOamEMepsGlobalIx,
                pr1646v2PbbEthOamEMepsTableIx }
   ::= {pr1646v2PbbEthOamEMepsSSCTable 1}

Pr1646v2PbbEthOamEMepsEntry ::=
   SEQUENCE
      {
      pr1646v2PbbEthOamEMepsGlobalIx
         GlobalIndex,
      pr1646v2PbbEthOamEMepsTableIx
         TableIndex,
      pr1646v2PbbEthOamEMepsMepName
         DisplayString,
      pr1646v2PbbEthOamEMepsMegLevel
         Integer32,
      pr1646v2PbbEthOamEMepsMepId
         INTEGER,
      pr1646v2PbbEthOamEMepsTxOam
         Counter32,
      pr1646v2PbbEthOamEMepsRxOam
         Counter32,
      pr1646v2PbbEthOamEMepsCcmTxCcm
         Counter32,
      pr1646v2PbbEthOamEMepsCcmRxValidCcm
         Counter32,
      pr1646v2PbbEthOamEMepsCcmTxRdi
         Counter32,
      pr1646v2PbbEthOamEMepsCcmRxRdi
         Counter32,
      pr1646v2PbbEthOamEMepsCcmRxSeqError
         Counter32,
      pr1646v2PbbEthOamEMepsCcmRxBadMegLevel
         Counter32,
      pr1646v2PbbEthOamEMepsCcmRxMismerge
         Counter32,
      pr1646v2PbbEthOamEMepsCcmRxUnexpPeriod
         Counter32,
      pr1646v2PbbEthOamEMepsCcmRxUnexpMep
         Counter32,
      pr1646v2PbbEthOamEMepsLoopbackTxLbm
         Counter32,
      pr1646v2PbbEthOamEMepsLoopbackRxLbr
         Counter32,
      pr1646v2PbbEthOamEMepsLoopbackRxLbm
         Counter32,
      pr1646v2PbbEthOamEMepsLoopbackTxLbr
         Counter32,
      pr1646v2PbbEthOamEMepsLoopbackTxMcLbm
         Counter32,
      pr1646v2PbbEthOamEMepsLoopbackRxMcLbm
         Counter32,
      pr1646v2PbbEthOamEMepsLoopbackRxLbrOutOfSeq
         Counter32,
      pr1646v2PbbEthOamEMepsLoopbackRxLbrTooLate
         Counter32,
      pr1646v2PbbEthOamEMepsLoopbackRxLbrBadData
         Counter32,
      pr1646v2PbbEthOamEMepsLinkTraceTxLtm
         Counter32,
      pr1646v2PbbEthOamEMepsLinkTraceRxLtr
         Counter32,
      pr1646v2PbbEthOamEMepsLinkTraceRxLtm
         Counter32,
      pr1646v2PbbEthOamEMepsLinkTraceTxLtr
         Counter32,
      pr1646v2PbbEthOamEMepsLinkTraceRxLtrTooLate
         Counter32,
      pr1646v2PbbEthOamEMepsLinkTraceRxLtrUnexp
         Counter32,
      pr1646v2PbbEthOamEMepsDelayTxDmm
         Counter32,
      pr1646v2PbbEthOamEMepsDelayRxDmr
         Counter32,
      pr1646v2PbbEthOamEMepsDelayRxDmm
         Counter32,
      pr1646v2PbbEthOamEMepsDelayTxDmr
         Counter32,
      pr1646v2PbbEthOamEMepsLossTxLmm
         Counter32,
      pr1646v2PbbEthOamEMepsLossRxLmr
         Counter32,
      pr1646v2PbbEthOamEMepsLossRxLmm
         Counter32,
      pr1646v2PbbEthOamEMepsLossTxLmr
         Counter32,
      pr1646v2PbbEthOamEMepsSynthLossTxSlm
         Counter32,
      pr1646v2PbbEthOamEMepsSynthLossRxSlr
         Counter32,
      pr1646v2PbbEthOamEMepsSynthLossRxSlm
         Counter32,
      pr1646v2PbbEthOamEMepsSynthLossTxSlr
         Counter32,
      pr1646v2PbbEthOamEMepsSynthLossTx1Sl
         Counter32,
      pr1646v2PbbEthOamEMepsSynthLossRx1Sl
         Counter32,
      pr1646v2PbbEthOamEMepsSynthLossTxMc1Sl
         Counter32,
      pr1646v2PbbEthOamEMepsSynthLossRxMc1Sl
         Counter32,
      pr1646v2PbbEthOamEMepsAisTxAis
         Counter32,
      pr1646v2PbbEthOamEMepsAisRxAis
         Counter32,
      pr1646v2PbbEthOamEMepsApsTxAps
         Counter32,
      pr1646v2PbbEthOamEMepsApsRxAps
         Counter32,
      pr1646v2PbbEthOamEMepsApsRxApsMismatch
         Counter32,
      pr1646v2PbbEthOamEMepsPassiveDiscards
         Counter32,
      pr1646v2PbbEthOamEMepsDiscards
         Counter32
      }

pr1646v2PbbEthOamEMepsGlobalIx OBJECT-TYPE
   SYNTAX      GlobalIndex
   MAX-ACCESS  not-accessible
   STATUS      current
   DESCRIPTION
      "The value of the tlsCntTreeGlobalIndex of the MANAGED OBJECT."
   ::= {pr1646v2PbbEthOamEMepsEntry 10}

pr1646v2PbbEthOamEMepsTableIx OBJECT-TYPE
   SYNTAX      TableIndex
   MAX-ACCESS  not-accessible
   STATUS      current
   DESCRIPTION
      ""
   ::= {pr1646v2PbbEthOamEMepsEntry 11}

pr1646v2PbbEthOamEMepsMepName OBJECT-TYPE
   SYNTAX      DisplayString
   MAX-ACCESS  read-only
   STATUS      current
   DESCRIPTION
      "Path: ethOam.performance.meps.mepName"
   ::= {pr1646v2PbbEthOamEMepsEntry 16777216}

pr1646v2PbbEthOamEMepsMegLevel OBJECT-TYPE
   SYNTAX      Integer32
   MAX-ACCESS  read-only
   STATUS      current
   DESCRIPTION
      "Path: ethOam.performance.meps.megLevel"
   ::= {pr1646v2PbbEthOamEMepsEntry 33554432}

pr1646v2PbbEthOamEMepsMepId OBJECT-TYPE
   SYNTAX      INTEGER
               {
               unknown (8192)
               }
   MAX-ACCESS  read-only
   STATUS      current
   DESCRIPTION
      "Path: ethOam.performance.meps.mepId

       Possibilities:
               unknown   (8192)"
   ::= {pr1646v2PbbEthOamEMepsEntry 50331648}

pr1646v2PbbEthOamEMepsTxOam OBJECT-TYPE
   SYNTAX      Counter32
   MAX-ACCESS  read-only
   STATUS      current
   DESCRIPTION
      "Path: ethOam.performance.meps.txOam

       32 bit unsigned wrappable counter."
   ::= {pr1646v2PbbEthOamEMepsEntry 67108864}

pr1646v2PbbEthOamEMepsRxOam OBJECT-TYPE
   SYNTAX      Counter32
   MAX-ACCESS  read-only
   STATUS      current
   DESCRIPTION
      "Path: ethOam.performance.meps.rxOam

       32 bit unsigned wrappable counter."
   ::= {pr1646v2PbbEthOamEMepsEntry 83886080}

pr1646v2PbbEthOamEMepsCcmTxCcm OBJECT-TYPE
   SYNTAX      Counter32
   MAX-ACCESS  read-only
   STATUS      current
   DESCRIPTION
      "Path: ethOam.performance.meps.ccm.txCcm

       32 bit unsigned wrappable counter."
   ::= {pr1646v2PbbEthOamEMepsEntry 100728832}

pr1646v2PbbEthOamEMepsCcmRxValidCcm OBJECT-TYPE
   SYNTAX      Counter32
   MAX-ACCESS  read-only
   STATUS      current
   DESCRIPTION
      "Path: ethOam.performance.meps.ccm.rxValidCcm

       32 bit unsigned wrappable counter."
   ::= {pr1646v2PbbEthOamEMepsEntry 100794368}

pr1646v2PbbEthOamEMepsCcmTxRdi OBJECT-TYPE
   SYNTAX      Counter32
   MAX-ACCESS  read-only
   STATUS      current
   DESCRIPTION
      "Path: ethOam.performance.meps.ccm.txRdi

       32 bit unsigned wrappable counter."
   ::= {pr1646v2PbbEthOamEMepsEntry 101253120}

pr1646v2PbbEthOamEMepsCcmRxRdi OBJECT-TYPE
   SYNTAX      Counter32
   MAX-ACCESS  read-only
   STATUS      current
   DESCRIPTION
      "Path: ethOam.performance.meps.ccm.rxRdi

       32 bit unsigned wrappable counter."
   ::= {pr1646v2PbbEthOamEMepsEntry 100859904}

pr1646v2PbbEthOamEMepsCcmRxSeqError OBJECT-TYPE
   SYNTAX      Counter32
   MAX-ACCESS  read-only
   STATUS      current
   DESCRIPTION
      "Path: ethOam.performance.meps.ccm.rxSeqError

       32 bit unsigned wrappable counter."
   ::= {pr1646v2PbbEthOamEMepsEntry 100925440}

pr1646v2PbbEthOamEMepsCcmRxBadMegLevel OBJECT-TYPE
   SYNTAX      Counter32
   MAX-ACCESS  read-only
   STATUS      current
   DESCRIPTION
      "Path: ethOam.performance.meps.ccm.rxBadMegLevel

       32 bit unsigned wrappable counter."
   ::= {pr1646v2PbbEthOamEMepsEntry 100990976}

pr1646v2PbbEthOamEMepsCcmRxMismerge OBJECT-TYPE
   SYNTAX      Counter32
   MAX-ACCESS  read-only
   STATUS      current
   DESCRIPTION
      "Path: ethOam.performance.meps.ccm.rxMismerge

       32 bit unsigned wrappable counter."
   ::= {pr1646v2PbbEthOamEMepsEntry 101056512}

pr1646v2PbbEthOamEMepsCcmRxUnexpPeriod OBJECT-TYPE
   SYNTAX      Counter32
   MAX-ACCESS  read-only
   STATUS      current
   DESCRIPTION
      "Path: ethOam.performance.meps.ccm.rxUnexpPeriod

       32 bit unsigned wrappable counter."
   ::= {pr1646v2PbbEthOamEMepsEntry 101122048}

pr1646v2PbbEthOamEMepsCcmRxUnexpMep OBJECT-TYPE
   SYNTAX      Counter32
   MAX-ACCESS  read-only
   STATUS      current
   DESCRIPTION
      "Path: ethOam.performance.meps.ccm.rxUnexpMep

       32 bit unsigned wrappable counter."
   ::= {pr1646v2PbbEthOamEMepsEntry 101187584}

pr1646v2PbbEthOamEMepsLoopbackTxLbm OBJECT-TYPE
   SYNTAX      Counter32
   MAX-ACCESS  read-only
   STATUS      current
   DESCRIPTION
      "Path: ethOam.performance.meps.loopback.txLbm

       32 bit unsigned wrappable counter."
   ::= {pr1646v2PbbEthOamEMepsEntry 117506048}

pr1646v2PbbEthOamEMepsLoopbackRxLbr OBJECT-TYPE
   SYNTAX      Counter32
   MAX-ACCESS  read-only
   STATUS      current
   DESCRIPTION
      "Path: ethOam.performance.meps.loopback.rxLbr

       32 bit unsigned wrappable counter."
   ::= {pr1646v2PbbEthOamEMepsEntry 117702656}

pr1646v2PbbEthOamEMepsLoopbackRxLbm OBJECT-TYPE
   SYNTAX      Counter32
   MAX-ACCESS  read-only
   STATUS      current
   DESCRIPTION
      "Path: ethOam.performance.meps.loopback.rxLbm

       32 bit unsigned wrappable counter."
   ::= {pr1646v2PbbEthOamEMepsEntry 117571584}

pr1646v2PbbEthOamEMepsLoopbackTxLbr OBJECT-TYPE
   SYNTAX      Counter32
   MAX-ACCESS  read-only
   STATUS      current
   DESCRIPTION
      "Path: ethOam.performance.meps.loopback.txLbr

       32 bit unsigned wrappable counter."
   ::= {pr1646v2PbbEthOamEMepsEntry 117637120}

pr1646v2PbbEthOamEMepsLoopbackTxMcLbm OBJECT-TYPE
   SYNTAX      Counter32
   MAX-ACCESS  read-only
   STATUS      current
   DESCRIPTION
      "Path: ethOam.performance.meps.loopback.txMcLbm

       32 bit unsigned wrappable counter."
   ::= {pr1646v2PbbEthOamEMepsEntry 118030336}

pr1646v2PbbEthOamEMepsLoopbackRxMcLbm OBJECT-TYPE
   SYNTAX      Counter32
   MAX-ACCESS  read-only
   STATUS      current
   DESCRIPTION
      "Path: ethOam.performance.meps.loopback.rxMcLbm

       32 bit unsigned wrappable counter."
   ::= {pr1646v2PbbEthOamEMepsEntry 117964800}

pr1646v2PbbEthOamEMepsLoopbackRxLbrOutOfSeq OBJECT-TYPE
   SYNTAX      Counter32
   MAX-ACCESS  read-only
   STATUS      current
   DESCRIPTION
      "Path: ethOam.performance.meps.loopback.rxLbrOutOfSeq

       32 bit unsigned wrappable counter."
   ::= {pr1646v2PbbEthOamEMepsEntry 117768192}

pr1646v2PbbEthOamEMepsLoopbackRxLbrTooLate OBJECT-TYPE
   SYNTAX      Counter32
   MAX-ACCESS  read-only
   STATUS      current
   DESCRIPTION
      "Path: ethOam.performance.meps.loopback.rxLbrTooLate

       32 bit unsigned wrappable counter."
   ::= {pr1646v2PbbEthOamEMepsEntry 117833728}

pr1646v2PbbEthOamEMepsLoopbackRxLbrBadData OBJECT-TYPE
   SYNTAX      Counter32
   MAX-ACCESS  read-only
   STATUS      current
   DESCRIPTION
      "Path: ethOam.performance.meps.loopback.rxLbrBadData

       32 bit unsigned wrappable counter."
   ::= {pr1646v2PbbEthOamEMepsEntry 117899264}

pr1646v2PbbEthOamEMepsLinkTraceTxLtm OBJECT-TYPE
   SYNTAX      Counter32
   MAX-ACCESS  read-only
   STATUS      current
   DESCRIPTION
      "Path: ethOam.performance.meps.linkTrace.txLtm

       32 bit unsigned wrappable counter."
   ::= {pr1646v2PbbEthOamEMepsEntry 134283264}

pr1646v2PbbEthOamEMepsLinkTraceRxLtr OBJECT-TYPE
   SYNTAX      Counter32
   MAX-ACCESS  read-only
   STATUS      current
   DESCRIPTION
      "Path: ethOam.performance.meps.linkTrace.rxLtr

       32 bit unsigned wrappable counter."
   ::= {pr1646v2PbbEthOamEMepsEntry 134479872}

pr1646v2PbbEthOamEMepsLinkTraceRxLtm OBJECT-TYPE
   SYNTAX      Counter32
   MAX-ACCESS  read-only
   STATUS      current
   DESCRIPTION
      "Path: ethOam.performance.meps.linkTrace.rxLtm

       32 bit unsigned wrappable counter."
   ::= {pr1646v2PbbEthOamEMepsEntry 134348800}

pr1646v2PbbEthOamEMepsLinkTraceTxLtr OBJECT-TYPE
   SYNTAX      Counter32
   MAX-ACCESS  read-only
   STATUS      current
   DESCRIPTION
      "Path: ethOam.performance.meps.linkTrace.txLtr

       32 bit unsigned wrappable counter."
   ::= {pr1646v2PbbEthOamEMepsEntry 134414336}

pr1646v2PbbEthOamEMepsLinkTraceRxLtrTooLate OBJECT-TYPE
   SYNTAX      Counter32
   MAX-ACCESS  read-only
   STATUS      current
   DESCRIPTION
      "Path: ethOam.performance.meps.linkTrace.rxLtrTooLate

       32 bit unsigned wrappable counter."
   ::= {pr1646v2PbbEthOamEMepsEntry 134545408}

pr1646v2PbbEthOamEMepsLinkTraceRxLtrUnexp OBJECT-TYPE
   SYNTAX      Counter32
   MAX-ACCESS  read-only
   STATUS      current
   DESCRIPTION
      "Path: ethOam.performance.meps.linkTrace.rxLtrUnexp

       32 bit unsigned wrappable counter."
   ::= {pr1646v2PbbEthOamEMepsEntry 134610944}

pr1646v2PbbEthOamEMepsDelayTxDmm OBJECT-TYPE
   SYNTAX      Counter32
   MAX-ACCESS  read-only
   STATUS      current
   DESCRIPTION
      "Path: ethOam.performance.meps.delay.txDmm

       32 bit unsigned wrappable counter."
   ::= {pr1646v2PbbEthOamEMepsEntry 151060480}

pr1646v2PbbEthOamEMepsDelayRxDmr OBJECT-TYPE
   SYNTAX      Counter32
   MAX-ACCESS  read-only
   STATUS      current
   DESCRIPTION
      "Path: ethOam.performance.meps.delay.rxDmr

       32 bit unsigned wrappable counter."
   ::= {pr1646v2PbbEthOamEMepsEntry 151257088}

pr1646v2PbbEthOamEMepsDelayRxDmm OBJECT-TYPE
   SYNTAX      Counter32
   MAX-ACCESS  read-only
   STATUS      current
   DESCRIPTION
      "Path: ethOam.performance.meps.delay.rxDmm

       32 bit unsigned wrappable counter."
   ::= {pr1646v2PbbEthOamEMepsEntry 151126016}

pr1646v2PbbEthOamEMepsDelayTxDmr OBJECT-TYPE
   SYNTAX      Counter32
   MAX-ACCESS  read-only
   STATUS      current
   DESCRIPTION
      "Path: ethOam.performance.meps.delay.txDmr

       32 bit unsigned wrappable counter."
   ::= {pr1646v2PbbEthOamEMepsEntry 151191552}

pr1646v2PbbEthOamEMepsLossTxLmm OBJECT-TYPE
   SYNTAX      Counter32
   MAX-ACCESS  read-only
   STATUS      current
   DESCRIPTION
      "Path: ethOam.performance.meps.loss.txLmm

       32 bit unsigned wrappable counter."
   ::= {pr1646v2PbbEthOamEMepsEntry 167837696}

pr1646v2PbbEthOamEMepsLossRxLmr OBJECT-TYPE
   SYNTAX      Counter32
   MAX-ACCESS  read-only
   STATUS      current
   DESCRIPTION
      "Path: ethOam.performance.meps.loss.rxLmr

       32 bit unsigned wrappable counter."
   ::= {pr1646v2PbbEthOamEMepsEntry 168034304}

pr1646v2PbbEthOamEMepsLossRxLmm OBJECT-TYPE
   SYNTAX      Counter32
   MAX-ACCESS  read-only
   STATUS      current
   DESCRIPTION
      "Path: ethOam.performance.meps.loss.rxLmm

       32 bit unsigned wrappable counter."
   ::= {pr1646v2PbbEthOamEMepsEntry 167903232}

pr1646v2PbbEthOamEMepsLossTxLmr OBJECT-TYPE
   SYNTAX      Counter32
   MAX-ACCESS  read-only
   STATUS      current
   DESCRIPTION
      "Path: ethOam.performance.meps.loss.txLmr

       32 bit unsigned wrappable counter."
   ::= {pr1646v2PbbEthOamEMepsEntry 167968768}

pr1646v2PbbEthOamEMepsSynthLossTxSlm OBJECT-TYPE
   SYNTAX      Counter32
   MAX-ACCESS  read-only
   STATUS      current
   DESCRIPTION
      "Path: ethOam.performance.meps.synthLoss.txSlm

       32 bit unsigned wrappable counter."
   ::= {pr1646v2PbbEthOamEMepsEntry 251723776}

pr1646v2PbbEthOamEMepsSynthLossRxSlr OBJECT-TYPE
   SYNTAX      Counter32
   MAX-ACCESS  read-only
   STATUS      current
   DESCRIPTION
      "Path: ethOam.performance.meps.synthLoss.rxSlr

       32 bit unsigned wrappable counter."
   ::= {pr1646v2PbbEthOamEMepsEntry 251920384}

pr1646v2PbbEthOamEMepsSynthLossRxSlm OBJECT-TYPE
   SYNTAX      Counter32
   MAX-ACCESS  read-only
   STATUS      current
   DESCRIPTION
      "Path: ethOam.performance.meps.synthLoss.rxSlm

       32 bit unsigned wrappable counter."
   ::= {pr1646v2PbbEthOamEMepsEntry 251789312}

pr1646v2PbbEthOamEMepsSynthLossTxSlr OBJECT-TYPE
   SYNTAX      Counter32
   MAX-ACCESS  read-only
   STATUS      current
   DESCRIPTION
      "Path: ethOam.performance.meps.synthLoss.txSlr

       32 bit unsigned wrappable counter."
   ::= {pr1646v2PbbEthOamEMepsEntry 251854848}

pr1646v2PbbEthOamEMepsSynthLossTx1Sl OBJECT-TYPE
   SYNTAX      Counter32
   MAX-ACCESS  read-only
   STATUS      current
   DESCRIPTION
      "Path: ethOam.performance.meps.synthLoss.tx1Sl

       32 bit unsigned wrappable counter."
   ::= {pr1646v2PbbEthOamEMepsEntry 251985920}

pr1646v2PbbEthOamEMepsSynthLossRx1Sl OBJECT-TYPE
   SYNTAX      Counter32
   MAX-ACCESS  read-only
   STATUS      current
   DESCRIPTION
      "Path: ethOam.performance.meps.synthLoss.rx1Sl

       32 bit unsigned wrappable counter."
   ::= {pr1646v2PbbEthOamEMepsEntry 252051456}

pr1646v2PbbEthOamEMepsSynthLossTxMc1Sl OBJECT-TYPE
   SYNTAX      Counter32
   MAX-ACCESS  read-only
   STATUS      current
   DESCRIPTION
      "Path: ethOam.performance.meps.synthLoss.txMc1Sl

       32 bit unsigned wrappable counter."
   ::= {pr1646v2PbbEthOamEMepsEntry 252116992}

pr1646v2PbbEthOamEMepsSynthLossRxMc1Sl OBJECT-TYPE
   SYNTAX      Counter32
   MAX-ACCESS  read-only
   STATUS      current
   DESCRIPTION
      "Path: ethOam.performance.meps.synthLoss.rxMc1Sl

       32 bit unsigned wrappable counter."
   ::= {pr1646v2PbbEthOamEMepsEntry 252182528}

pr1646v2PbbEthOamEMepsAisTxAis OBJECT-TYPE
   SYNTAX      Counter32
   MAX-ACCESS  read-only
   STATUS      current
   DESCRIPTION
      "Path: ethOam.performance.meps.ais.txAis

       32 bit unsigned wrappable counter."
   ::= {pr1646v2PbbEthOamEMepsEntry 201392128}

pr1646v2PbbEthOamEMepsAisRxAis OBJECT-TYPE
   SYNTAX      Counter32
   MAX-ACCESS  read-only
   STATUS      current
   DESCRIPTION
      "Path: ethOam.performance.meps.ais.rxAis

       32 bit unsigned wrappable counter."
   ::= {pr1646v2PbbEthOamEMepsEntry 201457664}

pr1646v2PbbEthOamEMepsApsTxAps OBJECT-TYPE
   SYNTAX      Counter32
   MAX-ACCESS  read-only
   STATUS      current
   DESCRIPTION
      "Path: ethOam.performance.meps.aps.txAps

       32 bit unsigned wrappable counter."
   ::= {pr1646v2PbbEthOamEMepsEntry 234946560}

pr1646v2PbbEthOamEMepsApsRxAps OBJECT-TYPE
   SYNTAX      Counter32
   MAX-ACCESS  read-only
   STATUS      current
   DESCRIPTION
      "Path: ethOam.performance.meps.aps.rxAps

       32 bit unsigned wrappable counter."
   ::= {pr1646v2PbbEthOamEMepsEntry 235012096}

pr1646v2PbbEthOamEMepsApsRxApsMismatch OBJECT-TYPE
   SYNTAX      Counter32
   MAX-ACCESS  read-only
   STATUS      current
   DESCRIPTION
      "Path: ethOam.performance.meps.aps.rxApsMismatch

       32 bit unsigned wrappable counter."
   ::= {pr1646v2PbbEthOamEMepsEntry 235077632}

pr1646v2PbbEthOamEMepsPassiveDiscards OBJECT-TYPE
   SYNTAX      Counter32
   MAX-ACCESS  read-only
   STATUS      current
   DESCRIPTION
      "Path: ethOam.performance.meps.passiveDiscards

       32 bit unsigned wrappable counter."
   ::= {pr1646v2PbbEthOamEMepsEntry 218103808}

pr1646v2PbbEthOamEMepsDiscards OBJECT-TYPE
   SYNTAX      Counter32
   MAX-ACCESS  read-only
   STATUS      current
   DESCRIPTION
      "Path: ethOam.performance.meps.discards

       32 bit unsigned wrappable counter."
   ::= {pr1646v2PbbEthOamEMepsEntry 184549376}


pr1646v2PbbEthOamEMips OBJECT IDENTIFIER ::= {pr1646v2PbbEthOamE 30}

pr1646v2PbbEthOamEMipsSSCTable OBJECT-TYPE
   SYNTAX      SEQUENCE OF Pr1646v2PbbEthOamEMipsEntry
   MAX-ACCESS  not-accessible
   STATUS      current
   DESCRIPTION
      "ETH OAM MIP statistics"
   ::= {pr1646v2PbbEthOamEMips 1}

pr1646v2PbbEthOamEMipsEntry OBJECT-TYPE
   SYNTAX      Pr1646v2PbbEthOamEMipsEntry
   MAX-ACCESS  not-accessible
   STATUS      current
   DESCRIPTION
      ""
   INDEX      { pr1646v2PbbEthOamEMipsGlobalIx,
                pr1646v2PbbEthOamEMipsTableIx }
   ::= {pr1646v2PbbEthOamEMipsSSCTable 1}

Pr1646v2PbbEthOamEMipsEntry ::=
   SEQUENCE
      {
      pr1646v2PbbEthOamEMipsGlobalIx
         GlobalIndex,
      pr1646v2PbbEthOamEMipsTableIx
         TableIndex,
      pr1646v2PbbEthOamEMipsMipName
         DisplayString,
      pr1646v2PbbEthOamEMipsMegLevel
         Integer32,
      pr1646v2PbbEthOamEMipsRxLbm
         Counter32,
      pr1646v2PbbEthOamEMipsTxLbr
         Counter32,
      pr1646v2PbbEthOamEMipsRxLtm
         Counter32,
      pr1646v2PbbEthOamEMipsTxLtm
         Counter32,
      pr1646v2PbbEthOamEMipsTxLtr
         Counter32,
      pr1646v2PbbEthOamEMipsDiscards
         Counter32
      }

pr1646v2PbbEthOamEMipsGlobalIx OBJECT-TYPE
   SYNTAX      GlobalIndex
   MAX-ACCESS  not-accessible
   STATUS      current
   DESCRIPTION
      "The value of the tlsCntTreeGlobalIndex of the MANAGED OBJECT."
   ::= {pr1646v2PbbEthOamEMipsEntry 10}

pr1646v2PbbEthOamEMipsTableIx OBJECT-TYPE
   SYNTAX      TableIndex
   MAX-ACCESS  not-accessible
   STATUS      current
   DESCRIPTION
      ""
   ::= {pr1646v2PbbEthOamEMipsEntry 11}

pr1646v2PbbEthOamEMipsMipName OBJECT-TYPE
   SYNTAX      DisplayString
   MAX-ACCESS  read-only
   STATUS      current
   DESCRIPTION
      "Path: ethOam.performance.mips.mipName"
   ::= {pr1646v2PbbEthOamEMipsEntry 16777216}

pr1646v2PbbEthOamEMipsMegLevel OBJECT-TYPE
   SYNTAX      Integer32
   MAX-ACCESS  read-only
   STATUS      current
   DESCRIPTION
      "Path: ethOam.performance.mips.megLevel"
   ::= {pr1646v2PbbEthOamEMipsEntry 33554432}

pr1646v2PbbEthOamEMipsRxLbm OBJECT-TYPE
   SYNTAX      Counter32
   MAX-ACCESS  read-only
   STATUS      current
   DESCRIPTION
      "Path: ethOam.performance.mips.rxLbm

       32 bit unsigned wrappable counter."
   ::= {pr1646v2PbbEthOamEMipsEntry 50331648}

pr1646v2PbbEthOamEMipsTxLbr OBJECT-TYPE
   SYNTAX      Counter32
   MAX-ACCESS  read-only
   STATUS      current
   DESCRIPTION
      "Path: ethOam.performance.mips.txLbr

       32 bit unsigned wrappable counter."
   ::= {pr1646v2PbbEthOamEMipsEntry 67108864}

pr1646v2PbbEthOamEMipsRxLtm OBJECT-TYPE
   SYNTAX      Counter32
   MAX-ACCESS  read-only
   STATUS      current
   DESCRIPTION
      "Path: ethOam.performance.mips.rxLtm

       32 bit unsigned wrappable counter."
   ::= {pr1646v2PbbEthOamEMipsEntry 83886080}

pr1646v2PbbEthOamEMipsTxLtm OBJECT-TYPE
   SYNTAX      Counter32
   MAX-ACCESS  read-only
   STATUS      current
   DESCRIPTION
      "Path: ethOam.performance.mips.txLtm

       32 bit unsigned wrappable counter."
   ::= {pr1646v2PbbEthOamEMipsEntry 100663296}

pr1646v2PbbEthOamEMipsTxLtr OBJECT-TYPE
   SYNTAX      Counter32
   MAX-ACCESS  read-only
   STATUS      current
   DESCRIPTION
      "Path: ethOam.performance.mips.txLtr

       32 bit unsigned wrappable counter."
   ::= {pr1646v2PbbEthOamEMipsEntry 117440512}

pr1646v2PbbEthOamEMipsDiscards OBJECT-TYPE
   SYNTAX      Counter32
   MAX-ACCESS  read-only
   STATUS      current
   DESCRIPTION
      "Path: ethOam.performance.mips.discards

       32 bit unsigned wrappable counter."
   ::= {pr1646v2PbbEthOamEMipsEntry 134217728}


pr1646v2PbbEthOamEManagedMeps OBJECT IDENTIFIER ::= {pr1646v2PbbEthOamE 40}

pr1646v2PbbEthOamEManagedMepsSSCTable OBJECT-TYPE
   SYNTAX      SEQUENCE OF Pr1646v2PbbEthOamEManagedMepsEntry
   MAX-ACCESS  not-accessible
   STATUS      current
   DESCRIPTION
      "list of managed MEPs"
   ::= {pr1646v2PbbEthOamEManagedMeps 1}

pr1646v2PbbEthOamEManagedMepsEntry OBJECT-TYPE
   SYNTAX      Pr1646v2PbbEthOamEManagedMepsEntry
   MAX-ACCESS  not-accessible
   STATUS      current
   DESCRIPTION
      ""
   INDEX      { pr1646v2PbbEthOamEManagedMepsGlobalIx,
                pr1646v2PbbEthOamEManagedMepsTableIx }
   ::= {pr1646v2PbbEthOamEManagedMepsSSCTable 1}

Pr1646v2PbbEthOamEManagedMepsEntry ::=
   SEQUENCE
      {
      pr1646v2PbbEthOamEManagedMepsGlobalIx
         GlobalIndex,
      pr1646v2PbbEthOamEManagedMepsTableIx
         TableIndex,
      pr1646v2PbbEthOamEManagedMepsManagedMepName
         DisplayString,
      pr1646v2PbbEthOamEManagedMepsMegLevel
         Integer32,
      pr1646v2PbbEthOamEManagedMepsMegIdMaintDomainName
         DisplayString,
      pr1646v2PbbEthOamEManagedMepsMegIdShortMaName
         DisplayString,
      pr1646v2PbbEthOamEManagedMepsMepId
         Integer32,
      pr1646v2PbbEthOamEManagedMepsRxCcm
         Counter32,
      pr1646v2PbbEthOamEManagedMepsTxLbm
         Counter32,
      pr1646v2PbbEthOamEManagedMepsRxLbr
         Counter32,
      pr1646v2PbbEthOamEManagedMepsRxLbm
         Counter32,
      pr1646v2PbbEthOamEManagedMepsTxLmm
         Counter32,
      pr1646v2PbbEthOamEManagedMepsRxLmr
         Counter32,
      pr1646v2PbbEthOamEManagedMepsRxLmm
         Counter32,
      pr1646v2PbbEthOamEManagedMepsTxDmm
         Counter32,
      pr1646v2PbbEthOamEManagedMepsRxDmr
         Counter32,
      pr1646v2PbbEthOamEManagedMepsRxDmm
         Counter32,
      pr1646v2PbbEthOamEManagedMepsSlTxSlm
         Counter32,
      pr1646v2PbbEthOamEManagedMepsSlRxSlr
         Counter32,
      pr1646v2PbbEthOamEManagedMepsSlRxSlm
         Counter32,
      pr1646v2PbbEthOamEManagedMepsSlRx1SlCurrentNbrOfRxFrames
         Counter32,
      pr1646v2PbbEthOamEManagedMepsSlRx1SlCurrentNearEndLoss
         INTEGER,
      pr1646v2PbbEthOamEManagedMepsSlRx1SlOverallNbrOfRxFrames
         Counter32,
      pr1646v2PbbEthOamEManagedMepsSlRx1SlOverallNearEndLoss
         INTEGER,
      pr1646v2PbbEthOamEManagedMepsSlRxMc1SlCurrentNbrOfRxFrames
         Counter32,
      pr1646v2PbbEthOamEManagedMepsSlRxMc1SlCurrentNearEndLoss
         INTEGER,
      pr1646v2PbbEthOamEManagedMepsSlRxMc1SlOverallNbrOfRxFrames
         Counter32,
      pr1646v2PbbEthOamEManagedMepsSlRxMc1SlOverallNearEndLoss
         INTEGER
      }

pr1646v2PbbEthOamEManagedMepsGlobalIx OBJECT-TYPE
   SYNTAX      GlobalIndex
   MAX-ACCESS  not-accessible
   STATUS      current
   DESCRIPTION
      "The value of the tlsCntTreeGlobalIndex of the MANAGED OBJECT."
   ::= {pr1646v2PbbEthOamEManagedMepsEntry 10}

pr1646v2PbbEthOamEManagedMepsTableIx OBJECT-TYPE
   SYNTAX      TableIndex
   MAX-ACCESS  not-accessible
   STATUS      current
   DESCRIPTION
      ""
   ::= {pr1646v2PbbEthOamEManagedMepsEntry 11}

pr1646v2PbbEthOamEManagedMepsManagedMepName OBJECT-TYPE
   SYNTAX      DisplayString
   MAX-ACCESS  read-only
   STATUS      current
   DESCRIPTION
      "Path: ethOam.performance.managedMeps.managedMepName"
   ::= {pr1646v2PbbEthOamEManagedMepsEntry 201326592}

pr1646v2PbbEthOamEManagedMepsMegLevel OBJECT-TYPE
   SYNTAX      Integer32
   MAX-ACCESS  read-only
   STATUS      current
   DESCRIPTION
      "Path: ethOam.performance.managedMeps.megLevel"
   ::= {pr1646v2PbbEthOamEManagedMepsEntry 83886080}

pr1646v2PbbEthOamEManagedMepsMegIdMaintDomainName OBJECT-TYPE
   SYNTAX      DisplayString
   MAX-ACCESS  read-only
   STATUS      current
   DESCRIPTION
      "Path: ethOam.performance.managedMeps.megId.maintDomainName"
   ::= {pr1646v2PbbEthOamEManagedMepsEntry 100728832}

pr1646v2PbbEthOamEManagedMepsMegIdShortMaName OBJECT-TYPE
   SYNTAX      DisplayString
   MAX-ACCESS  read-only
   STATUS      current
   DESCRIPTION
      "Path: ethOam.performance.managedMeps.megId.shortMaName"
   ::= {pr1646v2PbbEthOamEManagedMepsEntry 100794368}

pr1646v2PbbEthOamEManagedMepsMepId OBJECT-TYPE
   SYNTAX      Integer32
   MAX-ACCESS  read-only
   STATUS      current
   DESCRIPTION
      "Path: ethOam.performance.managedMeps.mepId"
   ::= {pr1646v2PbbEthOamEManagedMepsEntry 117440512}

pr1646v2PbbEthOamEManagedMepsRxCcm OBJECT-TYPE
   SYNTAX      Counter32
   MAX-ACCESS  read-only
   STATUS      current
   DESCRIPTION
      "Path: ethOam.performance.managedMeps.rxCcm

       32 bit unsigned wrappable counter."
   ::= {pr1646v2PbbEthOamEManagedMepsEntry 335544320}

pr1646v2PbbEthOamEManagedMepsTxLbm OBJECT-TYPE
   SYNTAX      Counter32
   MAX-ACCESS  read-only
   STATUS      current
   DESCRIPTION
      "Path: ethOam.performance.managedMeps.txLbm

       32 bit unsigned wrappable counter."
   ::= {pr1646v2PbbEthOamEManagedMepsEntry 553648128}

pr1646v2PbbEthOamEManagedMepsRxLbr OBJECT-TYPE
   SYNTAX      Counter32
   MAX-ACCESS  read-only
   STATUS      current
   DESCRIPTION
      "Path: ethOam.performance.managedMeps.rxLbr

       32 bit unsigned wrappable counter."
   ::= {pr1646v2PbbEthOamEManagedMepsEntry 721420288}

pr1646v2PbbEthOamEManagedMepsRxLbm OBJECT-TYPE
   SYNTAX      Counter32
   MAX-ACCESS  read-only
   STATUS      current
   DESCRIPTION
      "Path: ethOam.performance.managedMeps.rxLbm

       32 bit unsigned wrappable counter."
   ::= {pr1646v2PbbEthOamEManagedMepsEntry 385875968}

pr1646v2PbbEthOamEManagedMepsTxLmm OBJECT-TYPE
   SYNTAX      Counter32
   MAX-ACCESS  read-only
   STATUS      current
   DESCRIPTION
      "Path: ethOam.performance.managedMeps.txLmm

       32 bit unsigned wrappable counter."
   ::= {pr1646v2PbbEthOamEManagedMepsEntry 520093696}

pr1646v2PbbEthOamEManagedMepsRxLmr OBJECT-TYPE
   SYNTAX      Counter32
   MAX-ACCESS  read-only
   STATUS      current
   DESCRIPTION
      "Path: ethOam.performance.managedMeps.rxLmr

       32 bit unsigned wrappable counter."
   ::= {pr1646v2PbbEthOamEManagedMepsEntry 687865856}

pr1646v2PbbEthOamEManagedMepsRxLmm OBJECT-TYPE
   SYNTAX      Counter32
   MAX-ACCESS  read-only
   STATUS      current
   DESCRIPTION
      "Path: ethOam.performance.managedMeps.rxLmm

       32 bit unsigned wrappable counter."
   ::= {pr1646v2PbbEthOamEManagedMepsEntry 352321536}

pr1646v2PbbEthOamEManagedMepsTxDmm OBJECT-TYPE
   SYNTAX      Counter32
   MAX-ACCESS  read-only
   STATUS      current
   DESCRIPTION
      "Path: ethOam.performance.managedMeps.txDmm

       32 bit unsigned wrappable counter."
   ::= {pr1646v2PbbEthOamEManagedMepsEntry 536870912}

pr1646v2PbbEthOamEManagedMepsRxDmr OBJECT-TYPE
   SYNTAX      Counter32
   MAX-ACCESS  read-only
   STATUS      current
   DESCRIPTION
      "Path: ethOam.performance.managedMeps.rxDmr

       32 bit unsigned wrappable counter."
   ::= {pr1646v2PbbEthOamEManagedMepsEntry 704643072}

pr1646v2PbbEthOamEManagedMepsRxDmm OBJECT-TYPE
   SYNTAX      Counter32
   MAX-ACCESS  read-only
   STATUS      current
   DESCRIPTION
      "Path: ethOam.performance.managedMeps.rxDmm

       32 bit unsigned wrappable counter."
   ::= {pr1646v2PbbEthOamEManagedMepsEntry 369098752}

pr1646v2PbbEthOamEManagedMepsSlTxSlm OBJECT-TYPE
   SYNTAX      Counter32
   MAX-ACCESS  read-only
   STATUS      current
   DESCRIPTION
      "Path: ethOam.performance.managedMeps.synthLoss.txSlm

       32 bit unsigned wrappable counter."
   ::= {pr1646v2PbbEthOamEManagedMepsEntry 855900160}

pr1646v2PbbEthOamEManagedMepsSlRxSlr OBJECT-TYPE
   SYNTAX      Counter32
   MAX-ACCESS  read-only
   STATUS      current
   DESCRIPTION
      "Path: ethOam.performance.managedMeps.synthLoss.rxSlr

       32 bit unsigned wrappable counter."
   ::= {pr1646v2PbbEthOamEManagedMepsEntry 855965696}

pr1646v2PbbEthOamEManagedMepsSlRxSlm OBJECT-TYPE
   SYNTAX      Counter32
   MAX-ACCESS  read-only
   STATUS      current
   DESCRIPTION
      "Path: ethOam.performance.managedMeps.synthLoss.rxSlm

       32 bit unsigned wrappable counter."
   ::= {pr1646v2PbbEthOamEManagedMepsEntry 855703552}

pr1646v2PbbEthOamEManagedMepsSlRx1SlCurrentNbrOfRxFrames OBJECT-TYPE
   SYNTAX      Counter32
   MAX-ACCESS  read-only
   STATUS      current
   DESCRIPTION
      "Path: ethOam.performance.managedMeps.synthLoss.rx1Sl.current.nbrOfRxFrames

       32 bit unsigned wrappable counter."
   ::= {pr1646v2PbbEthOamEManagedMepsEntry 855769345}

pr1646v2PbbEthOamEManagedMepsSlRx1SlCurrentNearEndLoss OBJECT-TYPE
   SYNTAX      INTEGER
               {
               invalid (2147483647)
               }
   MAX-ACCESS  read-only
   STATUS      current
   DESCRIPTION
      "Path: ethOam.performance.managedMeps.synthLoss.rx1Sl.current.nearEndLoss

       Possibilities:
               invalid   (2147483647)"
   ::= {pr1646v2PbbEthOamEManagedMepsEntry 855769346}

pr1646v2PbbEthOamEManagedMepsSlRx1SlOverallNbrOfRxFrames OBJECT-TYPE
   SYNTAX      Counter32
   MAX-ACCESS  read-only
   STATUS      current
   DESCRIPTION
      "Path: ethOam.performance.managedMeps.synthLoss.rx1Sl.overall.nbrOfRxFrames

       32 bit unsigned wrappable counter."
   ::= {pr1646v2PbbEthOamEManagedMepsEntry 855769601}

pr1646v2PbbEthOamEManagedMepsSlRx1SlOverallNearEndLoss OBJECT-TYPE
   SYNTAX      INTEGER
               {
               invalid (2147483647)
               }
   MAX-ACCESS  read-only
   STATUS      current
   DESCRIPTION
      "Path: ethOam.performance.managedMeps.synthLoss.rx1Sl.overall.nearEndLoss

       Possibilities:
               invalid   (2147483647)"
   ::= {pr1646v2PbbEthOamEManagedMepsEntry 855769602}

pr1646v2PbbEthOamEManagedMepsSlRxMc1SlCurrentNbrOfRxFrames OBJECT-TYPE
   SYNTAX      Counter32
   MAX-ACCESS  read-only
   STATUS      current
   DESCRIPTION
      "Path: ethOam.performance.managedMeps.synthLoss.rxMc1Sl.current.nbrOfRxFrames

       32 bit unsigned wrappable counter."
   ::= {pr1646v2PbbEthOamEManagedMepsEntry 855834881}

pr1646v2PbbEthOamEManagedMepsSlRxMc1SlCurrentNearEndLoss OBJECT-TYPE
   SYNTAX      INTEGER
               {
               invalid (2147483647)
               }
   MAX-ACCESS  read-only
   STATUS      current
   DESCRIPTION
      "Path: ethOam.performance.managedMeps.synthLoss.rxMc1Sl.current.nearEndLoss

       Possibilities:
               invalid   (2147483647)"
   ::= {pr1646v2PbbEthOamEManagedMepsEntry 855834882}

pr1646v2PbbEthOamEManagedMepsSlRxMc1SlOverallNbrOfRxFrames OBJECT-TYPE
   SYNTAX      Counter32
   MAX-ACCESS  read-only
   STATUS      current
   DESCRIPTION
      "Path: ethOam.performance.managedMeps.synthLoss.rxMc1Sl.overall.nbrOfRxFrames

       32 bit unsigned wrappable counter."
   ::= {pr1646v2PbbEthOamEManagedMepsEntry 855835137}

pr1646v2PbbEthOamEManagedMepsSlRxMc1SlOverallNearEndLoss OBJECT-TYPE
   SYNTAX      INTEGER
               {
               invalid (2147483647)
               }
   MAX-ACCESS  read-only
   STATUS      current
   DESCRIPTION
      "Path: ethOam.performance.managedMeps.synthLoss.rxMc1Sl.overall.nearEndLoss

       Possibilities:
               invalid   (2147483647)"
   ::= {pr1646v2PbbEthOamEManagedMepsEntry 855835138}

pr1646v2PbbEthOamEManagedMepsSlRx1SlErrorLog OBJECT-TYPE
   SYNTAX      SEQUENCE OF Pr1646v2PbbEthOamEManagedMepsSlRx1SlErrorLogEntry
   MAX-ACCESS  not-accessible
   STATUS      current
   DESCRIPTION
      ""
   ::= {pr1646v2PbbEthOamEManagedMeps 855769856}

pr1646v2PbbEthOamEManagedMepsSlRx1SlErrorLogEntry OBJECT-TYPE
   SYNTAX      Pr1646v2PbbEthOamEManagedMepsSlRx1SlErrorLogEntry
   MAX-ACCESS  not-accessible
   STATUS      current
   DESCRIPTION
      ""
   INDEX      { pr1646v2PbbEthOamEManagedMepsSlRx1SlErrorLogGlobalIx,
                pr1646v2PbbEthOamEManagedMepsTableIx,
                pr1646v2PbbEthOamEManagedMepsSlRx1SlErrorLogTableIx }
   ::= {pr1646v2PbbEthOamEManagedMepsSlRx1SlErrorLog 1}

Pr1646v2PbbEthOamEManagedMepsSlRx1SlErrorLogEntry ::=
   SEQUENCE
      {
      pr1646v2PbbEthOamEManagedMepsSlRx1SlErrorLogGlobalIx
         GlobalIndex,
      pr1646v2PbbEthOamEManagedMepsSlRx1SlErrorLogTableIx
         TableIndex,
      pr1646v2PbbEthOamEManagedMepsSlRx1SlErrorLogTimeStamp
         DisplayString,
      pr1646v2PbbEthOamEManagedMepsSlRx1SlErrorLogSysUpTime
         TimeTicks,
      pr1646v2PbbEthOamEManagedMepsSlRx1SlErrorLogNbrOfRxFrames
         Counter32,
      pr1646v2PbbEthOamEManagedMepsSlRx1SlErrorLogNearEndLoss
         INTEGER
      }

pr1646v2PbbEthOamEManagedMepsSlRx1SlErrorLogGlobalIx OBJECT-TYPE
   SYNTAX      GlobalIndex
   MAX-ACCESS  not-accessible
   STATUS      current
   DESCRIPTION
      "The value of the tlsCntTreeGlobalIndex of the MANAGED OBJECT."
   ::= {pr1646v2PbbEthOamEManagedMepsSlRx1SlErrorLogEntry 10}

pr1646v2PbbEthOamEManagedMepsSlRx1SlErrorLogTableIx OBJECT-TYPE
   SYNTAX      TableIndex
   MAX-ACCESS  not-accessible
   STATUS      current
   DESCRIPTION
      ""
   ::= {pr1646v2PbbEthOamEManagedMepsSlRx1SlErrorLogEntry 11}

pr1646v2PbbEthOamEManagedMepsSlRx1SlErrorLogTimeStamp OBJECT-TYPE
   SYNTAX      DisplayString
   MAX-ACCESS  read-only
   STATUS      current
   DESCRIPTION
      "Path: ethOam.performance.managedMeps.synthLoss.rx1Sl.errorLog.timeStamp"
   ::= {pr1646v2PbbEthOamEManagedMepsSlRx1SlErrorLogEntry 134217728}

pr1646v2PbbEthOamEManagedMepsSlRx1SlErrorLogSysUpTime OBJECT-TYPE
   SYNTAX      TimeTicks
   MAX-ACCESS  read-only
   STATUS      current
   DESCRIPTION
      "Path: ethOam.performance.managedMeps.synthLoss.rx1Sl.errorLog.sysUpTime

       Time in centi-second."
   ::= {pr1646v2PbbEthOamEManagedMepsSlRx1SlErrorLogEntry 16777216}

pr1646v2PbbEthOamEManagedMepsSlRx1SlErrorLogNbrOfRxFrames OBJECT-TYPE
   SYNTAX      Counter32
   MAX-ACCESS  read-only
   STATUS      current
   DESCRIPTION
      "Path: ethOam.performance.managedMeps.synthLoss.rx1Sl.errorLog.nbrOfRxFrames

       32 bit unsigned wrappable counter."
   ::= {pr1646v2PbbEthOamEManagedMepsSlRx1SlErrorLogEntry 50331648}

pr1646v2PbbEthOamEManagedMepsSlRx1SlErrorLogNearEndLoss OBJECT-TYPE
   SYNTAX      INTEGER
               {
               invalid (2147483647)
               }
   MAX-ACCESS  read-only
   STATUS      current
   DESCRIPTION
      "Path: ethOam.performance.managedMeps.synthLoss.rx1Sl.errorLog.nearEndLoss

       Possibilities:
               invalid   (2147483647)"
   ::= {pr1646v2PbbEthOamEManagedMepsSlRx1SlErrorLogEntry 100663296}

pr1646v2PbbEthOamEManagedMepsSlRxMc1SlErrorLog OBJECT-TYPE
   SYNTAX      SEQUENCE OF Pr1646v2PbbEthOamEManagedMepsSlRxMc1SlErrorLogEntry
   MAX-ACCESS  not-accessible
   STATUS      current
   DESCRIPTION
      ""
   ::= {pr1646v2PbbEthOamEManagedMeps 855835392}

pr1646v2PbbEthOamEManagedMepsSlRxMc1SlErrorLogEntry OBJECT-TYPE
   SYNTAX      Pr1646v2PbbEthOamEManagedMepsSlRxMc1SlErrorLogEntry
   MAX-ACCESS  not-accessible
   STATUS      current
   DESCRIPTION
      ""
   INDEX      { pr1646v2PbbEthOamEManagedMepsSlRxMc1SlErrorLogGlobalIx,
                pr1646v2PbbEthOamEManagedMepsTableIx,
                pr1646v2PbbEthOamEManagedMepsSlRxMc1SlErrorLogTableIx }
   ::= {pr1646v2PbbEthOamEManagedMepsSlRxMc1SlErrorLog 1}

Pr1646v2PbbEthOamEManagedMepsSlRxMc1SlErrorLogEntry ::=
   SEQUENCE
      {
      pr1646v2PbbEthOamEManagedMepsSlRxMc1SlErrorLogGlobalIx
         GlobalIndex,
      pr1646v2PbbEthOamEManagedMepsSlRxMc1SlErrorLogTableIx
         TableIndex,
      pr1646v2PbbEthOamEManagedMepsSlRxMc1SlErrorLogTimeStamp
         DisplayString,
      pr1646v2PbbEthOamEManagedMepsSlRxMc1SlErrorLogSysUpTime
         TimeTicks,
      pr1646v2PbbEthOamEManagedMepsSlRxMc1SlErrorLogNbrOfRxFrames
         Counter32,
      pr1646v2PbbEthOamEManagedMepsSlRxMc1SlErrorLogNearEndLoss
         INTEGER
      }

pr1646v2PbbEthOamEManagedMepsSlRxMc1SlErrorLogGlobalIx OBJECT-TYPE
   SYNTAX      GlobalIndex
   MAX-ACCESS  not-accessible
   STATUS      current
   DESCRIPTION
      "The value of the tlsCntTreeGlobalIndex of the MANAGED OBJECT."
   ::= {pr1646v2PbbEthOamEManagedMepsSlRxMc1SlErrorLogEntry 10}

pr1646v2PbbEthOamEManagedMepsSlRxMc1SlErrorLogTableIx OBJECT-TYPE
   SYNTAX      TableIndex
   MAX-ACCESS  not-accessible
   STATUS      current
   DESCRIPTION
      ""
   ::= {pr1646v2PbbEthOamEManagedMepsSlRxMc1SlErrorLogEntry 11}

pr1646v2PbbEthOamEManagedMepsSlRxMc1SlErrorLogTimeStamp OBJECT-TYPE
   SYNTAX      DisplayString
   MAX-ACCESS  read-only
   STATUS      current
   DESCRIPTION
      "Path: ethOam.performance.managedMeps.synthLoss.rxMc1Sl.errorLog.timeStamp"
   ::= {pr1646v2PbbEthOamEManagedMepsSlRxMc1SlErrorLogEntry 134217728}

pr1646v2PbbEthOamEManagedMepsSlRxMc1SlErrorLogSysUpTime OBJECT-TYPE
   SYNTAX      TimeTicks
   MAX-ACCESS  read-only
   STATUS      current
   DESCRIPTION
      "Path: ethOam.performance.managedMeps.synthLoss.rxMc1Sl.errorLog.sysUpTime

       Time in centi-second."
   ::= {pr1646v2PbbEthOamEManagedMepsSlRxMc1SlErrorLogEntry 16777216}

pr1646v2PbbEthOamEManagedMepsSlRxMc1SlErrorLogNbrOfRxFrames OBJECT-TYPE
   SYNTAX      Counter32
   MAX-ACCESS  read-only
   STATUS      current
   DESCRIPTION
      "Path: ethOam.performance.managedMeps.synthLoss.rxMc1Sl.errorLog.nbrOfRxFrames

       32 bit unsigned wrappable counter."
   ::= {pr1646v2PbbEthOamEManagedMepsSlRxMc1SlErrorLogEntry 50331648}

pr1646v2PbbEthOamEManagedMepsSlRxMc1SlErrorLogNearEndLoss OBJECT-TYPE
   SYNTAX      INTEGER
               {
               invalid (2147483647)
               }
   MAX-ACCESS  read-only
   STATUS      current
   DESCRIPTION
      "Path: ethOam.performance.managedMeps.synthLoss.rxMc1Sl.errorLog.nearEndLoss

       Possibilities:
               invalid   (2147483647)"
   ::= {pr1646v2PbbEthOamEManagedMepsSlRxMc1SlErrorLogEntry 100663296}



fr1646v2PbbEthOamE OBJECT IDENTIFIER ::= {r1646v2PbbEthOamE 13}


fr1646v2PbbEthOamEAlarm OBJECT IDENTIFIER ::= {fr1646v2PbbEthOamE 202}

fr1646v2PbbEthOamEAlarmSSCTable OBJECT-TYPE
   SYNTAX      SEQUENCE OF Fr1646v2PbbEthOamEAlarmEntry
   MAX-ACCESS  not-accessible
   STATUS      current
   DESCRIPTION
      "ETH OAM AlarmInfo"
   ::= {fr1646v2PbbEthOamEAlarm 1}

fr1646v2PbbEthOamEAlarmEntry OBJECT-TYPE
   SYNTAX      Fr1646v2PbbEthOamEAlarmEntry
   MAX-ACCESS  not-accessible
   STATUS      current
   DESCRIPTION
      ""
   INDEX      { fr1646v2PbbEthOamEAlarmGlobalIx }
   ::= {fr1646v2PbbEthOamEAlarmSSCTable 1}

Fr1646v2PbbEthOamEAlarmEntry ::=
   SEQUENCE
      {
      fr1646v2PbbEthOamEAlarmGlobalIx
         GlobalIndex,
      fr1646v2PbbEthOamEAlarmDiscriminator
         Integer32,
      fr1646v2PbbEthOamEAlarmCurrent
         Integer32,
      fr1646v2PbbEthOamEAlarmPrevious
         Integer32,
      fr1646v2PbbEthOamEAlarmMask
         Integer32,
      fr1646v2PbbEthOamEAlarmLevDelay
         Integer32,
      fr1646v2PbbEthOamEAlarmLevJitter
         Integer32,
      fr1646v2PbbEthOamEAlarmLevLossOfContinuity
         Integer32,
      fr1646v2PbbEthOamEAlarmLevMismerge
         Integer32,
      fr1646v2PbbEthOamEAlarmLevUnexpectedMep
         Integer32,
      fr1646v2PbbEthOamEAlarmLevUnexpectedMegLevel
         Integer32,
      fr1646v2PbbEthOamEAlarmLevUnexpectedPeriod
         Integer32,
      fr1646v2PbbEthOamEAlarmLevRdi
         Integer32,
      fr1646v2PbbEthOamEAlarmLevAis
         Integer32,
      fr1646v2PbbEthOamEAlarmLevMacStatus
         Integer32,
      fr1646v2PbbEthOamEAlarmLevQualityMonitor
         Integer32
      }

fr1646v2PbbEthOamEAlarmGlobalIx OBJECT-TYPE
   SYNTAX      GlobalIndex
   MAX-ACCESS  not-accessible
   STATUS      current
   DESCRIPTION
      "The value of the tlsCntTreeGlobalIndex of the MANAGED OBJECT."
   ::= {fr1646v2PbbEthOamEAlarmEntry 10}

fr1646v2PbbEthOamEAlarmDiscriminator OBJECT-TYPE
   SYNTAX      Integer32
   MAX-ACCESS  read-only
   STATUS      current
   DESCRIPTION
      "Path: ethOam.alarms.alarmInfo.discriminator"
   ::= {fr1646v2PbbEthOamEAlarmEntry 16777216}

fr1646v2PbbEthOamEAlarmCurrent OBJECT-TYPE
   SYNTAX      Integer32
   MAX-ACCESS  read-only
   STATUS      current
   DESCRIPTION
      "Path: ethOam.alarms.alarmInfo.currentAlarms

       Bit meanings:
               bit 1 = delay,
               bit 2 = jitter,
               bit 3 = lossOfContinuity,
               bit 4 = mismerge,
               bit 5 = unexpectedMep,
               bit 6 = unexpectedMegLevel,
               bit 7 = unexpectedPeriod,
               bit 8 = rdi,
               bit 9 = ais,
               bit 10 = macStatus,
               bit 11 = qualityMonitor"
   ::= {fr1646v2PbbEthOamEAlarmEntry 33554432}

fr1646v2PbbEthOamEAlarmPrevious OBJECT-TYPE
   SYNTAX      Integer32
   MAX-ACCESS  read-only
   STATUS      current
   DESCRIPTION
      "Path: ethOam.alarms.alarmInfo.previousAlarms

       Bit meanings:
               bit 1 = delay,
               bit 2 = jitter,
               bit 3 = lossOfContinuity,
               bit 4 = mismerge,
               bit 5 = unexpectedMep,
               bit 6 = unexpectedMegLevel,
               bit 7 = unexpectedPeriod,
               bit 8 = rdi,
               bit 9 = ais,
               bit 10 = macStatus,
               bit 11 = qualityMonitor"
   ::= {fr1646v2PbbEthOamEAlarmEntry 50331648}

fr1646v2PbbEthOamEAlarmMask OBJECT-TYPE
   SYNTAX      Integer32
   MAX-ACCESS  read-only
   STATUS      current
   DESCRIPTION
      "Path: ethOam.alarms.alarmInfo.alarmMask

       Bit meanings:
               bit 1 = delay,
               bit 2 = jitter,
               bit 3 = lossOfContinuity,
               bit 4 = mismerge,
               bit 5 = unexpectedMep,
               bit 6 = unexpectedMegLevel,
               bit 7 = unexpectedPeriod,
               bit 8 = rdi,
               bit 9 = ais,
               bit 10 = macStatus,
               bit 11 = qualityMonitor"
   ::= {fr1646v2PbbEthOamEAlarmEntry 67108864}

fr1646v2PbbEthOamEAlarmLevDelay OBJECT-TYPE
   SYNTAX      Integer32
   MAX-ACCESS  read-only
   STATUS      current
   DESCRIPTION
      "Path: ethOam.alarms.alarmInfo.alarmLevel.delay"
   ::= {fr1646v2PbbEthOamEAlarmEntry 84017152}

fr1646v2PbbEthOamEAlarmLevJitter OBJECT-TYPE
   SYNTAX      Integer32
   MAX-ACCESS  read-only
   STATUS      current
   DESCRIPTION
      "Path: ethOam.alarms.alarmInfo.alarmLevel.jitter"
   ::= {fr1646v2PbbEthOamEAlarmEntry 84082688}

fr1646v2PbbEthOamEAlarmLevLossOfContinuity OBJECT-TYPE
   SYNTAX      Integer32
   MAX-ACCESS  read-only
   STATUS      current
   DESCRIPTION
      "Path: ethOam.alarms.alarmInfo.alarmLevel.lossOfContinuity"
   ::= {fr1646v2PbbEthOamEAlarmEntry 84148224}

fr1646v2PbbEthOamEAlarmLevMismerge OBJECT-TYPE
   SYNTAX      Integer32
   MAX-ACCESS  read-only
   STATUS      current
   DESCRIPTION
      "Path: ethOam.alarms.alarmInfo.alarmLevel.mismerge"
   ::= {fr1646v2PbbEthOamEAlarmEntry 84213760}

fr1646v2PbbEthOamEAlarmLevUnexpectedMep OBJECT-TYPE
   SYNTAX      Integer32
   MAX-ACCESS  read-only
   STATUS      current
   DESCRIPTION
      "Path: ethOam.alarms.alarmInfo.alarmLevel.unexpectedMep"
   ::= {fr1646v2PbbEthOamEAlarmEntry 84279296}

fr1646v2PbbEthOamEAlarmLevUnexpectedMegLevel OBJECT-TYPE
   SYNTAX      Integer32
   MAX-ACCESS  read-only
   STATUS      current
   DESCRIPTION
      "Path: ethOam.alarms.alarmInfo.alarmLevel.unexpectedMegLevel"
   ::= {fr1646v2PbbEthOamEAlarmEntry 84344832}

fr1646v2PbbEthOamEAlarmLevUnexpectedPeriod OBJECT-TYPE
   SYNTAX      Integer32
   MAX-ACCESS  read-only
   STATUS      current
   DESCRIPTION
      "Path: ethOam.alarms.alarmInfo.alarmLevel.unexpectedPeriod"
   ::= {fr1646v2PbbEthOamEAlarmEntry 84410368}

fr1646v2PbbEthOamEAlarmLevRdi OBJECT-TYPE
   SYNTAX      Integer32
   MAX-ACCESS  read-only
   STATUS      current
   DESCRIPTION
      "Path: ethOam.alarms.alarmInfo.alarmLevel.rdi"
   ::= {fr1646v2PbbEthOamEAlarmEntry 84475904}

fr1646v2PbbEthOamEAlarmLevAis OBJECT-TYPE
   SYNTAX      Integer32
   MAX-ACCESS  read-only
   STATUS      current
   DESCRIPTION
      "Path: ethOam.alarms.alarmInfo.alarmLevel.ais"
   ::= {fr1646v2PbbEthOamEAlarmEntry 84541440}

fr1646v2PbbEthOamEAlarmLevMacStatus OBJECT-TYPE
   SYNTAX      Integer32
   MAX-ACCESS  read-only
   STATUS      current
   DESCRIPTION
      "Path: ethOam.alarms.alarmInfo.alarmLevel.macStatus"
   ::= {fr1646v2PbbEthOamEAlarmEntry 84606976}

fr1646v2PbbEthOamEAlarmLevQualityMonitor OBJECT-TYPE
   SYNTAX      Integer32
   MAX-ACCESS  read-only
   STATUS      current
   DESCRIPTION
      "Path: ethOam.alarms.alarmInfo.alarmLevel.qualityMonitor"
   ::= {fr1646v2PbbEthOamEAlarmEntry 84672512}


fr1646v2PbbEthOamEAlarmE2 OBJECT IDENTIFIER ::= {fr1646v2PbbEthOamEAlarm 2}

fr1646v2PbbEthOamEAlarmE2Entry OBJECT IDENTIFIER ::= {fr1646v2PbbEthOamEAlarmE2 1}

fr1646v2PbbEthOamEAlarmE2Delay OBJECT IDENTIFIER ::= {fr1646v2PbbEthOamEAlarmE2Entry 11}

fr1646v2PbbEthOamEAlarmE2DelayPfx OBJECT IDENTIFIER ::= {fr1646v2PbbEthOamEAlarmE2Delay 0}

fr1646v2PbbEthOamEAlarmE2DelayOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'delay'
                representing an alarm condition in the alarm word
                of attribute 'alarmInfo' of managed object 'pbbEthOamE'
                (root='router1646') has changed from the ON to the OFF state."
   ::= {fr1646v2PbbEthOamEAlarmE2DelayPfx 1}

fr1646v2PbbEthOamEAlarmE2DelayOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'delay'
                representing an alarm condition in the alarm word
                of attribute 'alarmInfo' of managed object 'pbbEthOamE'
                (root='router1646') has changed from the OFF to the ON state."
   ::= {fr1646v2PbbEthOamEAlarmE2DelayPfx 2}

fr1646v2PbbEthOamEAlarmE2Jitter OBJECT IDENTIFIER ::= {fr1646v2PbbEthOamEAlarmE2Entry 12}

fr1646v2PbbEthOamEAlarmE2JitterPfx OBJECT IDENTIFIER ::= {fr1646v2PbbEthOamEAlarmE2Jitter 0}

fr1646v2PbbEthOamEAlarmE2JitterOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'jitter'
                representing an alarm condition in the alarm word
                of attribute 'alarmInfo' of managed object 'pbbEthOamE'
                (root='router1646') has changed from the ON to the OFF state."
   ::= {fr1646v2PbbEthOamEAlarmE2JitterPfx 1}

fr1646v2PbbEthOamEAlarmE2JitterOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'jitter'
                representing an alarm condition in the alarm word
                of attribute 'alarmInfo' of managed object 'pbbEthOamE'
                (root='router1646') has changed from the OFF to the ON state."
   ::= {fr1646v2PbbEthOamEAlarmE2JitterPfx 2}

fr1646v2PbbEthOamEAlarmE2LossOfContinuity OBJECT IDENTIFIER ::= {fr1646v2PbbEthOamEAlarmE2Entry 13}

fr1646v2PbbEthOamEAlarmE2LossOfContinuityPfx OBJECT IDENTIFIER ::= {fr1646v2PbbEthOamEAlarmE2LossOfContinuity 0}

fr1646v2PbbEthOamEAlarmE2LossOfContinuityOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'lossOfContinuity'
                representing an alarm condition in the alarm word
                of attribute 'alarmInfo' of managed object 'pbbEthOamE'
                (root='router1646') has changed from the ON to the OFF state."
   ::= {fr1646v2PbbEthOamEAlarmE2LossOfContinuityPfx 1}

fr1646v2PbbEthOamEAlarmE2LossOfContinuityOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'lossOfContinuity'
                representing an alarm condition in the alarm word
                of attribute 'alarmInfo' of managed object 'pbbEthOamE'
                (root='router1646') has changed from the OFF to the ON state."
   ::= {fr1646v2PbbEthOamEAlarmE2LossOfContinuityPfx 2}

fr1646v2PbbEthOamEAlarmE2Mismerge OBJECT IDENTIFIER ::= {fr1646v2PbbEthOamEAlarmE2Entry 14}

fr1646v2PbbEthOamEAlarmE2MismergePfx OBJECT IDENTIFIER ::= {fr1646v2PbbEthOamEAlarmE2Mismerge 0}

fr1646v2PbbEthOamEAlarmE2MismergeOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'mismerge'
                representing an alarm condition in the alarm word
                of attribute 'alarmInfo' of managed object 'pbbEthOamE'
                (root='router1646') has changed from the ON to the OFF state."
   ::= {fr1646v2PbbEthOamEAlarmE2MismergePfx 1}

fr1646v2PbbEthOamEAlarmE2MismergeOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'mismerge'
                representing an alarm condition in the alarm word
                of attribute 'alarmInfo' of managed object 'pbbEthOamE'
                (root='router1646') has changed from the OFF to the ON state."
   ::= {fr1646v2PbbEthOamEAlarmE2MismergePfx 2}

fr1646v2PbbEthOamEAlarmE2UnexpectedMep OBJECT IDENTIFIER ::= {fr1646v2PbbEthOamEAlarmE2Entry 15}

fr1646v2PbbEthOamEAlarmE2UnexpectedMepPfx OBJECT IDENTIFIER ::= {fr1646v2PbbEthOamEAlarmE2UnexpectedMep 0}

fr1646v2PbbEthOamEAlarmE2UnexpectedMepOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedMep'
                representing an alarm condition in the alarm word
                of attribute 'alarmInfo' of managed object 'pbbEthOamE'
                (root='router1646') has changed from the ON to the OFF state."
   ::= {fr1646v2PbbEthOamEAlarmE2UnexpectedMepPfx 1}

fr1646v2PbbEthOamEAlarmE2UnexpectedMepOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedMep'
                representing an alarm condition in the alarm word
                of attribute 'alarmInfo' of managed object 'pbbEthOamE'
                (root='router1646') has changed from the OFF to the ON state."
   ::= {fr1646v2PbbEthOamEAlarmE2UnexpectedMepPfx 2}

fr1646v2PbbEthOamEAlarmE2UnexpectedMegLevel OBJECT IDENTIFIER ::= {fr1646v2PbbEthOamEAlarmE2Entry 16}

fr1646v2PbbEthOamEAlarmE2UnexpectedMegLevelPfx OBJECT IDENTIFIER ::= {fr1646v2PbbEthOamEAlarmE2UnexpectedMegLevel 0}

fr1646v2PbbEthOamEAlarmE2UnexpectedMegLevelOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedMegLevel'
                representing an alarm condition in the alarm word
                of attribute 'alarmInfo' of managed object 'pbbEthOamE'
                (root='router1646') has changed from the ON to the OFF state."
   ::= {fr1646v2PbbEthOamEAlarmE2UnexpectedMegLevelPfx 1}

fr1646v2PbbEthOamEAlarmE2UnexpectedMegLevelOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedMegLevel'
                representing an alarm condition in the alarm word
                of attribute 'alarmInfo' of managed object 'pbbEthOamE'
                (root='router1646') has changed from the OFF to the ON state."
   ::= {fr1646v2PbbEthOamEAlarmE2UnexpectedMegLevelPfx 2}

fr1646v2PbbEthOamEAlarmE2UnexpectedPeriod OBJECT IDENTIFIER ::= {fr1646v2PbbEthOamEAlarmE2Entry 17}

fr1646v2PbbEthOamEAlarmE2UnexpectedPeriodPfx OBJECT IDENTIFIER ::= {fr1646v2PbbEthOamEAlarmE2UnexpectedPeriod 0}

fr1646v2PbbEthOamEAlarmE2UnexpectedPeriodOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedPeriod'
                representing an alarm condition in the alarm word
                of attribute 'alarmInfo' of managed object 'pbbEthOamE'
                (root='router1646') has changed from the ON to the OFF state."
   ::= {fr1646v2PbbEthOamEAlarmE2UnexpectedPeriodPfx 1}

fr1646v2PbbEthOamEAlarmE2UnexpectedPeriodOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedPeriod'
                representing an alarm condition in the alarm word
                of attribute 'alarmInfo' of managed object 'pbbEthOamE'
                (root='router1646') has changed from the OFF to the ON state."
   ::= {fr1646v2PbbEthOamEAlarmE2UnexpectedPeriodPfx 2}

fr1646v2PbbEthOamEAlarmE2Rdi OBJECT IDENTIFIER ::= {fr1646v2PbbEthOamEAlarmE2Entry 18}

fr1646v2PbbEthOamEAlarmE2RdiPfx OBJECT IDENTIFIER ::= {fr1646v2PbbEthOamEAlarmE2Rdi 0}

fr1646v2PbbEthOamEAlarmE2RdiOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'rdi'
                representing an alarm condition in the alarm word
                of attribute 'alarmInfo' of managed object 'pbbEthOamE'
                (root='router1646') has changed from the ON to the OFF state."
   ::= {fr1646v2PbbEthOamEAlarmE2RdiPfx 1}

fr1646v2PbbEthOamEAlarmE2RdiOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'rdi'
                representing an alarm condition in the alarm word
                of attribute 'alarmInfo' of managed object 'pbbEthOamE'
                (root='router1646') has changed from the OFF to the ON state."
   ::= {fr1646v2PbbEthOamEAlarmE2RdiPfx 2}

fr1646v2PbbEthOamEAlarmE2Ais OBJECT IDENTIFIER ::= {fr1646v2PbbEthOamEAlarmE2Entry 19}

fr1646v2PbbEthOamEAlarmE2AisPfx OBJECT IDENTIFIER ::= {fr1646v2PbbEthOamEAlarmE2Ais 0}

fr1646v2PbbEthOamEAlarmE2AisOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ais'
                representing an alarm condition in the alarm word
                of attribute 'alarmInfo' of managed object 'pbbEthOamE'
                (root='router1646') has changed from the ON to the OFF state."
   ::= {fr1646v2PbbEthOamEAlarmE2AisPfx 1}

fr1646v2PbbEthOamEAlarmE2AisOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ais'
                representing an alarm condition in the alarm word
                of attribute 'alarmInfo' of managed object 'pbbEthOamE'
                (root='router1646') has changed from the OFF to the ON state."
   ::= {fr1646v2PbbEthOamEAlarmE2AisPfx 2}

fr1646v2PbbEthOamEAlarmE2MacStatus OBJECT IDENTIFIER ::= {fr1646v2PbbEthOamEAlarmE2Entry 20}

fr1646v2PbbEthOamEAlarmE2MacStatusPfx OBJECT IDENTIFIER ::= {fr1646v2PbbEthOamEAlarmE2MacStatus 0}

fr1646v2PbbEthOamEAlarmE2MacStatusOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'macStatus'
                representing an alarm condition in the alarm word
                of attribute 'alarmInfo' of managed object 'pbbEthOamE'
                (root='router1646') has changed from the ON to the OFF state."
   ::= {fr1646v2PbbEthOamEAlarmE2MacStatusPfx 1}

fr1646v2PbbEthOamEAlarmE2MacStatusOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'macStatus'
                representing an alarm condition in the alarm word
                of attribute 'alarmInfo' of managed object 'pbbEthOamE'
                (root='router1646') has changed from the OFF to the ON state."
   ::= {fr1646v2PbbEthOamEAlarmE2MacStatusPfx 2}

fr1646v2PbbEthOamEAlarmE2QualityMonitor OBJECT IDENTIFIER ::= {fr1646v2PbbEthOamEAlarmE2Entry 21}

fr1646v2PbbEthOamEAlarmE2QualityMonitorPfx OBJECT IDENTIFIER ::= {fr1646v2PbbEthOamEAlarmE2QualityMonitor 0}

fr1646v2PbbEthOamEAlarmE2QualityMonitorOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qualityMonitor'
                representing an alarm condition in the alarm word
                of attribute 'alarmInfo' of managed object 'pbbEthOamE'
                (root='router1646') has changed from the ON to the OFF state."
   ::= {fr1646v2PbbEthOamEAlarmE2QualityMonitorPfx 1}

fr1646v2PbbEthOamEAlarmE2QualityMonitorOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qualityMonitor'
                representing an alarm condition in the alarm word
                of attribute 'alarmInfo' of managed object 'pbbEthOamE'
                (root='router1646') has changed from the OFF to the ON state."
   ::= {fr1646v2PbbEthOamEAlarmE2QualityMonitorPfx 2}



ar1646v2PbbEthOamE OBJECT IDENTIFIER ::= {r1646v2PbbEthOamE 16}


ar1646v2PbbEthOamEStopPacketDebug OBJECT IDENTIFIER ::= {ar1646v2PbbEthOamE 32}

ar1646v2PbbEthOamEStopPacketDebugTable OBJECT-TYPE
   SYNTAX      SEQUENCE OF Ar1646v2PbbEthOamEStopPacketDebugEntry
   MAX-ACCESS  not-accessible
   STATUS      current
   DESCRIPTION
      "action in the debug group"
   ::= {ar1646v2PbbEthOamEStopPacketDebug 1}

ar1646v2PbbEthOamEStopPacketDebugEntry OBJECT-TYPE
   SYNTAX      Ar1646v2PbbEthOamEStopPacketDebugEntry
   MAX-ACCESS  not-accessible
   STATUS      current
   DESCRIPTION
      ""
   INDEX      { ar1646v2PbbEthOamEStopPacketDebugGlobalIx }
   ::= {ar1646v2PbbEthOamEStopPacketDebugTable 1}

Ar1646v2PbbEthOamEStopPacketDebugEntry ::=
   SEQUENCE
      {
      ar1646v2PbbEthOamEStopPacketDebugGlobalIx
         GlobalIndex,
      ar1646v2PbbEthOamEStopPacketDebugValue
         Integer32
      }

ar1646v2PbbEthOamEStopPacketDebugGlobalIx OBJECT-TYPE
   SYNTAX      GlobalIndex
   MAX-ACCESS  not-accessible
   STATUS      current
   DESCRIPTION
      "The value of the tlsCntTreeGlobalIndex of the MANAGED OBJECT."
   ::= {ar1646v2PbbEthOamEStopPacketDebugEntry 10}

ar1646v2PbbEthOamEStopPacketDebugValue OBJECT-TYPE
   SYNTAX      Integer32
   MAX-ACCESS  read-write
   STATUS      current
   DESCRIPTION
      "Path: ethOam.actions.stopPacketDebug"
   ::= {ar1646v2PbbEthOamEStopPacketDebugEntry 2147483648}


ar1646v2PbbEthOamEStartPacketDebug OBJECT IDENTIFIER ::= {ar1646v2PbbEthOamE 31}

ar1646v2PbbEthOamEStartPacketDebugTable OBJECT-TYPE
   SYNTAX      SEQUENCE OF Ar1646v2PbbEthOamEStartPacketDebugEntry
   MAX-ACCESS  not-accessible
   STATUS      current
   DESCRIPTION
      "action in the debug group"
   ::= {ar1646v2PbbEthOamEStartPacketDebug 1}

ar1646v2PbbEthOamEStartPacketDebugEntry OBJECT-TYPE
   SYNTAX      Ar1646v2PbbEthOamEStartPacketDebugEntry
   MAX-ACCESS  not-accessible
   STATUS      current
   DESCRIPTION
      ""
   INDEX      { ar1646v2PbbEthOamEStartPacketDebugGlobalIx }
   ::= {ar1646v2PbbEthOamEStartPacketDebugTable 1}

Ar1646v2PbbEthOamEStartPacketDebugEntry ::=
   SEQUENCE
      {
      ar1646v2PbbEthOamEStartPacketDebugGlobalIx
         GlobalIndex,
      ar1646v2PbbEthOamEStartPacketDebugValue
         Integer32
      }

ar1646v2PbbEthOamEStartPacketDebugGlobalIx OBJECT-TYPE
   SYNTAX      GlobalIndex
   MAX-ACCESS  not-accessible
   STATUS      current
   DESCRIPTION
      "The value of the tlsCntTreeGlobalIndex of the MANAGED OBJECT."
   ::= {ar1646v2PbbEthOamEStartPacketDebugEntry 10}

ar1646v2PbbEthOamEStartPacketDebugValue OBJECT-TYPE
   SYNTAX      Integer32
   MAX-ACCESS  read-write
   STATUS      current
   DESCRIPTION
      "Path: ethOam.actions.startPacketDebug"
   ::= {ar1646v2PbbEthOamEStartPacketDebugEntry 2147483648}


ar1646v2PbbEthOamEClearCounters OBJECT IDENTIFIER ::= {ar1646v2PbbEthOamE 263}

ar1646v2PbbEthOamEClearCountersTable OBJECT-TYPE
   SYNTAX      SEQUENCE OF Ar1646v2PbbEthOamEClearCountersEntry
   MAX-ACCESS  not-accessible
   STATUS      current
   DESCRIPTION
      "reset counters"
   ::= {ar1646v2PbbEthOamEClearCounters 1}

ar1646v2PbbEthOamEClearCountersEntry OBJECT-TYPE
   SYNTAX      Ar1646v2PbbEthOamEClearCountersEntry
   MAX-ACCESS  not-accessible
   STATUS      current
   DESCRIPTION
      ""
   INDEX      { ar1646v2PbbEthOamEClearCountersGlobalIx }
   ::= {ar1646v2PbbEthOamEClearCountersTable 1}

Ar1646v2PbbEthOamEClearCountersEntry ::=
   SEQUENCE
      {
      ar1646v2PbbEthOamEClearCountersGlobalIx
         GlobalIndex,
      ar1646v2PbbEthOamEClearCountersValue
         Integer32
      }

ar1646v2PbbEthOamEClearCountersGlobalIx OBJECT-TYPE
   SYNTAX      GlobalIndex
   MAX-ACCESS  not-accessible
   STATUS      current
   DESCRIPTION
      "The value of the tlsCntTreeGlobalIndex of the MANAGED OBJECT."
   ::= {ar1646v2PbbEthOamEClearCountersEntry 10}

ar1646v2PbbEthOamEClearCountersValue OBJECT-TYPE
   SYNTAX      Integer32
   MAX-ACCESS  read-write
   STATUS      current
   DESCRIPTION
      "Path: ethOam.actions.clearCounters"
   ::= {ar1646v2PbbEthOamEClearCountersEntry 2147483648}


ar1646v2PbbEthOamEClearMpStats OBJECT IDENTIFIER ::= {ar1646v2PbbEthOamE 28}

ar1646v2PbbEthOamEClearMpStatsTable OBJECT-TYPE
   SYNTAX      SEQUENCE OF Ar1646v2PbbEthOamEClearMpStatsEntry
   MAX-ACCESS  not-accessible
   STATUS      current
   DESCRIPTION
      "clear Maintenance Point statistics"
   ::= {ar1646v2PbbEthOamEClearMpStats 1}

ar1646v2PbbEthOamEClearMpStatsEntry OBJECT-TYPE
   SYNTAX      Ar1646v2PbbEthOamEClearMpStatsEntry
   MAX-ACCESS  not-accessible
   STATUS      current
   DESCRIPTION
      ""
   INDEX      { ar1646v2PbbEthOamEClearMpStatsGlobalIx }
   ::= {ar1646v2PbbEthOamEClearMpStatsTable 1}

Ar1646v2PbbEthOamEClearMpStatsEntry ::=
   SEQUENCE
      {
      ar1646v2PbbEthOamEClearMpStatsGlobalIx
         GlobalIndex,
      ar1646v2PbbEthOamEClearMpStatsValue
         Integer32
      }

ar1646v2PbbEthOamEClearMpStatsGlobalIx OBJECT-TYPE
   SYNTAX      GlobalIndex
   MAX-ACCESS  not-accessible
   STATUS      current
   DESCRIPTION
      "The value of the tlsCntTreeGlobalIndex of the MANAGED OBJECT."
   ::= {ar1646v2PbbEthOamEClearMpStatsEntry 10}

ar1646v2PbbEthOamEClearMpStatsValue OBJECT-TYPE
   SYNTAX      Integer32
   MAX-ACCESS  read-write
   STATUS      current
   DESCRIPTION
      "Path: ethOam.actions.clearMpStats"
   ::= {ar1646v2PbbEthOamEClearMpStatsEntry 2147483648}


ar1646v2PbbEthOamEMaintenancePointName OBJECT IDENTIFIER ::= {ar1646v2PbbEthOamE 29}

ar1646v2PbbEthOamEMaintenancePointNameTable OBJECT-TYPE
   SYNTAX      SEQUENCE OF Ar1646v2PbbEthOamEMaintenancePointNameEntry
   MAX-ACCESS  not-accessible
   STATUS      current
   DESCRIPTION
      "data needed for clearStats action"
   ::= {ar1646v2PbbEthOamEMaintenancePointName 1}

ar1646v2PbbEthOamEMaintenancePointNameEntry OBJECT-TYPE
   SYNTAX      Ar1646v2PbbEthOamEMaintenancePointNameEntry
   MAX-ACCESS  not-accessible
   STATUS      current
   DESCRIPTION
      ""
   INDEX      { ar1646v2PbbEthOamEMaintenancePointNameGlobalIx }
   ::= {ar1646v2PbbEthOamEMaintenancePointNameTable 1}

Ar1646v2PbbEthOamEMaintenancePointNameEntry ::=
   SEQUENCE
      {
      ar1646v2PbbEthOamEMaintenancePointNameGlobalIx
         GlobalIndex,
      ar1646v2PbbEthOamEMaintenancePointNameValue
         DisplayString
      }

ar1646v2PbbEthOamEMaintenancePointNameGlobalIx OBJECT-TYPE
   SYNTAX      GlobalIndex
   MAX-ACCESS  not-accessible
   STATUS      current
   DESCRIPTION
      "The value of the tlsCntTreeGlobalIndex of the MANAGED OBJECT."
   ::= {ar1646v2PbbEthOamEMaintenancePointNameEntry 10}

ar1646v2PbbEthOamEMaintenancePointNameValue OBJECT-TYPE
   SYNTAX      DisplayString
   MAX-ACCESS  read-write
   STATUS      current
   DESCRIPTION
      "Path: ethOam.actions.maintenancePointName"
   ::= {ar1646v2PbbEthOamEMaintenancePointNameEntry 2147483648}


ar1646v2PbbEthOamESlmOnDemand OBJECT IDENTIFIER ::= {ar1646v2PbbEthOamE 45}

ar1646v2PbbEthOamESlmOnDemandTable OBJECT-TYPE
   SYNTAX      SEQUENCE OF Ar1646v2PbbEthOamESlmOnDemandEntry
   MAX-ACCESS  not-accessible
   STATUS      current
   DESCRIPTION
      "start synthetic loss measurement"
   ::= {ar1646v2PbbEthOamESlmOnDemand 1}

ar1646v2PbbEthOamESlmOnDemandEntry OBJECT-TYPE
   SYNTAX      Ar1646v2PbbEthOamESlmOnDemandEntry
   MAX-ACCESS  not-accessible
   STATUS      current
   DESCRIPTION
      ""
   INDEX      { ar1646v2PbbEthOamESlmOnDemandGlobalIx }
   ::= {ar1646v2PbbEthOamESlmOnDemandTable 1}

Ar1646v2PbbEthOamESlmOnDemandEntry ::=
   SEQUENCE
      {
      ar1646v2PbbEthOamESlmOnDemandGlobalIx
         GlobalIndex,
      ar1646v2PbbEthOamESlmOnDemandValue
         Integer32
      }

ar1646v2PbbEthOamESlmOnDemandGlobalIx OBJECT-TYPE
   SYNTAX      GlobalIndex
   MAX-ACCESS  not-accessible
   STATUS      current
   DESCRIPTION
      "The value of the tlsCntTreeGlobalIndex of the MANAGED OBJECT."
   ::= {ar1646v2PbbEthOamESlmOnDemandEntry 10}

ar1646v2PbbEthOamESlmOnDemandValue OBJECT-TYPE
   SYNTAX      Integer32
   MAX-ACCESS  read-write
   STATUS      current
   DESCRIPTION
      "Path: ethOam.actions.slmOnDemand"
   ::= {ar1646v2PbbEthOamESlmOnDemandEntry 2147483648}


ar1646v2PbbEthOamEAction OBJECT IDENTIFIER ::= {ar1646v2PbbEthOamE 46}

ar1646v2PbbEthOamEActionSSCTable OBJECT-TYPE
   SYNTAX      SEQUENCE OF Ar1646v2PbbEthOamEActionEntry
   MAX-ACCESS  not-accessible
   STATUS      current
   DESCRIPTION
      "data needed for synthetic loss measurement"
   ::= {ar1646v2PbbEthOamEAction 1}

ar1646v2PbbEthOamEActionEntry OBJECT-TYPE
   SYNTAX      Ar1646v2PbbEthOamEActionEntry
   MAX-ACCESS  not-accessible
   STATUS      current
   DESCRIPTION
      ""
   INDEX      { ar1646v2PbbEthOamEActionGlobalIx }
   ::= {ar1646v2PbbEthOamEActionSSCTable 1}

Ar1646v2PbbEthOamEActionEntry ::=
   SEQUENCE
      {
      ar1646v2PbbEthOamEActionGlobalIx
         GlobalIndex,
      ar1646v2PbbEthOamEActionAction
         INTEGER,
      ar1646v2PbbEthOamEActionName
         DisplayString
      }

ar1646v2PbbEthOamEActionGlobalIx OBJECT-TYPE
   SYNTAX      GlobalIndex
   MAX-ACCESS  not-accessible
   STATUS      current
   DESCRIPTION
      "The value of the tlsCntTreeGlobalIndex of the MANAGED OBJECT."
   ::= {ar1646v2PbbEthOamEActionEntry 10}

ar1646v2PbbEthOamEActionAction OBJECT-TYPE
   SYNTAX      INTEGER
               {
               start (1),
               stop (2)
               }
   MAX-ACCESS  read-write
   STATUS      current
   DESCRIPTION
      "Path: ethOam.actions.action.action

       Possibilities:
               start   (1)
               stop   (2)"
   ::= {ar1646v2PbbEthOamEActionEntry 16777216}

ar1646v2PbbEthOamEActionName OBJECT-TYPE
   SYNTAX      DisplayString
   MAX-ACCESS  read-write
   STATUS      current
   DESCRIPTION
      "Path: ethOam.actions.action.name"
   ::= {ar1646v2PbbEthOamEActionEntry 33554432}


ar1646v2PbbEthOamEStartMcLoopback OBJECT IDENTIFIER ::= {ar1646v2PbbEthOamE 33}

ar1646v2PbbEthOamEStartMcLoopbackTable OBJECT-TYPE
   SYNTAX      SEQUENCE OF Ar1646v2PbbEthOamEStartMcLoopbackEntry
   MAX-ACCESS  not-accessible
   STATUS      current
   DESCRIPTION
      "start multicast loopback"
   ::= {ar1646v2PbbEthOamEStartMcLoopback 1}

ar1646v2PbbEthOamEStartMcLoopbackEntry OBJECT-TYPE
   SYNTAX      Ar1646v2PbbEthOamEStartMcLoopbackEntry
   MAX-ACCESS  not-accessible
   STATUS      current
   DESCRIPTION
      ""
   INDEX      { ar1646v2PbbEthOamEStartMcLoopbackGlobalIx }
   ::= {ar1646v2PbbEthOamEStartMcLoopbackTable 1}

Ar1646v2PbbEthOamEStartMcLoopbackEntry ::=
   SEQUENCE
      {
      ar1646v2PbbEthOamEStartMcLoopbackGlobalIx
         GlobalIndex,
      ar1646v2PbbEthOamEStartMcLoopbackValue
         Integer32
      }

ar1646v2PbbEthOamEStartMcLoopbackGlobalIx OBJECT-TYPE
   SYNTAX      GlobalIndex
   MAX-ACCESS  not-accessible
   STATUS      current
   DESCRIPTION
      "The value of the tlsCntTreeGlobalIndex of the MANAGED OBJECT."
   ::= {ar1646v2PbbEthOamEStartMcLoopbackEntry 10}

ar1646v2PbbEthOamEStartMcLoopbackValue OBJECT-TYPE
   SYNTAX      Integer32
   MAX-ACCESS  read-write
   STATUS      current
   DESCRIPTION
      "Path: ethOam.actions.startMcLoopback"
   ::= {ar1646v2PbbEthOamEStartMcLoopbackEntry 2147483648}


ar1646v2PbbEthOamEMcLoopbackData OBJECT IDENTIFIER ::= {ar1646v2PbbEthOamE 34}

ar1646v2PbbEthOamEMcLoopbackDataSSCTable OBJECT-TYPE
   SYNTAX      SEQUENCE OF Ar1646v2PbbEthOamEMcLoopbackDataEntry
   MAX-ACCESS  not-accessible
   STATUS      current
   DESCRIPTION
      "data needed for multicast loopback action"
   ::= {ar1646v2PbbEthOamEMcLoopbackData 1}

ar1646v2PbbEthOamEMcLoopbackDataEntry OBJECT-TYPE
   SYNTAX      Ar1646v2PbbEthOamEMcLoopbackDataEntry
   MAX-ACCESS  not-accessible
   STATUS      current
   DESCRIPTION
      ""
   INDEX      { ar1646v2PbbEthOamEMcLoopbackDataGlobalIx }
   ::= {ar1646v2PbbEthOamEMcLoopbackDataSSCTable 1}

Ar1646v2PbbEthOamEMcLoopbackDataEntry ::=
   SEQUENCE
      {
      ar1646v2PbbEthOamEMcLoopbackDataGlobalIx
         GlobalIndex,
      ar1646v2PbbEthOamEMcLoopbackDataSourceMepName
         DisplayString,
      ar1646v2PbbEthOamEMcLoopbackDataPriority
         Integer32
      }

ar1646v2PbbEthOamEMcLoopbackDataGlobalIx OBJECT-TYPE
   SYNTAX      GlobalIndex
   MAX-ACCESS  not-accessible
   STATUS      current
   DESCRIPTION
      "The value of the tlsCntTreeGlobalIndex of the MANAGED OBJECT."
   ::= {ar1646v2PbbEthOamEMcLoopbackDataEntry 10}

ar1646v2PbbEthOamEMcLoopbackDataSourceMepName OBJECT-TYPE
   SYNTAX      DisplayString
   MAX-ACCESS  read-write
   STATUS      current
   DESCRIPTION
      "Path: ethOam.actions.mcLoopbackData.sourceMepName"
   ::= {ar1646v2PbbEthOamEMcLoopbackDataEntry 16777216}

ar1646v2PbbEthOamEMcLoopbackDataPriority OBJECT-TYPE
   SYNTAX      Integer32
   MAX-ACCESS  read-write
   STATUS      current
   DESCRIPTION
      "Path: ethOam.actions.mcLoopbackData.priority"
   ::= {ar1646v2PbbEthOamEMcLoopbackDataEntry 33554432}


ar1646v2PbbEthOamEStartLinkTrace OBJECT IDENTIFIER ::= {ar1646v2PbbEthOamE 25}

ar1646v2PbbEthOamEStartLinkTraceTable OBJECT-TYPE
   SYNTAX      SEQUENCE OF Ar1646v2PbbEthOamEStartLinkTraceEntry
   MAX-ACCESS  not-accessible
   STATUS      current
   DESCRIPTION
      "start link trace"
   ::= {ar1646v2PbbEthOamEStartLinkTrace 1}

ar1646v2PbbEthOamEStartLinkTraceEntry OBJECT-TYPE
   SYNTAX      Ar1646v2PbbEthOamEStartLinkTraceEntry
   MAX-ACCESS  not-accessible
   STATUS      current
   DESCRIPTION
      ""
   INDEX      { ar1646v2PbbEthOamEStartLinkTraceGlobalIx }
   ::= {ar1646v2PbbEthOamEStartLinkTraceTable 1}

Ar1646v2PbbEthOamEStartLinkTraceEntry ::=
   SEQUENCE
      {
      ar1646v2PbbEthOamEStartLinkTraceGlobalIx
         GlobalIndex,
      ar1646v2PbbEthOamEStartLinkTraceValue
         Integer32
      }

ar1646v2PbbEthOamEStartLinkTraceGlobalIx OBJECT-TYPE
   SYNTAX      GlobalIndex
   MAX-ACCESS  not-accessible
   STATUS      current
   DESCRIPTION
      "The value of the tlsCntTreeGlobalIndex of the MANAGED OBJECT."
   ::= {ar1646v2PbbEthOamEStartLinkTraceEntry 10}

ar1646v2PbbEthOamEStartLinkTraceValue OBJECT-TYPE
   SYNTAX      Integer32
   MAX-ACCESS  read-write
   STATUS      current
   DESCRIPTION
      "Path: ethOam.actions.startLinkTrace"
   ::= {ar1646v2PbbEthOamEStartLinkTraceEntry 2147483648}


ar1646v2PbbEthOamELinkTraceData OBJECT IDENTIFIER ::= {ar1646v2PbbEthOamE 26}

ar1646v2PbbEthOamELinkTraceDataSSCTable OBJECT-TYPE
   SYNTAX      SEQUENCE OF Ar1646v2PbbEthOamELinkTraceDataEntry
   MAX-ACCESS  not-accessible
   STATUS      current
   DESCRIPTION
      "data needed for link trace action"
   ::= {ar1646v2PbbEthOamELinkTraceData 1}

ar1646v2PbbEthOamELinkTraceDataEntry OBJECT-TYPE
   SYNTAX      Ar1646v2PbbEthOamELinkTraceDataEntry
   MAX-ACCESS  not-accessible
   STATUS      current
   DESCRIPTION
      ""
   INDEX      { ar1646v2PbbEthOamELinkTraceDataGlobalIx }
   ::= {ar1646v2PbbEthOamELinkTraceDataSSCTable 1}

Ar1646v2PbbEthOamELinkTraceDataEntry ::=
   SEQUENCE
      {
      ar1646v2PbbEthOamELinkTraceDataGlobalIx
         GlobalIndex,
      ar1646v2PbbEthOamELinkTraceDataSourceMepName
         DisplayString,
      ar1646v2PbbEthOamELinkTraceDataDestinationMepId
         Integer32,
      ar1646v2PbbEthOamELinkTraceDataDestinationMacAddress
         OCTET STRING,
      ar1646v2PbbEthOamELinkTraceDataTtl
         Integer32
      }

ar1646v2PbbEthOamELinkTraceDataGlobalIx OBJECT-TYPE
   SYNTAX      GlobalIndex
   MAX-ACCESS  not-accessible
   STATUS      current
   DESCRIPTION
      "The value of the tlsCntTreeGlobalIndex of the MANAGED OBJECT."
   ::= {ar1646v2PbbEthOamELinkTraceDataEntry 10}

ar1646v2PbbEthOamELinkTraceDataSourceMepName OBJECT-TYPE
   SYNTAX      DisplayString
   MAX-ACCESS  read-write
   STATUS      current
   DESCRIPTION
      "Path: ethOam.actions.linkTraceData.sourceMepName"
   ::= {ar1646v2PbbEthOamELinkTraceDataEntry 16777216}

ar1646v2PbbEthOamELinkTraceDataDestinationMepId OBJECT-TYPE
   SYNTAX      Integer32
   MAX-ACCESS  read-write
   STATUS      current
   DESCRIPTION
      "Path: ethOam.actions.linkTraceData.destination.mepId"
   ::= {ar1646v2PbbEthOamELinkTraceDataEntry 33619968}

ar1646v2PbbEthOamELinkTraceDataDestinationMacAddress OBJECT-TYPE
   SYNTAX      OCTET STRING
   MAX-ACCESS  read-write
   STATUS      current
   DESCRIPTION
      "Path: ethOam.actions.linkTraceData.destination.macAddress

       MAC address."
   ::= {ar1646v2PbbEthOamELinkTraceDataEntry 33685504}

ar1646v2PbbEthOamELinkTraceDataTtl OBJECT-TYPE
   SYNTAX      Integer32
   MAX-ACCESS  read-write
   STATUS      current
   DESCRIPTION
      "Path: ethOam.actions.linkTraceData.ttl"
   ::= {ar1646v2PbbEthOamELinkTraceDataEntry 50331648}


ar1646v2PbbEthOamEClearDefectLog OBJECT IDENTIFIER ::= {ar1646v2PbbEthOamE 24}

ar1646v2PbbEthOamEClearDefectLogTable OBJECT-TYPE
   SYNTAX      SEQUENCE OF Ar1646v2PbbEthOamEClearDefectLogEntry
   MAX-ACCESS  not-accessible
   STATUS      current
   DESCRIPTION
      "clear defectLog table"
   ::= {ar1646v2PbbEthOamEClearDefectLog 1}

ar1646v2PbbEthOamEClearDefectLogEntry OBJECT-TYPE
   SYNTAX      Ar1646v2PbbEthOamEClearDefectLogEntry
   MAX-ACCESS  not-accessible
   STATUS      current
   DESCRIPTION
      ""
   INDEX      { ar1646v2PbbEthOamEClearDefectLogGlobalIx }
   ::= {ar1646v2PbbEthOamEClearDefectLogTable 1}

Ar1646v2PbbEthOamEClearDefectLogEntry ::=
   SEQUENCE
      {
      ar1646v2PbbEthOamEClearDefectLogGlobalIx
         GlobalIndex,
      ar1646v2PbbEthOamEClearDefectLogValue
         Integer32
      }

ar1646v2PbbEthOamEClearDefectLogGlobalIx OBJECT-TYPE
   SYNTAX      GlobalIndex
   MAX-ACCESS  not-accessible
   STATUS      current
   DESCRIPTION
      "The value of the tlsCntTreeGlobalIndex of the MANAGED OBJECT."
   ::= {ar1646v2PbbEthOamEClearDefectLogEntry 10}

ar1646v2PbbEthOamEClearDefectLogValue OBJECT-TYPE
   SYNTAX      Integer32
   MAX-ACCESS  read-write
   STATUS      current
   DESCRIPTION
      "Path: ethOam.actions.clearDefectLog"
   ::= {ar1646v2PbbEthOamEClearDefectLogEntry 2147483648}



END
