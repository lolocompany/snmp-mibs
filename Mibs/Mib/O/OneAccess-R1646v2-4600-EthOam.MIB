OneAccess-R1646v2-4600-EthOam DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2EthOam OBJECT IDENTIFIER ::= {r1646Rootv2 4600}

r1646v2EthOamMOProp OBJECT-TYPE
   SYNTAX      SEQUENCE OF R1646v2EthOamMOPropEntry
   MAX-ACCESS  not-accessible
   STATUS      current
   DESCRIPTION
      ""
   ::= {r1646v2EthOam 1}

r1646v2EthOamMOPropEntry OBJECT-TYPE
   SYNTAX      R1646v2EthOamMOPropEntry
   MAX-ACCESS  not-accessible
   STATUS      current
   DESCRIPTION
      ""
   INDEX      { r1646v2EthOamMOPropGlobalIx }
   ::= {r1646v2EthOamMOProp 1}

R1646v2EthOamMOPropEntry ::=
   SEQUENCE
      {
      r1646v2EthOamMOPropPath
         ContainmentPath,
      r1646v2EthOamMOPropRev
         ObjectRevision,
      r1646v2EthOamMOPropGlobalIx
         GlobalIndex
      }

r1646v2EthOamMOPropPath OBJECT-TYPE
   SYNTAX      ContainmentPath
   MAX-ACCESS  read-only
   STATUS      current
   DESCRIPTION
      "Textual description of the containment tree from the instance of
       the root object down to the instance of the current object."
   ::= {r1646v2EthOamMOPropEntry 3}

r1646v2EthOamMOPropRev OBJECT-TYPE
   SYNTAX      ObjectRevision
   MAX-ACCESS  read-only
   STATUS      current
   DESCRIPTION
      "This value corresponds with the revision of the MANAGED OBJECT."
   ::= {r1646v2EthOamMOPropEntry 4}

r1646v2EthOamMOPropGlobalIx OBJECT-TYPE
   SYNTAX      GlobalIndex
   MAX-ACCESS  read-only
   STATUS      current
   DESCRIPTION
      "The value of the tlsCntTreeGlobalIndex of the MANAGED OBJECT."
   ::= {r1646v2EthOamMOPropEntry 10}



er1646v2EthOam OBJECT IDENTIFIER ::= {r1646v2EthOam 11}


er1646v2EthOamMeps OBJECT IDENTIFIER ::= {er1646v2EthOam 10}

er1646v2EthOamMepsSSCTable OBJECT-TYPE
   SYNTAX      SEQUENCE OF Er1646v2EthOamMepsEntry
   MAX-ACCESS  not-accessible
   STATUS      current
   DESCRIPTION
      "table with local MEPs"
   ::= {er1646v2EthOamMeps 1}

er1646v2EthOamMepsEntry OBJECT-TYPE
   SYNTAX      Er1646v2EthOamMepsEntry
   MAX-ACCESS  not-accessible
   STATUS      current
   DESCRIPTION
      ""
   INDEX      { er1646v2EthOamMepsGlobalIx,
                er1646v2EthOamMepsTableIx }
   ::= {er1646v2EthOamMepsSSCTable 1}

Er1646v2EthOamMepsEntry ::=
   SEQUENCE
      {
      er1646v2EthOamMepsActions
         VariableLengthTableActions,
      er1646v2EthOamMepsGlobalIx
         GlobalIndex,
      er1646v2EthOamMepsTableIx
         TableIndex,
      er1646v2EthOamMepsName
         DisplayString,
      er1646v2EthOamMepsAdminStatus
         INTEGER,
      er1646v2EthOamMepsMode
         INTEGER,
      er1646v2EthOamMepsType
         INTEGER,
      er1646v2EthOamMepsInterface
         DisplayString,
      er1646v2EthOamMepsVid
         INTEGER,
      er1646v2EthOamMepsTpid
         INTEGER,
      er1646v2EthOamMepsPrioMapQueue
         INTEGER,
      er1646v2EthOamMepsPrioMapDropLevel
         INTEGER,
      er1646v2EthOamMepsMegLevel
         Integer32,
      er1646v2EthOamMepsMepId
         Integer32,
      er1646v2EthOamMepsAlarmMask
         Integer32,
      er1646v2EthOamMepsEfd
         INTEGER,
      er1646v2EthOamMepsRdiMask
         Integer32,
      er1646v2EthOamMepsProtocolVersionLoss
         INTEGER,
      er1646v2EthOamMepsCcMegIdMaintDomainName
         DisplayString,
      er1646v2EthOamMepsCcMegIdShortMaName
         DisplayString,
      er1646v2EthOamMepsCcPriority
         Integer32,
      er1646v2EthOamMepsCcPeriod
         INTEGER,
      er1646v2EthOamMepsCcState
         INTEGER,
      er1646v2EthOamMepsCcLossThreshold
         Integer32,
      er1646v2EthOamMepsAisMegLevel
         Integer32,
      er1646v2EthOamMepsAisPriority
         Integer32,
      er1646v2EthOamMepsAisPeriod
         INTEGER,
      er1646v2EthOamMepsAisState
         INTEGER,
      er1646v2EthOamMepsLossDataCount
         Integer32,
      er1646v2EthOamMepsIndex
         INTEGER
      }

er1646v2EthOamMepsActions OBJECT-TYPE
   SYNTAX      VariableLengthTableActions
   MAX-ACCESS  read-write
   STATUS      current
   DESCRIPTION
      "By way of this field, some manipulations
       on this table may be performed."
   ::= {er1646v2EthOamMepsEntry 2}

er1646v2EthOamMepsGlobalIx OBJECT-TYPE
   SYNTAX      GlobalIndex
   MAX-ACCESS  not-accessible
   STATUS      current
   DESCRIPTION
      "The value of the tlsCntTreeGlobalIndex of the MANAGED OBJECT."
   ::= {er1646v2EthOamMepsEntry 10}

er1646v2EthOamMepsTableIx OBJECT-TYPE
   SYNTAX      TableIndex
   MAX-ACCESS  not-accessible
   STATUS      current
   DESCRIPTION
      ""
   ::= {er1646v2EthOamMepsEntry 11}

er1646v2EthOamMepsName OBJECT-TYPE
   SYNTAX      DisplayString
   MAX-ACCESS  read-write
   STATUS      current
   DESCRIPTION
      "Path: ethOam.editConf.meps.name"
   ::= {er1646v2EthOamMepsEntry 16777216}

er1646v2EthOamMepsAdminStatus OBJECT-TYPE
   SYNTAX      INTEGER
               {
               up (1),
               down (2)
               }
   MAX-ACCESS  read-write
   STATUS      current
   DESCRIPTION
      "Path: ethOam.editConf.meps.adminStatus

       Possibilities:
               up   (1)
               down   (2)"
   ::= {er1646v2EthOamMepsEntry 33554432}

er1646v2EthOamMepsMode OBJECT-TYPE
   SYNTAX      INTEGER
               {
               ym1731 (1),
               s802m1ag (2),
               hybrid (3)
               }
   MAX-ACCESS  read-write
   STATUS      current
   DESCRIPTION
      "Path: ethOam.editConf.meps.mode

       Possibilities:
               y-1731   (1)
               802-1ag   (2)
               hybrid   (3)"
   ::= {er1646v2EthOamMepsEntry 50331648}

er1646v2EthOamMepsType OBJECT-TYPE
   SYNTAX      INTEGER
               {
               inwardFacing (1),
               outwardFacing (2)
               }
   MAX-ACCESS  read-write
   STATUS      current
   DESCRIPTION
      "Path: ethOam.editConf.meps.type

       Possibilities:
               inwardFacing   (1)
               outwardFacing   (2)"
   ::= {er1646v2EthOamMepsEntry 67108864}

er1646v2EthOamMepsInterface OBJECT-TYPE
   SYNTAX      DisplayString
   MAX-ACCESS  read-write
   STATUS      current
   DESCRIPTION
      "Path: ethOam.editConf.meps.interface"
   ::= {er1646v2EthOamMepsEntry 83886080}

er1646v2EthOamMepsVid OBJECT-TYPE
   SYNTAX      INTEGER
               {
               untagged (0)
               }
   MAX-ACCESS  read-write
   STATUS      current
   DESCRIPTION
      "Path: ethOam.editConf.meps.vid

       Possibilities:
               untagged   (0)"
   ::= {er1646v2EthOamMepsEntry 100663296}

er1646v2EthOamMepsTpid OBJECT-TYPE
   SYNTAX      INTEGER
               {
               dot1Q (33024),
               dot1ad (34984)
               }
   MAX-ACCESS  read-write
   STATUS      current
   DESCRIPTION
      "Path: ethOam.editConf.meps.tpid

       Possibilities:
               dot1Q   (33024)
               dot1ad   (34984)"
   ::= {er1646v2EthOamMepsEntry 402653184}

er1646v2EthOamMepsPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.meps.prioMap.queue

       Possibilities:
               queue1   (0)
               queue2   (1)
               queue3   (2)
               queue4   (3)
               queue5   (4)
               lowDelayQueue   (5)
               lowDelay2Queue   (6)
               systemQueue   (7)"
   ::= {er1646v2EthOamMepsEntry 251723776}

er1646v2EthOamMepsPrioMapDropLevel OBJECT-TYPE
   SYNTAX      INTEGER
               {
               dropOnQueue (0)
               }
   MAX-ACCESS  read-write
   STATUS      current
   DESCRIPTION
      "Path: ethOam.editConf.meps.prioMap.dropLevel

       Possibilities:
               dropOnQueue   (0)"
   ::= {er1646v2EthOamMepsEntry 251789312}

er1646v2EthOamMepsMegLevel OBJECT-TYPE
   SYNTAX      Integer32
   MAX-ACCESS  read-write
   STATUS      current
   DESCRIPTION
      "Path: ethOam.editConf.meps.megLevel"
   ::= {er1646v2EthOamMepsEntry 117440512}

er1646v2EthOamMepsMepId OBJECT-TYPE
   SYNTAX      Integer32
   MAX-ACCESS  read-write
   STATUS      current
   DESCRIPTION
      "Path: ethOam.editConf.meps.mepId"
   ::= {er1646v2EthOamMepsEntry 134217728}

er1646v2EthOamMepsAlarmMask OBJECT-TYPE
   SYNTAX      Integer32
   MAX-ACCESS  read-write
   STATUS      current
   DESCRIPTION
      "Path: ethOam.editConf.meps.alarmMask

       Bit meanings:
               bit 4 = mismerge,
               bit 5 = unexpectedMep,
               bit 6 = unexpectedMegLevel,
               bit 7 = unexpectedPeriod,
               bit 8 = rdi,
               bit 9 = ais,
               bit 10 = macStatus"
   ::= {er1646v2EthOamMepsEntry 150994944}

er1646v2EthOamMepsEfd OBJECT-TYPE
   SYNTAX      INTEGER
               {
               disabled (0),
               enabled (1),
               enabledLfp (2)
               }
   MAX-ACCESS  read-write
   STATUS      current
   DESCRIPTION
      "Path: ethOam.editConf.meps.efd

       Possibilities:
               disabled   (0)
               enabled   (1)
               enabledLfp   (2)"
   ::= {er1646v2EthOamMepsEntry 285212672}

er1646v2EthOamMepsRdiMask OBJECT-TYPE
   SYNTAX      Integer32
   MAX-ACCESS  read-write
   STATUS      current
   DESCRIPTION
      "Path: ethOam.editConf.meps.rdiMask

       Bit meanings:
               bit 3 = lossOfContinuity,
               bit 4 = mismerge,
               bit 5 = unexpectedMep,
               bit 6 = unexpectedMegLevel,
               bit 7 = unexpectedPeriod,
               bit 10 = macStatus"
   ::= {er1646v2EthOamMepsEntry 318767104}

er1646v2EthOamMepsProtocolVersionLoss OBJECT-TYPE
   SYNTAX      INTEGER
               {
               ym1731u05m2006 (1),
               ym1731u02m2008 (2)
               }
   MAX-ACCESS  read-write
   STATUS      current
   DESCRIPTION
      "Path: ethOam.editConf.meps.protocolVersion.loss

       Possibilities:
               y-1731_05-2006   (1)
               y-1731_02-2008   (2)"
   ::= {er1646v2EthOamMepsEntry 335609856}

er1646v2EthOamMepsCcMegIdMaintDomainName OBJECT-TYPE
   SYNTAX      DisplayString
   MAX-ACCESS  read-write
   STATUS      current
   DESCRIPTION
      "Path: ethOam.editConf.meps.cc.megId.maintDomainName"
   ::= {er1646v2EthOamMepsEntry 167837952}

er1646v2EthOamMepsCcMegIdShortMaName OBJECT-TYPE
   SYNTAX      DisplayString
   MAX-ACCESS  read-write
   STATUS      current
   DESCRIPTION
      "Path: ethOam.editConf.meps.cc.megId.shortMaName"
   ::= {er1646v2EthOamMepsEntry 167838208}

er1646v2EthOamMepsCcPriority OBJECT-TYPE
   SYNTAX      Integer32
   MAX-ACCESS  read-write
   STATUS      current
   DESCRIPTION
      "Path: ethOam.editConf.meps.cc.priority"
   ::= {er1646v2EthOamMepsEntry 167903232}

er1646v2EthOamMepsCcPeriod OBJECT-TYPE
   SYNTAX      INTEGER
               {
               s10ms (2),
               s100ms (3),
               s1s (4),
               s10s (5),
               s1min (6),
               s10min (7)
               }
   MAX-ACCESS  read-write
   STATUS      current
   DESCRIPTION
      "Path: ethOam.editConf.meps.cc.period

       Possibilities:
               10ms   (2)
               100ms   (3)
               1s   (4)
               10s   (5)
               1min   (6)
               10min   (7)"
   ::= {er1646v2EthOamMepsEntry 167968768}

er1646v2EthOamMepsCcState OBJECT-TYPE
   SYNTAX      INTEGER
               {
               disabled (0),
               enabled (1)
               }
   MAX-ACCESS  read-write
   STATUS      current
   DESCRIPTION
      "Path: ethOam.editConf.meps.cc.state

       Possibilities:
               disabled   (0)
               enabled   (1)"
   ::= {er1646v2EthOamMepsEntry 168034304}

er1646v2EthOamMepsCcLossThreshold OBJECT-TYPE
   SYNTAX      Integer32
   MAX-ACCESS  read-write
   STATUS      current
   DESCRIPTION
      "Path: ethOam.editConf.meps.cc.lossThreshold"
   ::= {er1646v2EthOamMepsEntry 168099840}

er1646v2EthOamMepsAisMegLevel OBJECT-TYPE
   SYNTAX      Integer32
   MAX-ACCESS  read-write
   STATUS      current
   DESCRIPTION
      "Path: ethOam.editConf.meps.ais.megLevel"
   ::= {er1646v2EthOamMepsEntry 268500992}

er1646v2EthOamMepsAisPriority OBJECT-TYPE
   SYNTAX      Integer32
   MAX-ACCESS  read-write
   STATUS      current
   DESCRIPTION
      "Path: ethOam.editConf.meps.ais.priority"
   ::= {er1646v2EthOamMepsEntry 268566528}

er1646v2EthOamMepsAisPeriod OBJECT-TYPE
   SYNTAX      INTEGER
               {
               s1s (4),
               s1min (6)
               }
   MAX-ACCESS  read-write
   STATUS      current
   DESCRIPTION
      "Path: ethOam.editConf.meps.ais.period

       Possibilities:
               1s   (4)
               1min   (6)"
   ::= {er1646v2EthOamMepsEntry 268632064}

er1646v2EthOamMepsAisState OBJECT-TYPE
   SYNTAX      INTEGER
               {
               disabled (0),
               enabled (1)
               }
   MAX-ACCESS  read-write
   STATUS      current
   DESCRIPTION
      "Path: ethOam.editConf.meps.ais.state

       Possibilities:
               disabled   (0)
               enabled   (1)"
   ::= {er1646v2EthOamMepsEntry 268697600}

er1646v2EthOamMepsLossDataCount OBJECT-TYPE
   SYNTAX      Integer32
   MAX-ACCESS  read-write
   STATUS      current
   DESCRIPTION
      "Path: ethOam.editConf.meps.lossDataCount

       Bit meanings:
               bit 0 = data,
               bit 1 = cc,
               bit 2 = loss,
               bit 3 = delay"
   ::= {er1646v2EthOamMepsEntry 369098752}

er1646v2EthOamMepsIndex OBJECT-TYPE
   SYNTAX      INTEGER
               {
               auto (0)
               }
   MAX-ACCESS  read-write
   STATUS      current
   DESCRIPTION
      "Path: ethOam.editConf.meps.index

       Possibilities:
               auto   (0)"
   ::= {er1646v2EthOamMepsEntry 419430400}

er1646v2EthOamMepsReplyPrioMap OBJECT-TYPE
   SYNTAX      SEQUENCE OF Er1646v2EthOamMepsReplyPrioMapEntry
   MAX-ACCESS  not-accessible
   STATUS      current
   DESCRIPTION
      ""
   ::= {er1646v2EthOamMeps 352321536}

er1646v2EthOamMepsReplyPrioMapEntry OBJECT-TYPE
   SYNTAX      Er1646v2EthOamMepsReplyPrioMapEntry
   MAX-ACCESS  not-accessible
   STATUS      current
   DESCRIPTION
      ""
   INDEX      { er1646v2EthOamMepsReplyPrioMapGlobalIx,
                er1646v2EthOamMepsTableIx,
                er1646v2EthOamMepsReplyPrioMapTableIx }
   ::= {er1646v2EthOamMepsReplyPrioMap 1}

Er1646v2EthOamMepsReplyPrioMapEntry ::=
   SEQUENCE
      {
      er1646v2EthOamMepsReplyPrioMapActions
         VariableLengthTableActions,
      er1646v2EthOamMepsReplyPrioMapGlobalIx
         GlobalIndex,
      er1646v2EthOamMepsReplyPrioMapTableIx
         TableIndex,
      er1646v2EthOamMepsReplyPrioMapRxPriority
         Integer32,
      er1646v2EthOamMepsReplyPrioMapTxPriority
         INTEGER,
      er1646v2EthOamMepsReplyPrioMapQueue
         INTEGER,
      er1646v2EthOamMepsReplyPrioMapDropLevel
         INTEGER
      }

er1646v2EthOamMepsReplyPrioMapActions OBJECT-TYPE
   SYNTAX      VariableLengthTableActions
   MAX-ACCESS  read-write
   STATUS      current
   DESCRIPTION
      "By way of this field, some manipulations
       on this table may be performed."
   ::= {er1646v2EthOamMepsReplyPrioMapEntry 2}

er1646v2EthOamMepsReplyPrioMapGlobalIx OBJECT-TYPE
   SYNTAX      GlobalIndex
   MAX-ACCESS  not-accessible
   STATUS      current
   DESCRIPTION
      "The value of the tlsCntTreeGlobalIndex of the MANAGED OBJECT."
   ::= {er1646v2EthOamMepsReplyPrioMapEntry 10}

er1646v2EthOamMepsReplyPrioMapTableIx OBJECT-TYPE
   SYNTAX      TableIndex
   MAX-ACCESS  not-accessible
   STATUS      current
   DESCRIPTION
      ""
   ::= {er1646v2EthOamMepsReplyPrioMapEntry 11}

er1646v2EthOamMepsReplyPrioMapRxPriority OBJECT-TYPE
   SYNTAX      Integer32
   MAX-ACCESS  read-write
   STATUS      current
   DESCRIPTION
      "Path: ethOam.editConf.meps.replyPrioMap.rxPriority"
   ::= {er1646v2EthOamMepsReplyPrioMapEntry 16777216}

er1646v2EthOamMepsReplyPrioMapTxPriority OBJECT-TYPE
   SYNTAX      INTEGER
               {
               keepRxPrio (8)
               }
   MAX-ACCESS  read-write
   STATUS      current
   DESCRIPTION
      "Path: ethOam.editConf.meps.replyPrioMap.txPriority

       Possibilities:
               keepRxPrio   (8)"
   ::= {er1646v2EthOamMepsReplyPrioMapEntry 33554432}

er1646v2EthOamMepsReplyPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.meps.replyPrioMap.queue

       Possibilities:
               queue1   (0)
               queue2   (1)
               queue3   (2)
               queue4   (3)
               queue5   (4)
               lowDelayQueue   (5)
               lowDelay2Queue   (6)
               systemQueue   (7)"
   ::= {er1646v2EthOamMepsReplyPrioMapEntry 50331648}

er1646v2EthOamMepsReplyPrioMapDropLevel OBJECT-TYPE
   SYNTAX      INTEGER
               {
               dropOnQueue (0)
               }
   MAX-ACCESS  read-write
   STATUS      current
   DESCRIPTION
      "Path: ethOam.editConf.meps.replyPrioMap.dropLevel

       Possibilities:
               dropOnQueue   (0)"
   ::= {er1646v2EthOamMepsReplyPrioMapEntry 67108864}

er1646v2EthOamMepsManagedMep OBJECT-TYPE
   SYNTAX      SEQUENCE OF Er1646v2EthOamMepsManagedMepEntry
   MAX-ACCESS  not-accessible
   STATUS      current
   DESCRIPTION
      ""
   ::= {er1646v2EthOamMeps 184549376}

er1646v2EthOamMepsManagedMepEntry OBJECT-TYPE
   SYNTAX      Er1646v2EthOamMepsManagedMepEntry
   MAX-ACCESS  not-accessible
   STATUS      current
   DESCRIPTION
      ""
   INDEX      { er1646v2EthOamMepsManagedMepGlobalIx,
                er1646v2EthOamMepsTableIx,
                er1646v2EthOamMepsManagedMepTableIx }
   ::= {er1646v2EthOamMepsManagedMep 1}

Er1646v2EthOamMepsManagedMepEntry ::=
   SEQUENCE
      {
      er1646v2EthOamMepsManagedMepActions
         VariableLengthTableActions,
      er1646v2EthOamMepsManagedMepGlobalIx
         GlobalIndex,
      er1646v2EthOamMepsManagedMepTableIx
         TableIndex,
      er1646v2EthOamMepsManagedMepManagedMepName
         DisplayString,
      er1646v2EthOamMepsManagedMepMepId
         Integer32,
      er1646v2EthOamMepsManagedMepAlarmMask
         Integer32,
      er1646v2EthOamMepsManagedMepMacAddress
         OCTET STRING
      }

er1646v2EthOamMepsManagedMepActions OBJECT-TYPE
   SYNTAX      VariableLengthTableActions
   MAX-ACCESS  read-write
   STATUS      current
   DESCRIPTION
      "By way of this field, some manipulations
       on this table may be performed."
   ::= {er1646v2EthOamMepsManagedMepEntry 2}

er1646v2EthOamMepsManagedMepGlobalIx OBJECT-TYPE
   SYNTAX      GlobalIndex
   MAX-ACCESS  not-accessible
   STATUS      current
   DESCRIPTION
      "The value of the tlsCntTreeGlobalIndex of the MANAGED OBJECT."
   ::= {er1646v2EthOamMepsManagedMepEntry 10}

er1646v2EthOamMepsManagedMepTableIx OBJECT-TYPE
   SYNTAX      TableIndex
   MAX-ACCESS  not-accessible
   STATUS      current
   DESCRIPTION
      ""
   ::= {er1646v2EthOamMepsManagedMepEntry 11}

er1646v2EthOamMepsManagedMepManagedMepName OBJECT-TYPE
   SYNTAX      DisplayString
   MAX-ACCESS  read-write
   STATUS      current
   DESCRIPTION
      "Path: ethOam.editConf.meps.managedMep.managedMepName"
   ::= {er1646v2EthOamMepsManagedMepEntry 67108864}

er1646v2EthOamMepsManagedMepMepId OBJECT-TYPE
   SYNTAX      Integer32
   MAX-ACCESS  read-write
   STATUS      current
   DESCRIPTION
      "Path: ethOam.editConf.meps.managedMep.mepId"
   ::= {er1646v2EthOamMepsManagedMepEntry 16777216}

er1646v2EthOamMepsManagedMepAlarmMask OBJECT-TYPE
   SYNTAX      Integer32
   MAX-ACCESS  read-write
   STATUS      current
   DESCRIPTION
      "Path: ethOam.editConf.meps.managedMep.alarmMask

       Bit meanings:
               bit 3 = lossOfContinuity"
   ::= {er1646v2EthOamMepsManagedMepEntry 33554432}

er1646v2EthOamMepsManagedMepMacAddress OBJECT-TYPE
   SYNTAX      OCTET STRING
   MAX-ACCESS  read-write
   STATUS      current
   DESCRIPTION
      "Path: ethOam.editConf.meps.managedMep.macAddress

       MAC address."
   ::= {er1646v2EthOamMepsManagedMepEntry 50331648}

er1646v2EthOamMepsLoopback OBJECT-TYPE
   SYNTAX      SEQUENCE OF Er1646v2EthOamMepsLoopbackEntry
   MAX-ACCESS  not-accessible
   STATUS      current
   DESCRIPTION
      ""
   ::= {er1646v2EthOamMeps 201326592}

er1646v2EthOamMepsLoopbackEntry OBJECT-TYPE
   SYNTAX      Er1646v2EthOamMepsLoopbackEntry
   MAX-ACCESS  not-accessible
   STATUS      current
   DESCRIPTION
      ""
   INDEX      { er1646v2EthOamMepsLoopbackGlobalIx,
                er1646v2EthOamMepsTableIx,
                er1646v2EthOamMepsLoopbackTableIx }
   ::= {er1646v2EthOamMepsLoopback 1}

Er1646v2EthOamMepsLoopbackEntry ::=
   SEQUENCE
      {
      er1646v2EthOamMepsLoopbackActions
         VariableLengthTableActions,
      er1646v2EthOamMepsLoopbackGlobalIx
         GlobalIndex,
      er1646v2EthOamMepsLoopbackTableIx
         TableIndex,
      er1646v2EthOamMepsLoopbackDestinationMepId
         Integer32,
      er1646v2EthOamMepsLoopbackDestinationMacAddress
         OCTET STRING,
      er1646v2EthOamMepsLoopbackPriority
         Integer32,
      er1646v2EthOamMepsLoopbackPeriod
         INTEGER,
      er1646v2EthOamMepsLoopbackDataTlvSize
         Integer32,
      er1646v2EthOamMepsLoopbackState
         INTEGER
      }

er1646v2EthOamMepsLoopbackActions OBJECT-TYPE
   SYNTAX      VariableLengthTableActions
   MAX-ACCESS  read-write
   STATUS      current
   DESCRIPTION
      "By way of this field, some manipulations
       on this table may be performed."
   ::= {er1646v2EthOamMepsLoopbackEntry 2}

er1646v2EthOamMepsLoopbackGlobalIx OBJECT-TYPE
   SYNTAX      GlobalIndex
   MAX-ACCESS  not-accessible
   STATUS      current
   DESCRIPTION
      "The value of the tlsCntTreeGlobalIndex of the MANAGED OBJECT."
   ::= {er1646v2EthOamMepsLoopbackEntry 10}

er1646v2EthOamMepsLoopbackTableIx OBJECT-TYPE
   SYNTAX      TableIndex
   MAX-ACCESS  not-accessible
   STATUS      current
   DESCRIPTION
      ""
   ::= {er1646v2EthOamMepsLoopbackEntry 11}

er1646v2EthOamMepsLoopbackDestinationMepId OBJECT-TYPE
   SYNTAX      Integer32
   MAX-ACCESS  read-write
   STATUS      current
   DESCRIPTION
      "Path: ethOam.editConf.meps.loopback.destination.mepId"
   ::= {er1646v2EthOamMepsLoopbackEntry 16842752}

er1646v2EthOamMepsLoopbackDestinationMacAddress OBJECT-TYPE
   SYNTAX      OCTET STRING
   MAX-ACCESS  read-write
   STATUS      current
   DESCRIPTION
      "Path: ethOam.editConf.meps.loopback.destination.macAddress

       MAC address."
   ::= {er1646v2EthOamMepsLoopbackEntry 16908288}

er1646v2EthOamMepsLoopbackPriority OBJECT-TYPE
   SYNTAX      Integer32
   MAX-ACCESS  read-write
   STATUS      current
   DESCRIPTION
      "Path: ethOam.editConf.meps.loopback.priority"
   ::= {er1646v2EthOamMepsLoopbackEntry 33554432}

er1646v2EthOamMepsLoopbackPeriod OBJECT-TYPE
   SYNTAX      INTEGER
               {
               s100ms (3),
               s1s (4),
               s10s (5),
               s1min (6),
               s10min (7)
               }
   MAX-ACCESS  read-write
   STATUS      current
   DESCRIPTION
      "Path: ethOam.editConf.meps.loopback.period

       Possibilities:
               100ms   (3)
               1s   (4)
               10s   (5)
               1min   (6)
               10min   (7)"
   ::= {er1646v2EthOamMepsLoopbackEntry 50331648}

er1646v2EthOamMepsLoopbackDataTlvSize OBJECT-TYPE
   SYNTAX      Integer32
   MAX-ACCESS  read-write
   STATUS      current
   DESCRIPTION
      "Path: ethOam.editConf.meps.loopback.dataTlvSize"
   ::= {er1646v2EthOamMepsLoopbackEntry 83886080}

er1646v2EthOamMepsLoopbackState OBJECT-TYPE
   SYNTAX      INTEGER
               {
               paused (0),
               running (1)
               }
   MAX-ACCESS  read-write
   STATUS      current
   DESCRIPTION
      "Path: ethOam.editConf.meps.loopback.state

       Possibilities:
               paused   (0)
               running   (1)"
   ::= {er1646v2EthOamMepsLoopbackEntry 67108864}

er1646v2EthOamMepsLoss OBJECT-TYPE
   SYNTAX      SEQUENCE OF Er1646v2EthOamMepsLossEntry
   MAX-ACCESS  not-accessible
   STATUS      current
   DESCRIPTION
      ""
   ::= {er1646v2EthOamMeps 218103808}

er1646v2EthOamMepsLossEntry OBJECT-TYPE
   SYNTAX      Er1646v2EthOamMepsLossEntry
   MAX-ACCESS  not-accessible
   STATUS      current
   DESCRIPTION
      ""
   INDEX      { er1646v2EthOamMepsLossGlobalIx,
                er1646v2EthOamMepsTableIx,
                er1646v2EthOamMepsLossTableIx }
   ::= {er1646v2EthOamMepsLoss 1}

Er1646v2EthOamMepsLossEntry ::=
   SEQUENCE
      {
      er1646v2EthOamMepsLossActions
         VariableLengthTableActions,
      er1646v2EthOamMepsLossGlobalIx
         GlobalIndex,
      er1646v2EthOamMepsLossTableIx
         TableIndex,
      er1646v2EthOamMepsLossDestinationMepId
         Integer32,
      er1646v2EthOamMepsLossDestinationMacAddress
         OCTET STRING,
      er1646v2EthOamMepsLossPriority
         Integer32,
      er1646v2EthOamMepsLossPeriod
         INTEGER,
      er1646v2EthOamMepsLossLogging
         INTEGER,
      er1646v2EthOamMepsLossState
         INTEGER
      }

er1646v2EthOamMepsLossActions OBJECT-TYPE
   SYNTAX      VariableLengthTableActions
   MAX-ACCESS  read-write
   STATUS      current
   DESCRIPTION
      "By way of this field, some manipulations
       on this table may be performed."
   ::= {er1646v2EthOamMepsLossEntry 2}

er1646v2EthOamMepsLossGlobalIx OBJECT-TYPE
   SYNTAX      GlobalIndex
   MAX-ACCESS  not-accessible
   STATUS      current
   DESCRIPTION
      "The value of the tlsCntTreeGlobalIndex of the MANAGED OBJECT."
   ::= {er1646v2EthOamMepsLossEntry 10}

er1646v2EthOamMepsLossTableIx OBJECT-TYPE
   SYNTAX      TableIndex
   MAX-ACCESS  not-accessible
   STATUS      current
   DESCRIPTION
      ""
   ::= {er1646v2EthOamMepsLossEntry 11}

er1646v2EthOamMepsLossDestinationMepId OBJECT-TYPE
   SYNTAX      Integer32
   MAX-ACCESS  read-write
   STATUS      current
   DESCRIPTION
      "Path: ethOam.editConf.meps.loss.destination.mepId"
   ::= {er1646v2EthOamMepsLossEntry 16842752}

er1646v2EthOamMepsLossDestinationMacAddress OBJECT-TYPE
   SYNTAX      OCTET STRING
   MAX-ACCESS  read-write
   STATUS      current
   DESCRIPTION
      "Path: ethOam.editConf.meps.loss.destination.macAddress

       MAC address."
   ::= {er1646v2EthOamMepsLossEntry 16908288}

er1646v2EthOamMepsLossPriority OBJECT-TYPE
   SYNTAX      Integer32
   MAX-ACCESS  read-write
   STATUS      current
   DESCRIPTION
      "Path: ethOam.editConf.meps.loss.priority"
   ::= {er1646v2EthOamMepsLossEntry 33554432}

er1646v2EthOamMepsLossPeriod OBJECT-TYPE
   SYNTAX      INTEGER
               {
               s100ms (3),
               s1s (4),
               s10s (5),
               s1min (6),
               s10min (7)
               }
   MAX-ACCESS  read-write
   STATUS      current
   DESCRIPTION
      "Path: ethOam.editConf.meps.loss.period

       Possibilities:
               100ms   (3)
               1s   (4)
               10s   (5)
               1min   (6)
               10min   (7)"
   ::= {er1646v2EthOamMepsLossEntry 50331648}

er1646v2EthOamMepsLossLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: ethOam.editConf.meps.loss.logging

       Possibilities:
               disabled   (0)
               3min   (3)
               5min   (5)
               10min   (10)
               15min   (15)
               30min   (30)
               60min   (60)"
   ::= {er1646v2EthOamMepsLossEntry 100663296}

er1646v2EthOamMepsLossState OBJECT-TYPE
   SYNTAX      INTEGER
               {
               paused (0),
               running (1)
               }
   MAX-ACCESS  read-write
   STATUS      current
   DESCRIPTION
      "Path: ethOam.editConf.meps.loss.state

       Possibilities:
               paused   (0)
               running   (1)"
   ::= {er1646v2EthOamMepsLossEntry 117440512}

er1646v2EthOamMepsDelay OBJECT-TYPE
   SYNTAX      SEQUENCE OF Er1646v2EthOamMepsDelayEntry
   MAX-ACCESS  not-accessible
   STATUS      current
   DESCRIPTION
      ""
   ::= {er1646v2EthOamMeps 234881024}

er1646v2EthOamMepsDelayEntry OBJECT-TYPE
   SYNTAX      Er1646v2EthOamMepsDelayEntry
   MAX-ACCESS  not-accessible
   STATUS      current
   DESCRIPTION
      ""
   INDEX      { er1646v2EthOamMepsDelayGlobalIx,
                er1646v2EthOamMepsTableIx,
                er1646v2EthOamMepsDelayTableIx }
   ::= {er1646v2EthOamMepsDelay 1}

Er1646v2EthOamMepsDelayEntry ::=
   SEQUENCE
      {
      er1646v2EthOamMepsDelayActions
         VariableLengthTableActions,
      er1646v2EthOamMepsDelayGlobalIx
         GlobalIndex,
      er1646v2EthOamMepsDelayTableIx
         TableIndex,
      er1646v2EthOamMepsDelayDestinationMepId
         Integer32,
      er1646v2EthOamMepsDelayDestinationMacAddress
         OCTET STRING,
      er1646v2EthOamMepsDelayPriority
         Integer32,
      er1646v2EthOamMepsDelayPeriod
         INTEGER,
      er1646v2EthOamMepsDelayTimeOut
         Integer32,
      er1646v2EthOamMepsDelayAlarmSamples
         Integer32,
      er1646v2EthOamMepsDelayAlarmAlarmAvgOn
         Integer32,
      er1646v2EthOamMepsDelayAlarmAlarmAvgOff
         Integer32,
      er1646v2EthOamMepsDelayAlarmAlarmMaxOn
         Integer32,
      er1646v2EthOamMepsDelayAlarmAlarmMaxOff
         Integer32,
      er1646v2EthOamMepsDelayAlarmAlarmMinMaxOn
         Integer32,
      er1646v2EthOamMepsDelayAlarmAlarmMinMaxOff
         Integer32,
      er1646v2EthOamMepsDelayAlarmAlarmAvgJitterOn
         Integer32,
      er1646v2EthOamMepsDelayAlarmAlarmAvgJitterOff
         Integer32,
      er1646v2EthOamMepsDelayAlarmAlarmMaxJitterOn
         Integer32,
      er1646v2EthOamMepsDelayAlarmAlarmMaxJitterOff
         Integer32,
      er1646v2EthOamMepsDelayAlarmAlarmMask
         Integer32,
      er1646v2EthOamMepsDelayLogging
         INTEGER,
      er1646v2EthOamMepsDelayState
         INTEGER
      }

er1646v2EthOamMepsDelayActions OBJECT-TYPE
   SYNTAX      VariableLengthTableActions
   MAX-ACCESS  read-write
   STATUS      current
   DESCRIPTION
      "By way of this field, some manipulations
       on this table may be performed."
   ::= {er1646v2EthOamMepsDelayEntry 2}

er1646v2EthOamMepsDelayGlobalIx OBJECT-TYPE
   SYNTAX      GlobalIndex
   MAX-ACCESS  not-accessible
   STATUS      current
   DESCRIPTION
      "The value of the tlsCntTreeGlobalIndex of the MANAGED OBJECT."
   ::= {er1646v2EthOamMepsDelayEntry 10}

er1646v2EthOamMepsDelayTableIx OBJECT-TYPE
   SYNTAX      TableIndex
   MAX-ACCESS  not-accessible
   STATUS      current
   DESCRIPTION
      ""
   ::= {er1646v2EthOamMepsDelayEntry 11}

er1646v2EthOamMepsDelayDestinationMepId OBJECT-TYPE
   SYNTAX      Integer32
   MAX-ACCESS  read-write
   STATUS      current
   DESCRIPTION
      "Path: ethOam.editConf.meps.delay.destination.mepId"
   ::= {er1646v2EthOamMepsDelayEntry 16842752}

er1646v2EthOamMepsDelayDestinationMacAddress OBJECT-TYPE
   SYNTAX      OCTET STRING
   MAX-ACCESS  read-write
   STATUS      current
   DESCRIPTION
      "Path: ethOam.editConf.meps.delay.destination.macAddress

       MAC address."
   ::= {er1646v2EthOamMepsDelayEntry 16908288}

er1646v2EthOamMepsDelayPriority OBJECT-TYPE
   SYNTAX      Integer32
   MAX-ACCESS  read-write
   STATUS      current
   DESCRIPTION
      "Path: ethOam.editConf.meps.delay.priority"
   ::= {er1646v2EthOamMepsDelayEntry 33554432}

er1646v2EthOamMepsDelayPeriod OBJECT-TYPE
   SYNTAX      INTEGER
               {
               s100ms (3),
               s1s (4),
               s10s (5),
               s1min (6),
               s10min (7)
               }
   MAX-ACCESS  read-write
   STATUS      current
   DESCRIPTION
      "Path: ethOam.editConf.meps.delay.period

       Possibilities:
               100ms   (3)
               1s   (4)
               10s   (5)
               1min   (6)
               10min   (7)"
   ::= {er1646v2EthOamMepsDelayEntry 50331648}

er1646v2EthOamMepsDelayTimeOut OBJECT-TYPE
   SYNTAX      Integer32
   UNITS       "100msec"
   MAX-ACCESS  read-write
   STATUS      current
   DESCRIPTION
      "Path: ethOam.editConf.meps.delay.timeOut

       unit name = 100msec"
   ::= {er1646v2EthOamMepsDelayEntry 117440512}

er1646v2EthOamMepsDelayAlarmSamples OBJECT-TYPE
   SYNTAX      Integer32
   MAX-ACCESS  read-write
   STATUS      current
   DESCRIPTION
      "Path: ethOam.editConf.meps.delay.alarm.samples"
   ::= {er1646v2EthOamMepsDelayEntry 67174400}

er1646v2EthOamMepsDelayAlarmAlarmAvgOn OBJECT-TYPE
   SYNTAX      Integer32
   UNITS       "msec"
   MAX-ACCESS  read-write
   STATUS      current
   DESCRIPTION
      "Path: ethOam.editConf.meps.delay.alarm.alarmAvgOn

       unit name = msec"
   ::= {er1646v2EthOamMepsDelayEntry 67239936}

er1646v2EthOamMepsDelayAlarmAlarmAvgOff OBJECT-TYPE
   SYNTAX      Integer32
   UNITS       "msec"
   MAX-ACCESS  read-write
   STATUS      current
   DESCRIPTION
      "Path: ethOam.editConf.meps.delay.alarm.alarmAvgOff

       unit name = msec"
   ::= {er1646v2EthOamMepsDelayEntry 67305472}

er1646v2EthOamMepsDelayAlarmAlarmMaxOn OBJECT-TYPE
   SYNTAX      Integer32
   UNITS       "msec"
   MAX-ACCESS  read-write
   STATUS      current
   DESCRIPTION
      "Path: ethOam.editConf.meps.delay.alarm.alarmMaxOn

       unit name = msec"
   ::= {er1646v2EthOamMepsDelayEntry 67371008}

er1646v2EthOamMepsDelayAlarmAlarmMaxOff OBJECT-TYPE
   SYNTAX      Integer32
   UNITS       "msec"
   MAX-ACCESS  read-write
   STATUS      current
   DESCRIPTION
      "Path: ethOam.editConf.meps.delay.alarm.alarmMaxOff

       unit name = msec"
   ::= {er1646v2EthOamMepsDelayEntry 67436544}

er1646v2EthOamMepsDelayAlarmAlarmMinMaxOn OBJECT-TYPE
   SYNTAX      Integer32
   UNITS       "msec"
   MAX-ACCESS  read-write
   STATUS      current
   DESCRIPTION
      "Path: ethOam.editConf.meps.delay.alarm.alarmMinMaxOn

       unit name = msec"
   ::= {er1646v2EthOamMepsDelayEntry 67764224}

er1646v2EthOamMepsDelayAlarmAlarmMinMaxOff OBJECT-TYPE
   SYNTAX      Integer32
   UNITS       "msec"
   MAX-ACCESS  read-write
   STATUS      current
   DESCRIPTION
      "Path: ethOam.editConf.meps.delay.alarm.alarmMinMaxOff

       unit name = msec"
   ::= {er1646v2EthOamMepsDelayEntry 67829760}

er1646v2EthOamMepsDelayAlarmAlarmAvgJitterOn OBJECT-TYPE
   SYNTAX      Integer32
   UNITS       "msec"
   MAX-ACCESS  read-write
   STATUS      current
   DESCRIPTION
      "Path: ethOam.editConf.meps.delay.alarm.alarmAvgJitterOn

       unit name = msec"
   ::= {er1646v2EthOamMepsDelayEntry 67502080}

er1646v2EthOamMepsDelayAlarmAlarmAvgJitterOff OBJECT-TYPE
   SYNTAX      Integer32
   UNITS       "msec"
   MAX-ACCESS  read-write
   STATUS      current
   DESCRIPTION
      "Path: ethOam.editConf.meps.delay.alarm.alarmAvgJitterOff

       unit name = msec"
   ::= {er1646v2EthOamMepsDelayEntry 67567616}

er1646v2EthOamMepsDelayAlarmAlarmMaxJitterOn OBJECT-TYPE
   SYNTAX      Integer32
   UNITS       "msec"
   MAX-ACCESS  read-write
   STATUS      current
   DESCRIPTION
      "Path: ethOam.editConf.meps.delay.alarm.alarmMaxJitterOn

       unit name = msec"
   ::= {er1646v2EthOamMepsDelayEntry 67633152}

er1646v2EthOamMepsDelayAlarmAlarmMaxJitterOff OBJECT-TYPE
   SYNTAX      Integer32
   UNITS       "msec"
   MAX-ACCESS  read-write
   STATUS      current
   DESCRIPTION
      "Path: ethOam.editConf.meps.delay.alarm.alarmMaxJitterOff

       unit name = msec"
   ::= {er1646v2EthOamMepsDelayEntry 67698688}

er1646v2EthOamMepsDelayAlarmAlarmMask OBJECT-TYPE
   SYNTAX      Integer32
   MAX-ACCESS  read-write
   STATUS      current
   DESCRIPTION
      "Path: ethOam.editConf.meps.delay.alarm.alarmMask

       Bit meanings:
               bit 1 = delay,
               bit 2 = jitter"
   ::= {er1646v2EthOamMepsDelayEntry 67895296}

er1646v2EthOamMepsDelayLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: ethOam.editConf.meps.delay.logging

       Possibilities:
               disabled   (0)
               3min   (3)
               5min   (5)
               10min   (10)
               15min   (15)
               30min   (30)
               60min   (60)"
   ::= {er1646v2EthOamMepsDelayEntry 83886080}

er1646v2EthOamMepsDelayState OBJECT-TYPE
   SYNTAX      INTEGER
               {
               paused (0),
               running (1)
               }
   MAX-ACCESS  read-write
   STATUS      current
   DESCRIPTION
      "Path: ethOam.editConf.meps.delay.state

       Possibilities:
               paused   (0)
               running   (1)"
   ::= {er1646v2EthOamMepsDelayEntry 100663296}

er1646v2EthOamMepsQualityMonitor OBJECT-TYPE
   SYNTAX      SEQUENCE OF Er1646v2EthOamMepsQualityMonitorEntry
   MAX-ACCESS  not-accessible
   STATUS      current
   DESCRIPTION
      ""
   ::= {er1646v2EthOamMeps 301989888}

er1646v2EthOamMepsQualityMonitorEntry OBJECT-TYPE
   SYNTAX      Er1646v2EthOamMepsQualityMonitorEntry
   MAX-ACCESS  not-accessible
   STATUS      current
   DESCRIPTION
      ""
   INDEX      { er1646v2EthOamMepsQualityMonitorGlobalIx,
                er1646v2EthOamMepsTableIx,
                er1646v2EthOamMepsQualityMonitorTableIx }
   ::= {er1646v2EthOamMepsQualityMonitor 1}

Er1646v2EthOamMepsQualityMonitorEntry ::=
   SEQUENCE
      {
      er1646v2EthOamMepsQualityMonitorActions
         VariableLengthTableActions,
      er1646v2EthOamMepsQualityMonitorGlobalIx
         GlobalIndex,
      er1646v2EthOamMepsQualityMonitorTableIx
         TableIndex,
      er1646v2EthOamMepsQualityMonitorName
         DisplayString,
      er1646v2EthOamMepsQualityMonitorAdminStatus
         INTEGER,
      er1646v2EthOamMepsQualityMonitorDestinationMepId
         Integer32,
      er1646v2EthOamMepsQualityMonitorDestinationMacAddress
         OCTET STRING,
      er1646v2EthOamMepsQualityMonitorPriority
         Integer32,
      er1646v2EthOamMepsQualityMonitorPrioMapQueue
         INTEGER,
      er1646v2EthOamMepsQualityMonitorPrioMapDropLevel
         INTEGER,
      er1646v2EthOamMepsQualityMonitorProtocol
         INTEGER,
      er1646v2EthOamMepsQualityMonitorInterval
         Integer32,
      er1646v2EthOamMepsQualityMonitorTimeOut
         Integer32,
      er1646v2EthOamMepsQualityMonitorLength
         Integer32,
      er1646v2EthOamMepsQualityMonitorIdleSamples
         Integer32,
      er1646v2EthOamMepsQualityMonitorLossAlarmSamples
         Integer32,
      er1646v2EthOamMepsQualityMonitorLossAlarmAlarmOn
         Integer32,
      er1646v2EthOamMepsQualityMonitorLossAlarmAlarmOff
         Integer32,
      er1646v2EthOamMepsQualityMonitorLossAlarmAlarmUpOn
         Integer32,
      er1646v2EthOamMepsQualityMonitorLossAlarmAlarmUpOff
         Integer32,
      er1646v2EthOamMepsQualityMonitorLossAlarmAlarmDownOn
         Integer32,
      er1646v2EthOamMepsQualityMonitorLossAlarmAlarmDownOff
         Integer32,
      er1646v2EthOamMepsQualityMonitorDelayAlarmSamples
         Integer32,
      er1646v2EthOamMepsQualityMonitorDelayAlarmDelayAvrgOn
         Integer32,
      er1646v2EthOamMepsQualityMonitorDelayAlarmDelayAvrgOff
         Integer32,
      er1646v2EthOamMepsQualityMonitorDelayAlarmDelayMaxOn
         Integer32,
      er1646v2EthOamMepsQualityMonitorDelayAlarmDelayMaxOff
         Integer32,
      er1646v2EthOamMepsQualityMonitorDelayAlarmDelayMinMaxOn
         Integer32,
      er1646v2EthOamMepsQualityMonitorDelayAlarmDelayMinMaxOff
         Integer32,
      er1646v2EthOamMepsQualityMonitorDelayAlarmDsType
         INTEGER,
      er1646v2EthOamMepsQualityMonitorDelayAlarmDsBinsN
         INTEGER,
      er1646v2EthOamMepsQualityMonitorDelayAlarmDsBinsNMn
         Integer32,
      er1646v2EthOamMepsQualityMonitorDelayAlarmDsBinsNMx
         Integer32,
      er1646v2EthOamMepsQualityMonitorDelayAlarmDsBinsTB1
         Integer32,
      er1646v2EthOamMepsQualityMonitorDelayAlarmDsBinsTB2
         Integer32,
      er1646v2EthOamMepsQualityMonitorDelayAlarmDsBinsTB3
         Integer32,
      er1646v2EthOamMepsQualityMonitorDelayAlarmDsBinsTB4
         Integer32,
      er1646v2EthOamMepsQualityMonitorDelayAlarmDsBinsTB5
         Integer32,
      er1646v2EthOamMepsQualityMonitorDelayAlarmDsBinsTB6
         Integer32,
      er1646v2EthOamMepsQualityMonitorDelayAlarmDsBinsTB7
         Integer32,
      er1646v2EthOamMepsQualityMonitorDelayAlarmDsBinsTB8
         Integer32,
      er1646v2EthOamMepsQualityMonitorDelayAlarmDsBinsTMx
         Integer32,
      er1646v2EthOamMepsQualityMonitorDelayAlarmJitterAvrgOn
         Integer32,
      er1646v2EthOamMepsQualityMonitorDelayAlarmJitterAvrgOff
         Integer32,
      er1646v2EthOamMepsQualityMonitorDelayAlarmJitterMaxOn
         Integer32,
      er1646v2EthOamMepsQualityMonitorDelayAlarmJitterMaxOff
         Integer32,
      er1646v2EthOamMepsQualityMonitorDelayAlarmJsN
         INTEGER,
      er1646v2EthOamMepsQualityMonitorDelayAlarmJsNMn
         Integer32,
      er1646v2EthOamMepsQualityMonitorDelayAlarmJsNMx
         Integer32,
      er1646v2EthOamMepsQualityMonitorDelayAlarmJsTB1
         Integer32,
      er1646v2EthOamMepsQualityMonitorDelayAlarmJsTB2
         Integer32,
      er1646v2EthOamMepsQualityMonitorDelayAlarmJsTB3
         Integer32,
      er1646v2EthOamMepsQualityMonitorDelayAlarmJsTB4
         Integer32,
      er1646v2EthOamMepsQualityMonitorDelayAlarmJsTB5
         Integer32,
      er1646v2EthOamMepsQualityMonitorDelayAlarmJsTB6
         Integer32,
      er1646v2EthOamMepsQualityMonitorDelayAlarmJsTB7
         Integer32,
      er1646v2EthOamMepsQualityMonitorDelayAlarmJsTB8
         Integer32,
      er1646v2EthOamMepsQualityMonitorDelayAlarmJsTMx
         Integer32,
      er1646v2EthOamMepsQualityMonitorDelayAlarmJitterUpAvrgOn
         Integer32,
      er1646v2EthOamMepsQualityMonitorDelayAlarmJitterUpAvrgOff
         Integer32,
      er1646v2EthOamMepsQualityMonitorDelayAlarmJitterUpMaxOn
         Integer32,
      er1646v2EthOamMepsQualityMonitorDelayAlarmJitterUpMaxOff
         Integer32,
      er1646v2EthOamMepsQualityMonitorDelayAlarmJupsN
         INTEGER,
      er1646v2EthOamMepsQualityMonitorDelayAlarmJupsNMn
         Integer32,
      er1646v2EthOamMepsQualityMonitorDelayAlarmJupsNMx
         Integer32,
      er1646v2EthOamMepsQualityMonitorDelayAlarmJupsTB1
         Integer32,
      er1646v2EthOamMepsQualityMonitorDelayAlarmJupsTB2
         Integer32,
      er1646v2EthOamMepsQualityMonitorDelayAlarmJupsTB3
         Integer32,
      er1646v2EthOamMepsQualityMonitorDelayAlarmJupsTB4
         Integer32,
      er1646v2EthOamMepsQualityMonitorDelayAlarmJupsTB5
         Integer32,
      er1646v2EthOamMepsQualityMonitorDelayAlarmJupsTB6
         Integer32,
      er1646v2EthOamMepsQualityMonitorDelayAlarmJupsTB7
         Integer32,
      er1646v2EthOamMepsQualityMonitorDelayAlarmJupsTB8
         Integer32,
      er1646v2EthOamMepsQualityMonitorDelayAlarmJupsTMx
         Integer32,
      er1646v2EthOamMepsQualityMonitorDelayAlarmJitterDownAvrgOn
         Integer32,
      er1646v2EthOamMepsQualityMonitorDelayAlarmJitterDownAvrgOff
         Integer32,
      er1646v2EthOamMepsQualityMonitorDelayAlarmJitterDownMaxOn
         Integer32,
      er1646v2EthOamMepsQualityMonitorDelayAlarmJitterDownMaxOff
         Integer32,
      er1646v2EthOamMepsQualityMonitorDelayAlarmJdownsN
         INTEGER,
      er1646v2EthOamMepsQualityMonitorDelayAlarmJdownsNMn
         Integer32,
      er1646v2EthOamMepsQualityMonitorDelayAlarmJdownsNMx
         Integer32,
      er1646v2EthOamMepsQualityMonitorDelayAlarmJdownsTB1
         Integer32,
      er1646v2EthOamMepsQualityMonitorDelayAlarmJdownsTB2
         Integer32,
      er1646v2EthOamMepsQualityMonitorDelayAlarmJdownsTB3
         Integer32,
      er1646v2EthOamMepsQualityMonitorDelayAlarmJdownsTB4
         Integer32,
      er1646v2EthOamMepsQualityMonitorDelayAlarmJdownsTB5
         Integer32,
      er1646v2EthOamMepsQualityMonitorDelayAlarmJdownsTB6
         Integer32,
      er1646v2EthOamMepsQualityMonitorDelayAlarmJdownsTB7
         Integer32,
      er1646v2EthOamMepsQualityMonitorDelayAlarmJdownsTB8
         Integer32,
      er1646v2EthOamMepsQualityMonitorDelayAlarmJdownsTMx
         Integer32,
      er1646v2EthOamMepsQualityMonitorDelayAlarmDelayUpAvrgOn
         Integer32,
      er1646v2EthOamMepsQualityMonitorDelayAlarmDelayUpAvrgOff
         Integer32,
      er1646v2EthOamMepsQualityMonitorDelayAlarmDelayUpMaxOn
         Integer32,
      er1646v2EthOamMepsQualityMonitorDelayAlarmDelayUpMaxOff
         Integer32,
      er1646v2EthOamMepsQualityMonitorDelayAlarmDupsType
         INTEGER,
      er1646v2EthOamMepsQualityMonitorDelayAlarmDupsBinsN
         INTEGER,
      er1646v2EthOamMepsQualityMonitorDelayAlarmDupsBinsNMn
         Integer32,
      er1646v2EthOamMepsQualityMonitorDelayAlarmDupsBinsNMx
         Integer32,
      er1646v2EthOamMepsQualityMonitorDelayAlarmDupsBinsTB1
         Integer32,
      er1646v2EthOamMepsQualityMonitorDelayAlarmDupsBinsTB2
         Integer32,
      er1646v2EthOamMepsQualityMonitorDelayAlarmDupsBinsTB3
         Integer32,
      er1646v2EthOamMepsQualityMonitorDelayAlarmDupsBinsTB4
         Integer32,
      er1646v2EthOamMepsQualityMonitorDelayAlarmDupsBinsTB5
         Integer32,
      er1646v2EthOamMepsQualityMonitorDelayAlarmDupsBinsTB6
         Integer32,
      er1646v2EthOamMepsQualityMonitorDelayAlarmDupsBinsTB7
         Integer32,
      er1646v2EthOamMepsQualityMonitorDelayAlarmDupsBinsTB8
         Integer32,
      er1646v2EthOamMepsQualityMonitorDelayAlarmDupsBinsTMx
         Integer32,
      er1646v2EthOamMepsQualityMonitorDelayAlarmDelayDownAvrgOn
         Integer32,
      er1646v2EthOamMepsQualityMonitorDelayAlarmDelayDownAvrgOff
         Integer32,
      er1646v2EthOamMepsQualityMonitorDelayAlarmDelayDownMaxOn
         Integer32,
      er1646v2EthOamMepsQualityMonitorDelayAlarmDelayDownMaxOff
         Integer32,
      er1646v2EthOamMepsQualityMonitorDelayAlarmDdownsType
         INTEGER,
      er1646v2EthOamMepsQualityMonitorDelayAlarmDdownsBinsN
         INTEGER,
      er1646v2EthOamMepsQualityMonitorDelayAlarmDdownsBinsNMn
         Integer32,
      er1646v2EthOamMepsQualityMonitorDelayAlarmDdownsBinsNMx
         Integer32,
      er1646v2EthOamMepsQualityMonitorDelayAlarmDdownsBinsTB1
         Integer32,
      er1646v2EthOamMepsQualityMonitorDelayAlarmDdownsBinsTB2
         Integer32,
      er1646v2EthOamMepsQualityMonitorDelayAlarmDdownsBinsTB3
         Integer32,
      er1646v2EthOamMepsQualityMonitorDelayAlarmDdownsBinsTB4
         Integer32,
      er1646v2EthOamMepsQualityMonitorDelayAlarmDdownsBinsTB5
         Integer32,
      er1646v2EthOamMepsQualityMonitorDelayAlarmDdownsBinsTB6
         Integer32,
      er1646v2EthOamMepsQualityMonitorDelayAlarmDdownsBinsTB7
         Integer32,
      er1646v2EthOamMepsQualityMonitorDelayAlarmDdownsBinsTB8
         Integer32,
      er1646v2EthOamMepsQualityMonitorDelayAlarmDdownsBinsTMx
         Integer32,
      er1646v2EthOamMepsQualityMonitorAlarmMask
         Integer32,
      er1646v2EthOamMepsQualityMonitorEventMask
         Integer32,
      er1646v2EthOamMepsQualityMonitorLogging
         INTEGER,
      er1646v2EthOamMepsQualityMonitorLoggingDepth
         INTEGER
      }

er1646v2EthOamMepsQualityMonitorActions OBJECT-TYPE
   SYNTAX      VariableLengthTableActions
   MAX-ACCESS  read-write
   STATUS      current
   DESCRIPTION
      "By way of this field, some manipulations
       on this table may be performed."
   ::= {er1646v2EthOamMepsQualityMonitorEntry 2}

er1646v2EthOamMepsQualityMonitorGlobalIx OBJECT-TYPE
   SYNTAX      GlobalIndex
   MAX-ACCESS  not-accessible
   STATUS      current
   DESCRIPTION
      "The value of the tlsCntTreeGlobalIndex of the MANAGED OBJECT."
   ::= {er1646v2EthOamMepsQualityMonitorEntry 10}

er1646v2EthOamMepsQualityMonitorTableIx OBJECT-TYPE
   SYNTAX      TableIndex
   MAX-ACCESS  not-accessible
   STATUS      current
   DESCRIPTION
      ""
   ::= {er1646v2EthOamMepsQualityMonitorEntry 11}

er1646v2EthOamMepsQualityMonitorName OBJECT-TYPE
   SYNTAX      DisplayString
   MAX-ACCESS  read-write
   STATUS      current
   DESCRIPTION
      "Path: ethOam.editConf.meps.qualityMonitor.name"
   ::= {er1646v2EthOamMepsQualityMonitorEntry 234881024}

er1646v2EthOamMepsQualityMonitorAdminStatus OBJECT-TYPE
   SYNTAX      INTEGER
               {
               enabled (1),
               disabled (3)
               }
   MAX-ACCESS  read-write
   STATUS      current
   DESCRIPTION
      "Path: ethOam.editConf.meps.qualityMonitor.adminStatus

       Possibilities:
               enabled   (1)
               disabled   (3)"
   ::= {er1646v2EthOamMepsQualityMonitorEntry 402653184}

er1646v2EthOamMepsQualityMonitorDestinationMepId OBJECT-TYPE
   SYNTAX      Integer32
   MAX-ACCESS  read-write
   STATUS      current
   DESCRIPTION
      "Path: ethOam.editConf.meps.qualityMonitor.destination.mepId"
   ::= {er1646v2EthOamMepsQualityMonitorEntry 16842752}

er1646v2EthOamMepsQualityMonitorDestinationMacAddress OBJECT-TYPE
   SYNTAX      OCTET STRING
   MAX-ACCESS  read-write
   STATUS      current
   DESCRIPTION
      "Path: ethOam.editConf.meps.qualityMonitor.destination.macAddress

       MAC address."
   ::= {er1646v2EthOamMepsQualityMonitorEntry 16908288}

er1646v2EthOamMepsQualityMonitorPriority OBJECT-TYPE
   SYNTAX      Integer32
   MAX-ACCESS  read-write
   STATUS      current
   DESCRIPTION
      "Path: ethOam.editConf.meps.qualityMonitor.priority"
   ::= {er1646v2EthOamMepsQualityMonitorEntry 33554432}

er1646v2EthOamMepsQualityMonitorPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.meps.qualityMonitor.prioMap.queue

       Possibilities:
               queue1   (0)
               queue2   (1)
               queue3   (2)
               queue4   (3)
               queue5   (4)
               lowDelayQueue   (5)
               lowDelay2Queue   (6)
               systemQueue   (7)"
   ::= {er1646v2EthOamMepsQualityMonitorEntry 285278208}

er1646v2EthOamMepsQualityMonitorPrioMapDropLevel OBJECT-TYPE
   SYNTAX      INTEGER
               {
               dropOnQueue (0)
               }
   MAX-ACCESS  read-write
   STATUS      current
   DESCRIPTION
      "Path: ethOam.editConf.meps.qualityMonitor.prioMap.dropLevel

       Possibilities:
               dropOnQueue   (0)"
   ::= {er1646v2EthOamMepsQualityMonitorEntry 285343744}

er1646v2EthOamMepsQualityMonitorProtocol OBJECT-TYPE
   SYNTAX      INTEGER
               {
               loopback (4),
               synthLoss (6),
               delay (7)
               }
   MAX-ACCESS  read-write
   STATUS      current
   DESCRIPTION
      "Path: ethOam.editConf.meps.qualityMonitor.protocol

       Possibilities:
               loopback   (4)
               synthLoss   (6)
               delay   (7)"
   ::= {er1646v2EthOamMepsQualityMonitorEntry 520093696}

er1646v2EthOamMepsQualityMonitorInterval OBJECT-TYPE
   SYNTAX      Integer32
   UNITS       "100msec"
   MAX-ACCESS  read-write
   STATUS      current
   DESCRIPTION
      "Path: ethOam.editConf.meps.qualityMonitor.interval

       unit name = 100msec"
   ::= {er1646v2EthOamMepsQualityMonitorEntry 50331648}

er1646v2EthOamMepsQualityMonitorTimeOut OBJECT-TYPE
   SYNTAX      Integer32
   UNITS       "100msec"
   MAX-ACCESS  read-write
   STATUS      current
   DESCRIPTION
      "Path: ethOam.editConf.meps.qualityMonitor.timeOut

       unit name = 100msec"
   ::= {er1646v2EthOamMepsQualityMonitorEntry 150994944}

er1646v2EthOamMepsQualityMonitorLength OBJECT-TYPE
   SYNTAX      Integer32
   MAX-ACCESS  read-write
   STATUS      current
   DESCRIPTION
      "Path: ethOam.editConf.meps.qualityMonitor.length"
   ::= {er1646v2EthOamMepsQualityMonitorEntry 83886080}

er1646v2EthOamMepsQualityMonitorIdleSamples OBJECT-TYPE
   SYNTAX      Integer32
   MAX-ACCESS  read-write
   STATUS      current
   DESCRIPTION
      "Path: ethOam.editConf.meps.qualityMonitor.idleSamples"
   ::= {er1646v2EthOamMepsQualityMonitorEntry 419430400}

er1646v2EthOamMepsQualityMonitorLossAlarmSamples OBJECT-TYPE
   SYNTAX      Integer32
   MAX-ACCESS  read-write
   STATUS      current
   DESCRIPTION
      "Path: ethOam.editConf.meps.qualityMonitor.lossAlarm.samples"
   ::= {er1646v2EthOamMepsQualityMonitorEntry 100728832}

er1646v2EthOamMepsQualityMonitorLossAlarmAlarmOn OBJECT-TYPE
   SYNTAX      Integer32
   MAX-ACCESS  read-write
   STATUS      current
   DESCRIPTION
      "Path: ethOam.editConf.meps.qualityMonitor.lossAlarm.alarmOn"
   ::= {er1646v2EthOamMepsQualityMonitorEntry 100794368}

er1646v2EthOamMepsQualityMonitorLossAlarmAlarmOff OBJECT-TYPE
   SYNTAX      Integer32
   MAX-ACCESS  read-write
   STATUS      current
   DESCRIPTION
      "Path: ethOam.editConf.meps.qualityMonitor.lossAlarm.alarmOff"
   ::= {er1646v2EthOamMepsQualityMonitorEntry 100859904}

er1646v2EthOamMepsQualityMonitorLossAlarmAlarmUpOn OBJECT-TYPE
   SYNTAX      Integer32
   MAX-ACCESS  read-write
   STATUS      current
   DESCRIPTION
      "Path: ethOam.editConf.meps.qualityMonitor.lossAlarm.alarmUpOn"
   ::= {er1646v2EthOamMepsQualityMonitorEntry 100925440}

er1646v2EthOamMepsQualityMonitorLossAlarmAlarmUpOff OBJECT-TYPE
   SYNTAX      Integer32
   MAX-ACCESS  read-write
   STATUS      current
   DESCRIPTION
      "Path: ethOam.editConf.meps.qualityMonitor.lossAlarm.alarmUpOff"
   ::= {er1646v2EthOamMepsQualityMonitorEntry 100990976}

er1646v2EthOamMepsQualityMonitorLossAlarmAlarmDownOn OBJECT-TYPE
   SYNTAX      Integer32
   MAX-ACCESS  read-write
   STATUS      current
   DESCRIPTION
      "Path: ethOam.editConf.meps.qualityMonitor.lossAlarm.alarmDownOn"
   ::= {er1646v2EthOamMepsQualityMonitorEntry 101056512}

er1646v2EthOamMepsQualityMonitorLossAlarmAlarmDownOff OBJECT-TYPE
   SYNTAX      Integer32
   MAX-ACCESS  read-write
   STATUS      current
   DESCRIPTION
      "Path: ethOam.editConf.meps.qualityMonitor.lossAlarm.alarmDownOff"
   ::= {er1646v2EthOamMepsQualityMonitorEntry 101122048}

er1646v2EthOamMepsQualityMonitorDelayAlarmSamples OBJECT-TYPE
   SYNTAX      Integer32
   MAX-ACCESS  read-write
   STATUS      current
   DESCRIPTION
      "Path: ethOam.editConf.meps.qualityMonitor.delayAlarm.samples"
   ::= {er1646v2EthOamMepsQualityMonitorEntry 117506048}

er1646v2EthOamMepsQualityMonitorDelayAlarmDelayAvrgOn OBJECT-TYPE
   SYNTAX      Integer32
   UNITS       "msec"
   MAX-ACCESS  read-write
   STATUS      current
   DESCRIPTION
      "Path: ethOam.editConf.meps.qualityMonitor.delayAlarm.delayAvrgOn

       unit name = msec"
   ::= {er1646v2EthOamMepsQualityMonitorEntry 117571584}

er1646v2EthOamMepsQualityMonitorDelayAlarmDelayAvrgOff OBJECT-TYPE
   SYNTAX      Integer32
   UNITS       "msec"
   MAX-ACCESS  read-write
   STATUS      current
   DESCRIPTION
      "Path: ethOam.editConf.meps.qualityMonitor.delayAlarm.delayAvrgOff

       unit name = msec"
   ::= {er1646v2EthOamMepsQualityMonitorEntry 117637120}

er1646v2EthOamMepsQualityMonitorDelayAlarmDelayMaxOn OBJECT-TYPE
   SYNTAX      Integer32
   UNITS       "msec"
   MAX-ACCESS  read-write
   STATUS      current
   DESCRIPTION
      "Path: ethOam.editConf.meps.qualityMonitor.delayAlarm.delayMaxOn

       unit name = msec"
   ::= {er1646v2EthOamMepsQualityMonitorEntry 117702656}

er1646v2EthOamMepsQualityMonitorDelayAlarmDelayMaxOff OBJECT-TYPE
   SYNTAX      Integer32
   UNITS       "msec"
   MAX-ACCESS  read-write
   STATUS      current
   DESCRIPTION
      "Path: ethOam.editConf.meps.qualityMonitor.delayAlarm.delayMaxOff

       unit name = msec"
   ::= {er1646v2EthOamMepsQualityMonitorEntry 117768192}

er1646v2EthOamMepsQualityMonitorDelayAlarmDelayMinMaxOn OBJECT-TYPE
   SYNTAX      Integer32
   UNITS       "msec"
   MAX-ACCESS  read-write
   STATUS      current
   DESCRIPTION
      "Path: ethOam.editConf.meps.qualityMonitor.delayAlarm.delayMinMaxOn

       unit name = msec"
   ::= {er1646v2EthOamMepsQualityMonitorEntry 118095872}

er1646v2EthOamMepsQualityMonitorDelayAlarmDelayMinMaxOff OBJECT-TYPE
   SYNTAX      Integer32
   UNITS       "msec"
   MAX-ACCESS  read-write
   STATUS      current
   DESCRIPTION
      "Path: ethOam.editConf.meps.qualityMonitor.delayAlarm.delayMinMaxOff

       unit name = msec"
   ::= {er1646v2EthOamMepsQualityMonitorEntry 118161408}

er1646v2EthOamMepsQualityMonitorDelayAlarmDsType OBJECT-TYPE
   SYNTAX      INTEGER
               {
               fd (1),
               fdr (2)
               }
   MAX-ACCESS  read-write
   STATUS      current
   DESCRIPTION
      "Path: ethOam.editConf.meps.qualityMonitor.delayAlarm.delayStat.type

       Possibilities:
               fd   (1)
               fdr   (2)"
   ::= {er1646v2EthOamMepsQualityMonitorEntry 119283712}

er1646v2EthOamMepsQualityMonitorDelayAlarmDsBinsN OBJECT-TYPE
   SYNTAX      INTEGER
               {
               none (0)
               }
   MAX-ACCESS  read-write
   STATUS      current
   DESCRIPTION
      "Path: ethOam.editConf.meps.qualityMonitor.delayAlarm.delayStat.bins.none

       Possibilities:
               none   (0)"
   ::= {er1646v2EthOamMepsQualityMonitorEntry 119292928}

er1646v2EthOamMepsQualityMonitorDelayAlarmDsBinsNMn OBJECT-TYPE
   SYNTAX      Integer32
   UNITS       "msec"
   MAX-ACCESS  read-write
   STATUS      current
   DESCRIPTION
      "Path: ethOam.editConf.meps.qualityMonitor.delayAlarm.delayStat.bins.range.min

       unit name = msec"
   ::= {er1646v2EthOamMepsQualityMonitorEntry 119294080}

er1646v2EthOamMepsQualityMonitorDelayAlarmDsBinsNMx OBJECT-TYPE
   SYNTAX      Integer32
   UNITS       "msec"
   MAX-ACCESS  read-write
   STATUS      current
   DESCRIPTION
      "Path: ethOam.editConf.meps.qualityMonitor.delayAlarm.delayStat.bins.range.max

       unit name = msec"
   ::= {er1646v2EthOamMepsQualityMonitorEntry 119294208}

er1646v2EthOamMepsQualityMonitorDelayAlarmDsBinsTB1 OBJECT-TYPE
   SYNTAX      Integer32
   UNITS       "msec"
   MAX-ACCESS  read-write
   STATUS      current
   DESCRIPTION
      "Path: ethOam.editConf.meps.qualityMonitor.delayAlarm.delayStat.bins.table.bin1

       unit name = msec"
   ::= {er1646v2EthOamMepsQualityMonitorEntry 119295040}

er1646v2EthOamMepsQualityMonitorDelayAlarmDsBinsTB2 OBJECT-TYPE
   SYNTAX      Integer32
   UNITS       "msec"
   MAX-ACCESS  read-write
   STATUS      current
   DESCRIPTION
      "Path: ethOam.editConf.meps.qualityMonitor.delayAlarm.delayStat.bins.table.bin2

       unit name = msec"
   ::= {er1646v2EthOamMepsQualityMonitorEntry 119295104}

er1646v2EthOamMepsQualityMonitorDelayAlarmDsBinsTB3 OBJECT-TYPE
   SYNTAX      Integer32
   UNITS       "msec"
   MAX-ACCESS  read-write
   STATUS      current
   DESCRIPTION
      "Path: ethOam.editConf.meps.qualityMonitor.delayAlarm.delayStat.bins.table.bin3

       unit name = msec"
   ::= {er1646v2EthOamMepsQualityMonitorEntry 119295168}

er1646v2EthOamMepsQualityMonitorDelayAlarmDsBinsTB4 OBJECT-TYPE
   SYNTAX      Integer32
   UNITS       "msec"
   MAX-ACCESS  read-write
   STATUS      current
   DESCRIPTION
      "Path: ethOam.editConf.meps.qualityMonitor.delayAlarm.delayStat.bins.table.bin4

       unit name = msec"
   ::= {er1646v2EthOamMepsQualityMonitorEntry 119295232}

er1646v2EthOamMepsQualityMonitorDelayAlarmDsBinsTB5 OBJECT-TYPE
   SYNTAX      Integer32
   UNITS       "msec"
   MAX-ACCESS  read-write
   STATUS      current
   DESCRIPTION
      "Path: ethOam.editConf.meps.qualityMonitor.delayAlarm.delayStat.bins.table.bin5

       unit name = msec"
   ::= {er1646v2EthOamMepsQualityMonitorEntry 119295296}

er1646v2EthOamMepsQualityMonitorDelayAlarmDsBinsTB6 OBJECT-TYPE
   SYNTAX      Integer32
   UNITS       "msec"
   MAX-ACCESS  read-write
   STATUS      current
   DESCRIPTION
      "Path: ethOam.editConf.meps.qualityMonitor.delayAlarm.delayStat.bins.table.bin6

       unit name = msec"
   ::= {er1646v2EthOamMepsQualityMonitorEntry 119295360}

er1646v2EthOamMepsQualityMonitorDelayAlarmDsBinsTB7 OBJECT-TYPE
   SYNTAX      Integer32
   UNITS       "msec"
   MAX-ACCESS  read-write
   STATUS      current
   DESCRIPTION
      "Path: ethOam.editConf.meps.qualityMonitor.delayAlarm.delayStat.bins.table.bin7

       unit name = msec"
   ::= {er1646v2EthOamMepsQualityMonitorEntry 119295424}

er1646v2EthOamMepsQualityMonitorDelayAlarmDsBinsTB8 OBJECT-TYPE
   SYNTAX      Integer32
   UNITS       "msec"
   MAX-ACCESS  read-write
   STATUS      current
   DESCRIPTION
      "Path: ethOam.editConf.meps.qualityMonitor.delayAlarm.delayStat.bins.table.bin8

       unit name = msec"
   ::= {er1646v2EthOamMepsQualityMonitorEntry 119295488}

er1646v2EthOamMepsQualityMonitorDelayAlarmDsBinsTMx OBJECT-TYPE
   SYNTAX      Integer32
   UNITS       "msec"
   MAX-ACCESS  read-write
   STATUS      current
   DESCRIPTION
      "Path: ethOam.editConf.meps.qualityMonitor.delayAlarm.delayStat.bins.table.max

       unit name = msec"
   ::= {er1646v2EthOamMepsQualityMonitorEntry 119295552}

er1646v2EthOamMepsQualityMonitorDelayAlarmJitterAvrgOn OBJECT-TYPE
   SYNTAX      Integer32
   UNITS       "msec"
   MAX-ACCESS  read-write
   STATUS      current
   DESCRIPTION
      "Path: ethOam.editConf.meps.qualityMonitor.delayAlarm.jitterAvrgOn

       unit name = msec"
   ::= {er1646v2EthOamMepsQualityMonitorEntry 117833728}

er1646v2EthOamMepsQualityMonitorDelayAlarmJitterAvrgOff OBJECT-TYPE
   SYNTAX      Integer32
   UNITS       "msec"
   MAX-ACCESS  read-write
   STATUS      current
   DESCRIPTION
      "Path: ethOam.editConf.meps.qualityMonitor.delayAlarm.jitterAvrgOff

       unit name = msec"
   ::= {er1646v2EthOamMepsQualityMonitorEntry 117899264}

er1646v2EthOamMepsQualityMonitorDelayAlarmJitterMaxOn OBJECT-TYPE
   SYNTAX      Integer32
   UNITS       "msec"
   MAX-ACCESS  read-write
   STATUS      current
   DESCRIPTION
      "Path: ethOam.editConf.meps.qualityMonitor.delayAlarm.jitterMaxOn

       unit name = msec"
   ::= {er1646v2EthOamMepsQualityMonitorEntry 117964800}

er1646v2EthOamMepsQualityMonitorDelayAlarmJitterMaxOff OBJECT-TYPE
   SYNTAX      Integer32
   UNITS       "msec"
   MAX-ACCESS  read-write
   STATUS      current
   DESCRIPTION
      "Path: ethOam.editConf.meps.qualityMonitor.delayAlarm.jitterMaxOff

       unit name = msec"
   ::= {er1646v2EthOamMepsQualityMonitorEntry 118030336}

er1646v2EthOamMepsQualityMonitorDelayAlarmJsN OBJECT-TYPE
   SYNTAX      INTEGER
               {
               none (0)
               }
   MAX-ACCESS  read-write
   STATUS      current
   DESCRIPTION
      "Path: ethOam.editConf.meps.qualityMonitor.delayAlarm.jitterStat.none

       Possibilities:
               none   (0)"
   ::= {er1646v2EthOamMepsQualityMonitorEntry 119676928}

er1646v2EthOamMepsQualityMonitorDelayAlarmJsNMn OBJECT-TYPE
   SYNTAX      Integer32
   UNITS       "msec"
   MAX-ACCESS  read-write
   STATUS      current
   DESCRIPTION
      "Path: ethOam.editConf.meps.qualityMonitor.delayAlarm.jitterStat.range.min

       unit name = msec"
   ::= {er1646v2EthOamMepsQualityMonitorEntry 119686144}

er1646v2EthOamMepsQualityMonitorDelayAlarmJsNMx OBJECT-TYPE
   SYNTAX      Integer32
   UNITS       "msec"
   MAX-ACCESS  read-write
   STATUS      current
   DESCRIPTION
      "Path: ethOam.editConf.meps.qualityMonitor.delayAlarm.jitterStat.range.max

       unit name = msec"
   ::= {er1646v2EthOamMepsQualityMonitorEntry 119687168}

er1646v2EthOamMepsQualityMonitorDelayAlarmJsTB1 OBJECT-TYPE
   SYNTAX      Integer32
   UNITS       "msec"
   MAX-ACCESS  read-write
   STATUS      current
   DESCRIPTION
      "Path: ethOam.editConf.meps.qualityMonitor.delayAlarm.jitterStat.table.bin1

       unit name = msec"
   ::= {er1646v2EthOamMepsQualityMonitorEntry 119693824}

er1646v2EthOamMepsQualityMonitorDelayAlarmJsTB2 OBJECT-TYPE
   SYNTAX      Integer32
   UNITS       "msec"
   MAX-ACCESS  read-write
   STATUS      current
   DESCRIPTION
      "Path: ethOam.editConf.meps.qualityMonitor.delayAlarm.jitterStat.table.bin2

       unit name = msec"
   ::= {er1646v2EthOamMepsQualityMonitorEntry 119694336}

er1646v2EthOamMepsQualityMonitorDelayAlarmJsTB3 OBJECT-TYPE
   SYNTAX      Integer32
   UNITS       "msec"
   MAX-ACCESS  read-write
   STATUS      current
   DESCRIPTION
      "Path: ethOam.editConf.meps.qualityMonitor.delayAlarm.jitterStat.table.bin3

       unit name = msec"
   ::= {er1646v2EthOamMepsQualityMonitorEntry 119694848}

er1646v2EthOamMepsQualityMonitorDelayAlarmJsTB4 OBJECT-TYPE
   SYNTAX      Integer32
   UNITS       "msec"
   MAX-ACCESS  read-write
   STATUS      current
   DESCRIPTION
      "Path: ethOam.editConf.meps.qualityMonitor.delayAlarm.jitterStat.table.bin4

       unit name = msec"
   ::= {er1646v2EthOamMepsQualityMonitorEntry 119695360}

er1646v2EthOamMepsQualityMonitorDelayAlarmJsTB5 OBJECT-TYPE
   SYNTAX      Integer32
   UNITS       "msec"
   MAX-ACCESS  read-write
   STATUS      current
   DESCRIPTION
      "Path: ethOam.editConf.meps.qualityMonitor.delayAlarm.jitterStat.table.bin5

       unit name = msec"
   ::= {er1646v2EthOamMepsQualityMonitorEntry 119695872}

er1646v2EthOamMepsQualityMonitorDelayAlarmJsTB6 OBJECT-TYPE
   SYNTAX      Integer32
   UNITS       "msec"
   MAX-ACCESS  read-write
   STATUS      current
   DESCRIPTION
      "Path: ethOam.editConf.meps.qualityMonitor.delayAlarm.jitterStat.table.bin6

       unit name = msec"
   ::= {er1646v2EthOamMepsQualityMonitorEntry 119696384}

er1646v2EthOamMepsQualityMonitorDelayAlarmJsTB7 OBJECT-TYPE
   SYNTAX      Integer32
   UNITS       "msec"
   MAX-ACCESS  read-write
   STATUS      current
   DESCRIPTION
      "Path: ethOam.editConf.meps.qualityMonitor.delayAlarm.jitterStat.table.bin7

       unit name = msec"
   ::= {er1646v2EthOamMepsQualityMonitorEntry 119696896}

er1646v2EthOamMepsQualityMonitorDelayAlarmJsTB8 OBJECT-TYPE
   SYNTAX      Integer32
   UNITS       "msec"
   MAX-ACCESS  read-write
   STATUS      current
   DESCRIPTION
      "Path: ethOam.editConf.meps.qualityMonitor.delayAlarm.jitterStat.table.bin8

       unit name = msec"
   ::= {er1646v2EthOamMepsQualityMonitorEntry 119697408}

er1646v2EthOamMepsQualityMonitorDelayAlarmJsTMx OBJECT-TYPE
   SYNTAX      Integer32
   UNITS       "msec"
   MAX-ACCESS  read-write
   STATUS      current
   DESCRIPTION
      "Path: ethOam.editConf.meps.qualityMonitor.delayAlarm.jitterStat.table.max

       unit name = msec"
   ::= {er1646v2EthOamMepsQualityMonitorEntry 119697920}

er1646v2EthOamMepsQualityMonitorDelayAlarmJitterUpAvrgOn OBJECT-TYPE
   SYNTAX      Integer32
   UNITS       "msec"
   MAX-ACCESS  read-write
   STATUS      current
   DESCRIPTION
      "Path: ethOam.editConf.meps.qualityMonitor.delayAlarm.jitterUpAvrgOn

       unit name = msec"
   ::= {er1646v2EthOamMepsQualityMonitorEntry 118226944}

er1646v2EthOamMepsQualityMonitorDelayAlarmJitterUpAvrgOff OBJECT-TYPE
   SYNTAX      Integer32
   UNITS       "msec"
   MAX-ACCESS  read-write
   STATUS      current
   DESCRIPTION
      "Path: ethOam.editConf.meps.qualityMonitor.delayAlarm.jitterUpAvrgOff

       unit name = msec"
   ::= {er1646v2EthOamMepsQualityMonitorEntry 118292480}

er1646v2EthOamMepsQualityMonitorDelayAlarmJitterUpMaxOn OBJECT-TYPE
   SYNTAX      Integer32
   UNITS       "msec"
   MAX-ACCESS  read-write
   STATUS      current
   DESCRIPTION
      "Path: ethOam.editConf.meps.qualityMonitor.delayAlarm.jitterUpMaxOn

       unit name = msec"
   ::= {er1646v2EthOamMepsQualityMonitorEntry 118358016}

er1646v2EthOamMepsQualityMonitorDelayAlarmJitterUpMaxOff OBJECT-TYPE
   SYNTAX      Integer32
   UNITS       "msec"
   MAX-ACCESS  read-write
   STATUS      current
   DESCRIPTION
      "Path: ethOam.editConf.meps.qualityMonitor.delayAlarm.jitterUpMaxOff

       unit name = msec"
   ::= {er1646v2EthOamMepsQualityMonitorEntry 118423552}

er1646v2EthOamMepsQualityMonitorDelayAlarmJupsN OBJECT-TYPE
   SYNTAX      INTEGER
               {
               none (0)
               }
   MAX-ACCESS  read-write
   STATUS      current
   DESCRIPTION
      "Path: ethOam.editConf.meps.qualityMonitor.delayAlarm.jitterUpStat.none

       Possibilities:
               none   (0)"
   ::= {er1646v2EthOamMepsQualityMonitorEntry 119808000}

er1646v2EthOamMepsQualityMonitorDelayAlarmJupsNMn OBJECT-TYPE
   SYNTAX      Integer32
   UNITS       "msec"
   MAX-ACCESS  read-write
   STATUS      current
   DESCRIPTION
      "Path: ethOam.editConf.meps.qualityMonitor.delayAlarm.jitterUpStat.range.min

       unit name = msec"
   ::= {er1646v2EthOamMepsQualityMonitorEntry 119817216}

er1646v2EthOamMepsQualityMonitorDelayAlarmJupsNMx OBJECT-TYPE
   SYNTAX      Integer32
   UNITS       "msec"
   MAX-ACCESS  read-write
   STATUS      current
   DESCRIPTION
      "Path: ethOam.editConf.meps.qualityMonitor.delayAlarm.jitterUpStat.range.max

       unit name = msec"
   ::= {er1646v2EthOamMepsQualityMonitorEntry 119818240}

er1646v2EthOamMepsQualityMonitorDelayAlarmJupsTB1 OBJECT-TYPE
   SYNTAX      Integer32
   UNITS       "msec"
   MAX-ACCESS  read-write
   STATUS      current
   DESCRIPTION
      "Path: ethOam.editConf.meps.qualityMonitor.delayAlarm.jitterUpStat.table.bin1

       unit name = msec"
   ::= {er1646v2EthOamMepsQualityMonitorEntry 119824896}

er1646v2EthOamMepsQualityMonitorDelayAlarmJupsTB2 OBJECT-TYPE
   SYNTAX      Integer32
   UNITS       "msec"
   MAX-ACCESS  read-write
   STATUS      current
   DESCRIPTION
      "Path: ethOam.editConf.meps.qualityMonitor.delayAlarm.jitterUpStat.table.bin2

       unit name = msec"
   ::= {er1646v2EthOamMepsQualityMonitorEntry 119825408}

er1646v2EthOamMepsQualityMonitorDelayAlarmJupsTB3 OBJECT-TYPE
   SYNTAX      Integer32
   UNITS       "msec"
   MAX-ACCESS  read-write
   STATUS      current
   DESCRIPTION
      "Path: ethOam.editConf.meps.qualityMonitor.delayAlarm.jitterUpStat.table.bin3

       unit name = msec"
   ::= {er1646v2EthOamMepsQualityMonitorEntry 119825920}

er1646v2EthOamMepsQualityMonitorDelayAlarmJupsTB4 OBJECT-TYPE
   SYNTAX      Integer32
   UNITS       "msec"
   MAX-ACCESS  read-write
   STATUS      current
   DESCRIPTION
      "Path: ethOam.editConf.meps.qualityMonitor.delayAlarm.jitterUpStat.table.bin4

       unit name = msec"
   ::= {er1646v2EthOamMepsQualityMonitorEntry 119826432}

er1646v2EthOamMepsQualityMonitorDelayAlarmJupsTB5 OBJECT-TYPE
   SYNTAX      Integer32
   UNITS       "msec"
   MAX-ACCESS  read-write
   STATUS      current
   DESCRIPTION
      "Path: ethOam.editConf.meps.qualityMonitor.delayAlarm.jitterUpStat.table.bin5

       unit name = msec"
   ::= {er1646v2EthOamMepsQualityMonitorEntry 119826944}

er1646v2EthOamMepsQualityMonitorDelayAlarmJupsTB6 OBJECT-TYPE
   SYNTAX      Integer32
   UNITS       "msec"
   MAX-ACCESS  read-write
   STATUS      current
   DESCRIPTION
      "Path: ethOam.editConf.meps.qualityMonitor.delayAlarm.jitterUpStat.table.bin6

       unit name = msec"
   ::= {er1646v2EthOamMepsQualityMonitorEntry 119827456}

er1646v2EthOamMepsQualityMonitorDelayAlarmJupsTB7 OBJECT-TYPE
   SYNTAX      Integer32
   UNITS       "msec"
   MAX-ACCESS  read-write
   STATUS      current
   DESCRIPTION
      "Path: ethOam.editConf.meps.qualityMonitor.delayAlarm.jitterUpStat.table.bin7

       unit name = msec"
   ::= {er1646v2EthOamMepsQualityMonitorEntry 119827968}

er1646v2EthOamMepsQualityMonitorDelayAlarmJupsTB8 OBJECT-TYPE
   SYNTAX      Integer32
   UNITS       "msec"
   MAX-ACCESS  read-write
   STATUS      current
   DESCRIPTION
      "Path: ethOam.editConf.meps.qualityMonitor.delayAlarm.jitterUpStat.table.bin8

       unit name = msec"
   ::= {er1646v2EthOamMepsQualityMonitorEntry 119828480}

er1646v2EthOamMepsQualityMonitorDelayAlarmJupsTMx OBJECT-TYPE
   SYNTAX      Integer32
   UNITS       "msec"
   MAX-ACCESS  read-write
   STATUS      current
   DESCRIPTION
      "Path: ethOam.editConf.meps.qualityMonitor.delayAlarm.jitterUpStat.table.max

       unit name = msec"
   ::= {er1646v2EthOamMepsQualityMonitorEntry 119828992}

er1646v2EthOamMepsQualityMonitorDelayAlarmJitterDownAvrgOn OBJECT-TYPE
   SYNTAX      Integer32
   UNITS       "msec"
   MAX-ACCESS  read-write
   STATUS      current
   DESCRIPTION
      "Path: ethOam.editConf.meps.qualityMonitor.delayAlarm.jitterDownAvrgOn

       unit name = msec"
   ::= {er1646v2EthOamMepsQualityMonitorEntry 118489088}

er1646v2EthOamMepsQualityMonitorDelayAlarmJitterDownAvrgOff OBJECT-TYPE
   SYNTAX      Integer32
   UNITS       "msec"
   MAX-ACCESS  read-write
   STATUS      current
   DESCRIPTION
      "Path: ethOam.editConf.meps.qualityMonitor.delayAlarm.jitterDownAvrgOff

       unit name = msec"
   ::= {er1646v2EthOamMepsQualityMonitorEntry 118554624}

er1646v2EthOamMepsQualityMonitorDelayAlarmJitterDownMaxOn OBJECT-TYPE
   SYNTAX      Integer32
   UNITS       "msec"
   MAX-ACCESS  read-write
   STATUS      current
   DESCRIPTION
      "Path: ethOam.editConf.meps.qualityMonitor.delayAlarm.jitterDownMaxOn

       unit name = msec"
   ::= {er1646v2EthOamMepsQualityMonitorEntry 118620160}

er1646v2EthOamMepsQualityMonitorDelayAlarmJitterDownMaxOff OBJECT-TYPE
   SYNTAX      Integer32
   UNITS       "msec"
   MAX-ACCESS  read-write
   STATUS      current
   DESCRIPTION
      "Path: ethOam.editConf.meps.qualityMonitor.delayAlarm.jitterDownMaxOff

       unit name = msec"
   ::= {er1646v2EthOamMepsQualityMonitorEntry 118685696}

er1646v2EthOamMepsQualityMonitorDelayAlarmJdownsN OBJECT-TYPE
   SYNTAX      INTEGER
               {
               none (0)
               }
   MAX-ACCESS  read-write
   STATUS      current
   DESCRIPTION
      "Path: ethOam.editConf.meps.qualityMonitor.delayAlarm.jitterDownStat.none

       Possibilities:
               none   (0)"
   ::= {er1646v2EthOamMepsQualityMonitorEntry 119939072}

er1646v2EthOamMepsQualityMonitorDelayAlarmJdownsNMn OBJECT-TYPE
   SYNTAX      Integer32
   UNITS       "msec"
   MAX-ACCESS  read-write
   STATUS      current
   DESCRIPTION
      "Path: ethOam.editConf.meps.qualityMonitor.delayAlarm.jitterDownStat.range.min

       unit name = msec"
   ::= {er1646v2EthOamMepsQualityMonitorEntry 119948288}

er1646v2EthOamMepsQualityMonitorDelayAlarmJdownsNMx OBJECT-TYPE
   SYNTAX      Integer32
   UNITS       "msec"
   MAX-ACCESS  read-write
   STATUS      current
   DESCRIPTION
      "Path: ethOam.editConf.meps.qualityMonitor.delayAlarm.jitterDownStat.range.max

       unit name = msec"
   ::= {er1646v2EthOamMepsQualityMonitorEntry 119949312}

er1646v2EthOamMepsQualityMonitorDelayAlarmJdownsTB1 OBJECT-TYPE
   SYNTAX      Integer32
   UNITS       "msec"
   MAX-ACCESS  read-write
   STATUS      current
   DESCRIPTION
      "Path: ethOam.editConf.meps.qualityMonitor.delayAlarm.jitterDownStat.table.bin1

       unit name = msec"
   ::= {er1646v2EthOamMepsQualityMonitorEntry 119955968}

er1646v2EthOamMepsQualityMonitorDelayAlarmJdownsTB2 OBJECT-TYPE
   SYNTAX      Integer32
   UNITS       "msec"
   MAX-ACCESS  read-write
   STATUS      current
   DESCRIPTION
      "Path: ethOam.editConf.meps.qualityMonitor.delayAlarm.jitterDownStat.table.bin2

       unit name = msec"
   ::= {er1646v2EthOamMepsQualityMonitorEntry 119956480}

er1646v2EthOamMepsQualityMonitorDelayAlarmJdownsTB3 OBJECT-TYPE
   SYNTAX      Integer32
   UNITS       "msec"
   MAX-ACCESS  read-write
   STATUS      current
   DESCRIPTION
      "Path: ethOam.editConf.meps.qualityMonitor.delayAlarm.jitterDownStat.table.bin3

       unit name = msec"
   ::= {er1646v2EthOamMepsQualityMonitorEntry 119956992}

er1646v2EthOamMepsQualityMonitorDelayAlarmJdownsTB4 OBJECT-TYPE
   SYNTAX      Integer32
   UNITS       "msec"
   MAX-ACCESS  read-write
   STATUS      current
   DESCRIPTION
      "Path: ethOam.editConf.meps.qualityMonitor.delayAlarm.jitterDownStat.table.bin4

       unit name = msec"
   ::= {er1646v2EthOamMepsQualityMonitorEntry 119957504}

er1646v2EthOamMepsQualityMonitorDelayAlarmJdownsTB5 OBJECT-TYPE
   SYNTAX      Integer32
   UNITS       "msec"
   MAX-ACCESS  read-write
   STATUS      current
   DESCRIPTION
      "Path: ethOam.editConf.meps.qualityMonitor.delayAlarm.jitterDownStat.table.bin5

       unit name = msec"
   ::= {er1646v2EthOamMepsQualityMonitorEntry 119958016}

er1646v2EthOamMepsQualityMonitorDelayAlarmJdownsTB6 OBJECT-TYPE
   SYNTAX      Integer32
   UNITS       "msec"
   MAX-ACCESS  read-write
   STATUS      current
   DESCRIPTION
      "Path: ethOam.editConf.meps.qualityMonitor.delayAlarm.jitterDownStat.table.bin6

       unit name = msec"
   ::= {er1646v2EthOamMepsQualityMonitorEntry 119958528}

er1646v2EthOamMepsQualityMonitorDelayAlarmJdownsTB7 OBJECT-TYPE
   SYNTAX      Integer32
   UNITS       "msec"
   MAX-ACCESS  read-write
   STATUS      current
   DESCRIPTION
      "Path: ethOam.editConf.meps.qualityMonitor.delayAlarm.jitterDownStat.table.bin7

       unit name = msec"
   ::= {er1646v2EthOamMepsQualityMonitorEntry 119959040}

er1646v2EthOamMepsQualityMonitorDelayAlarmJdownsTB8 OBJECT-TYPE
   SYNTAX      Integer32
   UNITS       "msec"
   MAX-ACCESS  read-write
   STATUS      current
   DESCRIPTION
      "Path: ethOam.editConf.meps.qualityMonitor.delayAlarm.jitterDownStat.table.bin8

       unit name = msec"
   ::= {er1646v2EthOamMepsQualityMonitorEntry 119959552}

er1646v2EthOamMepsQualityMonitorDelayAlarmJdownsTMx OBJECT-TYPE
   SYNTAX      Integer32
   UNITS       "msec"
   MAX-ACCESS  read-write
   STATUS      current
   DESCRIPTION
      "Path: ethOam.editConf.meps.qualityMonitor.delayAlarm.jitterDownStat.table.max

       unit name = msec"
   ::= {er1646v2EthOamMepsQualityMonitorEntry 119960064}

er1646v2EthOamMepsQualityMonitorDelayAlarmDelayUpAvrgOn OBJECT-TYPE
   SYNTAX      Integer32
   UNITS       "msec"
   MAX-ACCESS  read-write
   STATUS      current
   DESCRIPTION
      "Path: ethOam.editConf.meps.qualityMonitor.delayAlarm.delayUpAvrgOn

       unit name = msec"
   ::= {er1646v2EthOamMepsQualityMonitorEntry 118751232}

er1646v2EthOamMepsQualityMonitorDelayAlarmDelayUpAvrgOff OBJECT-TYPE
   SYNTAX      Integer32
   UNITS       "msec"
   MAX-ACCESS  read-write
   STATUS      current
   DESCRIPTION
      "Path: ethOam.editConf.meps.qualityMonitor.delayAlarm.delayUpAvrgOff

       unit name = msec"
   ::= {er1646v2EthOamMepsQualityMonitorEntry 118816768}

er1646v2EthOamMepsQualityMonitorDelayAlarmDelayUpMaxOn OBJECT-TYPE
   SYNTAX      Integer32
   UNITS       "msec"
   MAX-ACCESS  read-write
   STATUS      current
   DESCRIPTION
      "Path: ethOam.editConf.meps.qualityMonitor.delayAlarm.delayUpMaxOn

       unit name = msec"
   ::= {er1646v2EthOamMepsQualityMonitorEntry 118882304}

er1646v2EthOamMepsQualityMonitorDelayAlarmDelayUpMaxOff OBJECT-TYPE
   SYNTAX      Integer32
   UNITS       "msec"
   MAX-ACCESS  read-write
   STATUS      current
   DESCRIPTION
      "Path: ethOam.editConf.meps.qualityMonitor.delayAlarm.delayUpMaxOff

       unit name = msec"
   ::= {er1646v2EthOamMepsQualityMonitorEntry 118947840}

er1646v2EthOamMepsQualityMonitorDelayAlarmDupsType OBJECT-TYPE
   SYNTAX      INTEGER
               {
               fd (1),
               fdr (2)
               }
   MAX-ACCESS  read-write
   STATUS      current
   DESCRIPTION
      "Path: ethOam.editConf.meps.qualityMonitor.delayAlarm.delayUpStat.type

       Possibilities:
               fd   (1)
               fdr   (2)"
   ::= {er1646v2EthOamMepsQualityMonitorEntry 119414784}

er1646v2EthOamMepsQualityMonitorDelayAlarmDupsBinsN OBJECT-TYPE
   SYNTAX      INTEGER
               {
               none (0)
               }
   MAX-ACCESS  read-write
   STATUS      current
   DESCRIPTION
      "Path: ethOam.editConf.meps.qualityMonitor.delayAlarm.delayUpStat.bins.none

       Possibilities:
               none   (0)"
   ::= {er1646v2EthOamMepsQualityMonitorEntry 119424000}

er1646v2EthOamMepsQualityMonitorDelayAlarmDupsBinsNMn OBJECT-TYPE
   SYNTAX      Integer32
   UNITS       "msec"
   MAX-ACCESS  read-write
   STATUS      current
   DESCRIPTION
      "Path: ethOam.editConf.meps.qualityMonitor.delayAlarm.delayUpStat.bins.range.min

       unit name = msec"
   ::= {er1646v2EthOamMepsQualityMonitorEntry 119425152}

er1646v2EthOamMepsQualityMonitorDelayAlarmDupsBinsNMx OBJECT-TYPE
   SYNTAX      Integer32
   UNITS       "msec"
   MAX-ACCESS  read-write
   STATUS      current
   DESCRIPTION
      "Path: ethOam.editConf.meps.qualityMonitor.delayAlarm.delayUpStat.bins.range.max

       unit name = msec"
   ::= {er1646v2EthOamMepsQualityMonitorEntry 119425280}

er1646v2EthOamMepsQualityMonitorDelayAlarmDupsBinsTB1 OBJECT-TYPE
   SYNTAX      Integer32
   UNITS       "msec"
   MAX-ACCESS  read-write
   STATUS      current
   DESCRIPTION
      "Path: ethOam.editConf.meps.qualityMonitor.delayAlarm.delayUpStat.bins.table.bin1

       unit name = msec"
   ::= {er1646v2EthOamMepsQualityMonitorEntry 119426112}

er1646v2EthOamMepsQualityMonitorDelayAlarmDupsBinsTB2 OBJECT-TYPE
   SYNTAX      Integer32
   UNITS       "msec"
   MAX-ACCESS  read-write
   STATUS      current
   DESCRIPTION
      "Path: ethOam.editConf.meps.qualityMonitor.delayAlarm.delayUpStat.bins.table.bin2

       unit name = msec"
   ::= {er1646v2EthOamMepsQualityMonitorEntry 119426176}

er1646v2EthOamMepsQualityMonitorDelayAlarmDupsBinsTB3 OBJECT-TYPE
   SYNTAX      Integer32
   UNITS       "msec"
   MAX-ACCESS  read-write
   STATUS      current
   DESCRIPTION
      "Path: ethOam.editConf.meps.qualityMonitor.delayAlarm.delayUpStat.bins.table.bin3

       unit name = msec"
   ::= {er1646v2EthOamMepsQualityMonitorEntry 119426240}

er1646v2EthOamMepsQualityMonitorDelayAlarmDupsBinsTB4 OBJECT-TYPE
   SYNTAX      Integer32
   UNITS       "msec"
   MAX-ACCESS  read-write
   STATUS      current
   DESCRIPTION
      "Path: ethOam.editConf.meps.qualityMonitor.delayAlarm.delayUpStat.bins.table.bin4

       unit name = msec"
   ::= {er1646v2EthOamMepsQualityMonitorEntry 119426304}

er1646v2EthOamMepsQualityMonitorDelayAlarmDupsBinsTB5 OBJECT-TYPE
   SYNTAX      Integer32
   UNITS       "msec"
   MAX-ACCESS  read-write
   STATUS      current
   DESCRIPTION
      "Path: ethOam.editConf.meps.qualityMonitor.delayAlarm.delayUpStat.bins.table.bin5

       unit name = msec"
   ::= {er1646v2EthOamMepsQualityMonitorEntry 119426368}

er1646v2EthOamMepsQualityMonitorDelayAlarmDupsBinsTB6 OBJECT-TYPE
   SYNTAX      Integer32
   UNITS       "msec"
   MAX-ACCESS  read-write
   STATUS      current
   DESCRIPTION
      "Path: ethOam.editConf.meps.qualityMonitor.delayAlarm.delayUpStat.bins.table.bin6

       unit name = msec"
   ::= {er1646v2EthOamMepsQualityMonitorEntry 119426432}

er1646v2EthOamMepsQualityMonitorDelayAlarmDupsBinsTB7 OBJECT-TYPE
   SYNTAX      Integer32
   UNITS       "msec"
   MAX-ACCESS  read-write
   STATUS      current
   DESCRIPTION
      "Path: ethOam.editConf.meps.qualityMonitor.delayAlarm.delayUpStat.bins.table.bin7

       unit name = msec"
   ::= {er1646v2EthOamMepsQualityMonitorEntry 119426496}

er1646v2EthOamMepsQualityMonitorDelayAlarmDupsBinsTB8 OBJECT-TYPE
   SYNTAX      Integer32
   UNITS       "msec"
   MAX-ACCESS  read-write
   STATUS      current
   DESCRIPTION
      "Path: ethOam.editConf.meps.qualityMonitor.delayAlarm.delayUpStat.bins.table.bin8

       unit name = msec"
   ::= {er1646v2EthOamMepsQualityMonitorEntry 119426560}

er1646v2EthOamMepsQualityMonitorDelayAlarmDupsBinsTMx OBJECT-TYPE
   SYNTAX      Integer32
   UNITS       "msec"
   MAX-ACCESS  read-write
   STATUS      current
   DESCRIPTION
      "Path: ethOam.editConf.meps.qualityMonitor.delayAlarm.delayUpStat.bins.table.max

       unit name = msec"
   ::= {er1646v2EthOamMepsQualityMonitorEntry 119426624}

er1646v2EthOamMepsQualityMonitorDelayAlarmDelayDownAvrgOn OBJECT-TYPE
   SYNTAX      Integer32
   UNITS       "msec"
   MAX-ACCESS  read-write
   STATUS      current
   DESCRIPTION
      "Path: ethOam.editConf.meps.qualityMonitor.delayAlarm.delayDownAvrgOn

       unit name = msec"
   ::= {er1646v2EthOamMepsQualityMonitorEntry 119013376}

er1646v2EthOamMepsQualityMonitorDelayAlarmDelayDownAvrgOff OBJECT-TYPE
   SYNTAX      Integer32
   UNITS       "msec"
   MAX-ACCESS  read-write
   STATUS      current
   DESCRIPTION
      "Path: ethOam.editConf.meps.qualityMonitor.delayAlarm.delayDownAvrgOff

       unit name = msec"
   ::= {er1646v2EthOamMepsQualityMonitorEntry 119078912}

er1646v2EthOamMepsQualityMonitorDelayAlarmDelayDownMaxOn OBJECT-TYPE
   SYNTAX      Integer32
   UNITS       "msec"
   MAX-ACCESS  read-write
   STATUS      current
   DESCRIPTION
      "Path: ethOam.editConf.meps.qualityMonitor.delayAlarm.delayDownMaxOn

       unit name = msec"
   ::= {er1646v2EthOamMepsQualityMonitorEntry 119144448}

er1646v2EthOamMepsQualityMonitorDelayAlarmDelayDownMaxOff OBJECT-TYPE
   SYNTAX      Integer32
   UNITS       "msec"
   MAX-ACCESS  read-write
   STATUS      current
   DESCRIPTION
      "Path: ethOam.editConf.meps.qualityMonitor.delayAlarm.delayDownMaxOff

       unit name = msec"
   ::= {er1646v2EthOamMepsQualityMonitorEntry 119209984}

er1646v2EthOamMepsQualityMonitorDelayAlarmDdownsType OBJECT-TYPE
   SYNTAX      INTEGER
               {
               fd (1),
               fdr (2)
               }
   MAX-ACCESS  read-write
   STATUS      current
   DESCRIPTION
      "Path: ethOam.editConf.meps.qualityMonitor.delayAlarm.delayDownStat.type

       Possibilities:
               fd   (1)
               fdr   (2)"
   ::= {er1646v2EthOamMepsQualityMonitorEntry 119545856}

er1646v2EthOamMepsQualityMonitorDelayAlarmDdownsBinsN OBJECT-TYPE
   SYNTAX      INTEGER
               {
               none (0)
               }
   MAX-ACCESS  read-write
   STATUS      current
   DESCRIPTION
      "Path: ethOam.editConf.meps.qualityMonitor.delayAlarm.delayDownStat.bins.none

       Possibilities:
               none   (0)"
   ::= {er1646v2EthOamMepsQualityMonitorEntry 119555072}

er1646v2EthOamMepsQualityMonitorDelayAlarmDdownsBinsNMn OBJECT-TYPE
   SYNTAX      Integer32
   UNITS       "msec"
   MAX-ACCESS  read-write
   STATUS      current
   DESCRIPTION
      "Path: ethOam.editConf.meps.qualityMonitor.delayAlarm.delayDownStat.bins.range.min

       unit name = msec"
   ::= {er1646v2EthOamMepsQualityMonitorEntry 119556224}

er1646v2EthOamMepsQualityMonitorDelayAlarmDdownsBinsNMx OBJECT-TYPE
   SYNTAX      Integer32
   UNITS       "msec"
   MAX-ACCESS  read-write
   STATUS      current
   DESCRIPTION
      "Path: ethOam.editConf.meps.qualityMonitor.delayAlarm.delayDownStat.bins.range.max

       unit name = msec"
   ::= {er1646v2EthOamMepsQualityMonitorEntry 119556352}

er1646v2EthOamMepsQualityMonitorDelayAlarmDdownsBinsTB1 OBJECT-TYPE
   SYNTAX      Integer32
   UNITS       "msec"
   MAX-ACCESS  read-write
   STATUS      current
   DESCRIPTION
      "Path: ethOam.editConf.meps.qualityMonitor.delayAlarm.delayDownStat.bins.table.bin1

       unit name = msec"
   ::= {er1646v2EthOamMepsQualityMonitorEntry 119557184}

er1646v2EthOamMepsQualityMonitorDelayAlarmDdownsBinsTB2 OBJECT-TYPE
   SYNTAX      Integer32
   UNITS       "msec"
   MAX-ACCESS  read-write
   STATUS      current
   DESCRIPTION
      "Path: ethOam.editConf.meps.qualityMonitor.delayAlarm.delayDownStat.bins.table.bin2

       unit name = msec"
   ::= {er1646v2EthOamMepsQualityMonitorEntry 119557248}

er1646v2EthOamMepsQualityMonitorDelayAlarmDdownsBinsTB3 OBJECT-TYPE
   SYNTAX      Integer32
   UNITS       "msec"
   MAX-ACCESS  read-write
   STATUS      current
   DESCRIPTION
      "Path: ethOam.editConf.meps.qualityMonitor.delayAlarm.delayDownStat.bins.table.bin3

       unit name = msec"
   ::= {er1646v2EthOamMepsQualityMonitorEntry 119557312}

er1646v2EthOamMepsQualityMonitorDelayAlarmDdownsBinsTB4 OBJECT-TYPE
   SYNTAX      Integer32
   UNITS       "msec"
   MAX-ACCESS  read-write
   STATUS      current
   DESCRIPTION
      "Path: ethOam.editConf.meps.qualityMonitor.delayAlarm.delayDownStat.bins.table.bin4

       unit name = msec"
   ::= {er1646v2EthOamMepsQualityMonitorEntry 119557376}

er1646v2EthOamMepsQualityMonitorDelayAlarmDdownsBinsTB5 OBJECT-TYPE
   SYNTAX      Integer32
   UNITS       "msec"
   MAX-ACCESS  read-write
   STATUS      current
   DESCRIPTION
      "Path: ethOam.editConf.meps.qualityMonitor.delayAlarm.delayDownStat.bins.table.bin5

       unit name = msec"
   ::= {er1646v2EthOamMepsQualityMonitorEntry 119557440}

er1646v2EthOamMepsQualityMonitorDelayAlarmDdownsBinsTB6 OBJECT-TYPE
   SYNTAX      Integer32
   UNITS       "msec"
   MAX-ACCESS  read-write
   STATUS      current
   DESCRIPTION
      "Path: ethOam.editConf.meps.qualityMonitor.delayAlarm.delayDownStat.bins.table.bin6

       unit name = msec"
   ::= {er1646v2EthOamMepsQualityMonitorEntry 119557504}

er1646v2EthOamMepsQualityMonitorDelayAlarmDdownsBinsTB7 OBJECT-TYPE
   SYNTAX      Integer32
   UNITS       "msec"
   MAX-ACCESS  read-write
   STATUS      current
   DESCRIPTION
      "Path: ethOam.editConf.meps.qualityMonitor.delayAlarm.delayDownStat.bins.table.bin7

       unit name = msec"
   ::= {er1646v2EthOamMepsQualityMonitorEntry 119557568}

er1646v2EthOamMepsQualityMonitorDelayAlarmDdownsBinsTB8 OBJECT-TYPE
   SYNTAX      Integer32
   UNITS       "msec"
   MAX-ACCESS  read-write
   STATUS      current
   DESCRIPTION
      "Path: ethOam.editConf.meps.qualityMonitor.delayAlarm.delayDownStat.bins.table.bin8

       unit name = msec"
   ::= {er1646v2EthOamMepsQualityMonitorEntry 119557632}

er1646v2EthOamMepsQualityMonitorDelayAlarmDdownsBinsTMx OBJECT-TYPE
   SYNTAX      Integer32
   UNITS       "msec"
   MAX-ACCESS  read-write
   STATUS      current
   DESCRIPTION
      "Path: ethOam.editConf.meps.qualityMonitor.delayAlarm.delayDownStat.bins.table.max

       unit name = msec"
   ::= {er1646v2EthOamMepsQualityMonitorEntry 119557696}

er1646v2EthOamMepsQualityMonitorAlarmMask OBJECT-TYPE
   SYNTAX      Integer32
   MAX-ACCESS  read-write
   STATUS      current
   DESCRIPTION
      "Path: ethOam.editConf.meps.qualityMonitor.alarmMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1646v2EthOamMepsQualityMonitorEntry 251658240}

er1646v2EthOamMepsQualityMonitorEventMask OBJECT-TYPE
   SYNTAX      Integer32
   MAX-ACCESS  read-write
   STATUS      current
   DESCRIPTION
      "Path: ethOam.editConf.meps.qualityMonitor.eventMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1646v2EthOamMepsQualityMonitorEntry 268435456}

er1646v2EthOamMepsQualityMonitorLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: ethOam.editConf.meps.qualityMonitor.logging

       Possibilities:
               disabled   (0)
               3min   (3)
               5min   (5)
               10min   (10)
               15min   (15)
               30min   (30)
               60min   (60)"
   ::= {er1646v2EthOamMepsQualityMonitorEntry 201326592}

er1646v2EthOamMepsQualityMonitorLoggingDepth OBJECT-TYPE
   SYNTAX      INTEGER
               {
               s2 (2),
               s4 (4),
               s8 (8),
               s16 (16),
               s32 (32),
               s128 (128),
               s512 (512),
               s1024 (1024)
               }
   MAX-ACCESS  read-write
   STATUS      current
   DESCRIPTION
      "Path: ethOam.editConf.meps.qualityMonitor.loggingDepth

       Possibilities:
               2   (2)
               4   (4)
               8   (8)
               16   (16)
               32   (32)
               128   (128)
               512   (512)
               1024   (1024)"
   ::= {er1646v2EthOamMepsQualityMonitorEntry 503316480}

er1646v2EthOamMepsSynthLoss OBJECT-TYPE
   SYNTAX      SEQUENCE OF Er1646v2EthOamMepsSynthLossEntry
   MAX-ACCESS  not-accessible
   STATUS      current
   DESCRIPTION
      ""
   ::= {er1646v2EthOamMeps 385875968}

er1646v2EthOamMepsSynthLossEntry OBJECT-TYPE
   SYNTAX      Er1646v2EthOamMepsSynthLossEntry
   MAX-ACCESS  not-accessible
   STATUS      current
   DESCRIPTION
      ""
   INDEX      { er1646v2EthOamMepsSynthLossGlobalIx,
                er1646v2EthOamMepsTableIx,
                er1646v2EthOamMepsSynthLossTableIx }
   ::= {er1646v2EthOamMepsSynthLoss 1}

Er1646v2EthOamMepsSynthLossEntry ::=
   SEQUENCE
      {
      er1646v2EthOamMepsSynthLossActions
         VariableLengthTableActions,
      er1646v2EthOamMepsSynthLossGlobalIx
         GlobalIndex,
      er1646v2EthOamMepsSynthLossTableIx
         TableIndex,
      er1646v2EthOamMepsSynthLossName
         DisplayString,
      er1646v2EthOamMepsSynthLossDestinationMepId
         Integer32,
      er1646v2EthOamMepsSynthLossDestinationMacAddress
         OCTET STRING,
      er1646v2EthOamMepsSynthLossPriority
         Integer32,
      er1646v2EthOamMepsSynthLossState
         INTEGER,
      er1646v2EthOamMepsSynthLossType
         INTEGER,
      er1646v2EthOamMepsSynthLossNbrOfFrames
         Integer32,
      er1646v2EthOamMepsSynthLossPeriod
         INTEGER,
      er1646v2EthOamMepsSynthLossDataTlvSize
         Integer32,
      er1646v2EthOamMepsSynthLossTestInterval
         Integer32
      }

er1646v2EthOamMepsSynthLossActions OBJECT-TYPE
   SYNTAX      VariableLengthTableActions
   MAX-ACCESS  read-write
   STATUS      current
   DESCRIPTION
      "By way of this field, some manipulations
       on this table may be performed."
   ::= {er1646v2EthOamMepsSynthLossEntry 2}

er1646v2EthOamMepsSynthLossGlobalIx OBJECT-TYPE
   SYNTAX      GlobalIndex
   MAX-ACCESS  not-accessible
   STATUS      current
   DESCRIPTION
      "The value of the tlsCntTreeGlobalIndex of the MANAGED OBJECT."
   ::= {er1646v2EthOamMepsSynthLossEntry 10}

er1646v2EthOamMepsSynthLossTableIx OBJECT-TYPE
   SYNTAX      TableIndex
   MAX-ACCESS  not-accessible
   STATUS      current
   DESCRIPTION
      ""
   ::= {er1646v2EthOamMepsSynthLossEntry 11}

er1646v2EthOamMepsSynthLossName OBJECT-TYPE
   SYNTAX      DisplayString
   MAX-ACCESS  read-write
   STATUS      current
   DESCRIPTION
      "Path: ethOam.editConf.meps.synthLoss.name"
   ::= {er1646v2EthOamMepsSynthLossEntry 16777216}

er1646v2EthOamMepsSynthLossDestinationMepId OBJECT-TYPE
   SYNTAX      Integer32
   MAX-ACCESS  read-write
   STATUS      current
   DESCRIPTION
      "Path: ethOam.editConf.meps.synthLoss.destination.mepId"
   ::= {er1646v2EthOamMepsSynthLossEntry 33619968}

er1646v2EthOamMepsSynthLossDestinationMacAddress OBJECT-TYPE
   SYNTAX      OCTET STRING
   MAX-ACCESS  read-write
   STATUS      current
   DESCRIPTION
      "Path: ethOam.editConf.meps.synthLoss.destination.macAddress

       MAC address."
   ::= {er1646v2EthOamMepsSynthLossEntry 33685504}

er1646v2EthOamMepsSynthLossPriority OBJECT-TYPE
   SYNTAX      Integer32
   MAX-ACCESS  read-write
   STATUS      current
   DESCRIPTION
      "Path: ethOam.editConf.meps.synthLoss.priority"
   ::= {er1646v2EthOamMepsSynthLossEntry 50331648}

er1646v2EthOamMepsSynthLossState OBJECT-TYPE
   SYNTAX      INTEGER
               {
               singleEnded (0),
               dualEnded (1),
               dualEndedMC (2)
               }
   MAX-ACCESS  read-write
   STATUS      current
   DESCRIPTION
      "Path: ethOam.editConf.meps.synthLoss.state

       Possibilities:
               singleEnded   (0)
               dualEnded   (1)
               dualEndedMC   (2)"
   ::= {er1646v2EthOamMepsSynthLossEntry 83886080}

er1646v2EthOamMepsSynthLossType OBJECT-TYPE
   SYNTAX      INTEGER
               {
               onDemand (0),
               running (1)
               }
   MAX-ACCESS  read-write
   STATUS      current
   DESCRIPTION
      "Path: ethOam.editConf.meps.synthLoss.type

       Possibilities:
               onDemand   (0)
               running   (1)"
   ::= {er1646v2EthOamMepsSynthLossEntry 167772160}

er1646v2EthOamMepsSynthLossNbrOfFrames OBJECT-TYPE
   SYNTAX      Integer32
   MAX-ACCESS  read-write
   STATUS      current
   DESCRIPTION
      "Path: ethOam.editConf.meps.synthLoss.nbrOfFrames"
   ::= {er1646v2EthOamMepsSynthLossEntry 184549376}

er1646v2EthOamMepsSynthLossPeriod OBJECT-TYPE
   SYNTAX      INTEGER
               {
               s10ms (2),
               s100ms (3),
               s1s (4),
               s10s (5),
               s1min (6),
               s10min (7)
               }
   MAX-ACCESS  read-write
   STATUS      current
   DESCRIPTION
      "Path: ethOam.editConf.meps.synthLoss.period

       Possibilities:
               10ms   (2)
               100ms   (3)
               1s   (4)
               10s   (5)
               1min   (6)
               10min   (7)"
   ::= {er1646v2EthOamMepsSynthLossEntry 201326592}

er1646v2EthOamMepsSynthLossDataTlvSize OBJECT-TYPE
   SYNTAX      Integer32
   MAX-ACCESS  read-write
   STATUS      current
   DESCRIPTION
      "Path: ethOam.editConf.meps.synthLoss.dataTlvSize"
   ::= {er1646v2EthOamMepsSynthLossEntry 218103808}

er1646v2EthOamMepsSynthLossTestInterval OBJECT-TYPE
   SYNTAX      Integer32
   UNITS       "sec"
   MAX-ACCESS  read-write
   STATUS      current
   DESCRIPTION
      "Path: ethOam.editConf.meps.synthLoss.testInterval

       unit name = sec"
   ::= {er1646v2EthOamMepsSynthLossEntry 234881024}


er1646v2EthOamMips OBJECT IDENTIFIER ::= {er1646v2EthOam 11}

er1646v2EthOamMipsSSCTable OBJECT-TYPE
   SYNTAX      SEQUENCE OF Er1646v2EthOamMipsEntry
   MAX-ACCESS  not-accessible
   STATUS      current
   DESCRIPTION
      "table with local MIPs"
   ::= {er1646v2EthOamMips 1}

er1646v2EthOamMipsEntry OBJECT-TYPE
   SYNTAX      Er1646v2EthOamMipsEntry
   MAX-ACCESS  not-accessible
   STATUS      current
   DESCRIPTION
      ""
   INDEX      { er1646v2EthOamMipsGlobalIx,
                er1646v2EthOamMipsTableIx }
   ::= {er1646v2EthOamMipsSSCTable 1}

Er1646v2EthOamMipsEntry ::=
   SEQUENCE
      {
      er1646v2EthOamMipsActions
         VariableLengthTableActions,
      er1646v2EthOamMipsGlobalIx
         GlobalIndex,
      er1646v2EthOamMipsTableIx
         TableIndex,
      er1646v2EthOamMipsName
         DisplayString,
      er1646v2EthOamMipsAdminStatus
         INTEGER,
      er1646v2EthOamMipsMode
         INTEGER,
      er1646v2EthOamMipsInterface
         DisplayString,
      er1646v2EthOamMipsVid
         INTEGER,
      er1646v2EthOamMipsTpid
         INTEGER,
      er1646v2EthOamMipsPrioMapQueue
         INTEGER,
      er1646v2EthOamMipsPrioMapDropLevel
         INTEGER,
      er1646v2EthOamMipsMegLevel
         Integer32
      }

er1646v2EthOamMipsActions OBJECT-TYPE
   SYNTAX      VariableLengthTableActions
   MAX-ACCESS  read-write
   STATUS      current
   DESCRIPTION
      "By way of this field, some manipulations
       on this table may be performed."
   ::= {er1646v2EthOamMipsEntry 2}

er1646v2EthOamMipsGlobalIx OBJECT-TYPE
   SYNTAX      GlobalIndex
   MAX-ACCESS  not-accessible
   STATUS      current
   DESCRIPTION
      "The value of the tlsCntTreeGlobalIndex of the MANAGED OBJECT."
   ::= {er1646v2EthOamMipsEntry 10}

er1646v2EthOamMipsTableIx OBJECT-TYPE
   SYNTAX      TableIndex
   MAX-ACCESS  not-accessible
   STATUS      current
   DESCRIPTION
      ""
   ::= {er1646v2EthOamMipsEntry 11}

er1646v2EthOamMipsName OBJECT-TYPE
   SYNTAX      DisplayString
   MAX-ACCESS  read-write
   STATUS      current
   DESCRIPTION
      "Path: ethOam.editConf.mips.name"
   ::= {er1646v2EthOamMipsEntry 16777216}

er1646v2EthOamMipsAdminStatus OBJECT-TYPE
   SYNTAX      INTEGER
               {
               up (1),
               down (2)
               }
   MAX-ACCESS  read-write
   STATUS      current
   DESCRIPTION
      "Path: ethOam.editConf.mips.adminStatus

       Possibilities:
               up   (1)
               down   (2)"
   ::= {er1646v2EthOamMipsEntry 33554432}

er1646v2EthOamMipsMode OBJECT-TYPE
   SYNTAX      INTEGER
               {
               ym1731 (1),
               s802m1ag (2)
               }
   MAX-ACCESS  read-write
   STATUS      current
   DESCRIPTION
      "Path: ethOam.editConf.mips.mode

       Possibilities:
               y-1731   (1)
               802-1ag   (2)"
   ::= {er1646v2EthOamMipsEntry 50331648}

er1646v2EthOamMipsInterface OBJECT-TYPE
   SYNTAX      DisplayString
   MAX-ACCESS  read-write
   STATUS      current
   DESCRIPTION
      "Path: ethOam.editConf.mips.interface"
   ::= {er1646v2EthOamMipsEntry 67108864}

er1646v2EthOamMipsVid OBJECT-TYPE
   SYNTAX      INTEGER
               {
               untagged (0)
               }
   MAX-ACCESS  read-write
   STATUS      current
   DESCRIPTION
      "Path: ethOam.editConf.mips.vid

       Possibilities:
               untagged   (0)"
   ::= {er1646v2EthOamMipsEntry 83886080}

er1646v2EthOamMipsTpid OBJECT-TYPE
   SYNTAX      INTEGER
               {
               dot1Q (33024),
               dot1ad (34984)
               }
   MAX-ACCESS  read-write
   STATUS      current
   DESCRIPTION
      "Path: ethOam.editConf.mips.tpid

       Possibilities:
               dot1Q   (33024)
               dot1ad   (34984)"
   ::= {er1646v2EthOamMipsEntry 150994944}

er1646v2EthOamMipsPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.mips.prioMap.queue

       Possibilities:
               queue1   (0)
               queue2   (1)
               queue3   (2)
               queue4   (3)
               queue5   (4)
               lowDelayQueue   (5)
               lowDelay2Queue   (6)
               systemQueue   (7)"
   ::= {er1646v2EthOamMipsEntry 117506048}

er1646v2EthOamMipsPrioMapDropLevel OBJECT-TYPE
   SYNTAX      INTEGER
               {
               dropOnQueue (0)
               }
   MAX-ACCESS  read-write
   STATUS      current
   DESCRIPTION
      "Path: ethOam.editConf.mips.prioMap.dropLevel

       Possibilities:
               dropOnQueue   (0)"
   ::= {er1646v2EthOamMipsEntry 117571584}

er1646v2EthOamMipsMegLevel OBJECT-TYPE
   SYNTAX      Integer32
   MAX-ACCESS  read-write
   STATUS      current
   DESCRIPTION
      "Path: ethOam.editConf.mips.megLevel"
   ::= {er1646v2EthOamMipsEntry 100663296}

er1646v2EthOamMipsReplyPrioMap OBJECT-TYPE
   SYNTAX      SEQUENCE OF Er1646v2EthOamMipsReplyPrioMapEntry
   MAX-ACCESS  not-accessible
   STATUS      current
   DESCRIPTION
      ""
   ::= {er1646v2EthOamMips 134217728}

er1646v2EthOamMipsReplyPrioMapEntry OBJECT-TYPE
   SYNTAX      Er1646v2EthOamMipsReplyPrioMapEntry
   MAX-ACCESS  not-accessible
   STATUS      current
   DESCRIPTION
      ""
   INDEX      { er1646v2EthOamMipsReplyPrioMapGlobalIx,
                er1646v2EthOamMipsTableIx,
                er1646v2EthOamMipsReplyPrioMapTableIx }
   ::= {er1646v2EthOamMipsReplyPrioMap 1}

Er1646v2EthOamMipsReplyPrioMapEntry ::=
   SEQUENCE
      {
      er1646v2EthOamMipsReplyPrioMapActions
         VariableLengthTableActions,
      er1646v2EthOamMipsReplyPrioMapGlobalIx
         GlobalIndex,
      er1646v2EthOamMipsReplyPrioMapTableIx
         TableIndex,
      er1646v2EthOamMipsReplyPrioMapRxPriority
         Integer32,
      er1646v2EthOamMipsReplyPrioMapTxPriority
         INTEGER,
      er1646v2EthOamMipsReplyPrioMapQueue
         INTEGER,
      er1646v2EthOamMipsReplyPrioMapDropLevel
         INTEGER
      }

er1646v2EthOamMipsReplyPrioMapActions OBJECT-TYPE
   SYNTAX      VariableLengthTableActions
   MAX-ACCESS  read-write
   STATUS      current
   DESCRIPTION
      "By way of this field, some manipulations
       on this table may be performed."
   ::= {er1646v2EthOamMipsReplyPrioMapEntry 2}

er1646v2EthOamMipsReplyPrioMapGlobalIx OBJECT-TYPE
   SYNTAX      GlobalIndex
   MAX-ACCESS  not-accessible
   STATUS      current
   DESCRIPTION
      "The value of the tlsCntTreeGlobalIndex of the MANAGED OBJECT."
   ::= {er1646v2EthOamMipsReplyPrioMapEntry 10}

er1646v2EthOamMipsReplyPrioMapTableIx OBJECT-TYPE
   SYNTAX      TableIndex
   MAX-ACCESS  not-accessible
   STATUS      current
   DESCRIPTION
      ""
   ::= {er1646v2EthOamMipsReplyPrioMapEntry 11}

er1646v2EthOamMipsReplyPrioMapRxPriority OBJECT-TYPE
   SYNTAX      Integer32
   MAX-ACCESS  read-write
   STATUS      current
   DESCRIPTION
      "Path: ethOam.editConf.mips.replyPrioMap.rxPriority"
   ::= {er1646v2EthOamMipsReplyPrioMapEntry 16777216}

er1646v2EthOamMipsReplyPrioMapTxPriority OBJECT-TYPE
   SYNTAX      INTEGER
               {
               keepRxPrio (8)
               }
   MAX-ACCESS  read-write
   STATUS      current
   DESCRIPTION
      "Path: ethOam.editConf.mips.replyPrioMap.txPriority

       Possibilities:
               keepRxPrio   (8)"
   ::= {er1646v2EthOamMipsReplyPrioMapEntry 33554432}

er1646v2EthOamMipsReplyPrioMapQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethOam.editConf.mips.replyPrioMap.queue

       Possibilities:
               queue1   (0)
               queue2   (1)
               queue3   (2)
               queue4   (3)
               queue5   (4)
               lowDelayQueue   (5)
               lowDelay2Queue   (6)
               systemQueue   (7)"
   ::= {er1646v2EthOamMipsReplyPrioMapEntry 50331648}

er1646v2EthOamMipsReplyPrioMapDropLevel OBJECT-TYPE
   SYNTAX      INTEGER
               {
               dropOnQueue (0)
               }
   MAX-ACCESS  read-write
   STATUS      current
   DESCRIPTION
      "Path: ethOam.editConf.mips.replyPrioMap.dropLevel

       Possibilities:
               dropOnQueue   (0)"
   ::= {er1646v2EthOamMipsReplyPrioMapEntry 67108864}


er1646v2EthOamMask OBJECT IDENTIFIER ::= {er1646v2EthOam 223}

er1646v2EthOamMaskTable OBJECT-TYPE
   SYNTAX      SEQUENCE OF Er1646v2EthOamMaskEntry
   MAX-ACCESS  not-accessible
   STATUS      current
   DESCRIPTION
      "ETH OAM AlarmMask"
   ::= {er1646v2EthOamMask 1}

er1646v2EthOamMaskEntry OBJECT-TYPE
   SYNTAX      Er1646v2EthOamMaskEntry
   MAX-ACCESS  not-accessible
   STATUS      current
   DESCRIPTION
      ""
   INDEX      { er1646v2EthOamMaskGlobalIx }
   ::= {er1646v2EthOamMaskTable 1}

Er1646v2EthOamMaskEntry ::=
   SEQUENCE
      {
      er1646v2EthOamMaskGlobalIx
         GlobalIndex,
      er1646v2EthOamMaskValue
         Integer32
      }

er1646v2EthOamMaskGlobalIx OBJECT-TYPE
   SYNTAX      GlobalIndex
   MAX-ACCESS  not-accessible
   STATUS      current
   DESCRIPTION
      "The value of the tlsCntTreeGlobalIndex of the MANAGED OBJECT."
   ::= {er1646v2EthOamMaskEntry 10}

er1646v2EthOamMaskValue OBJECT-TYPE
   SYNTAX      Integer32
   MAX-ACCESS  read-write
   STATUS      current
   DESCRIPTION
      "Path: ethOam.editConf.alarmMask

       Bit meanings:
               bit 1 = delay,
               bit 2 = jitter,
               bit 3 = lossOfContinuity,
               bit 4 = mismerge,
               bit 5 = unexpectedMep,
               bit 6 = unexpectedMegLevel,
               bit 7 = unexpectedPeriod,
               bit 8 = rdi,
               bit 9 = ais,
               bit 10 = macStatus,
               bit 11 = qualityMonitor"
   ::= {er1646v2EthOamMaskEntry 2147483648}


er1646v2EthOamLevel OBJECT IDENTIFIER ::= {er1646v2EthOam 61}

er1646v2EthOamLevelSSCTable OBJECT-TYPE
   SYNTAX      SEQUENCE OF Er1646v2EthOamLevelEntry
   MAX-ACCESS  not-accessible
   STATUS      current
   DESCRIPTION
      "ETH OAM AlarmLevel"
   ::= {er1646v2EthOamLevel 1}

er1646v2EthOamLevelEntry OBJECT-TYPE
   SYNTAX      Er1646v2EthOamLevelEntry
   MAX-ACCESS  not-accessible
   STATUS      current
   DESCRIPTION
      ""
   INDEX      { er1646v2EthOamLevelGlobalIx }
   ::= {er1646v2EthOamLevelSSCTable 1}

Er1646v2EthOamLevelEntry ::=
   SEQUENCE
      {
      er1646v2EthOamLevelGlobalIx
         GlobalIndex,
      er1646v2EthOamLevelDelay
         Integer32,
      er1646v2EthOamLevelJitter
         Integer32,
      er1646v2EthOamLevelLossOfContinuity
         Integer32,
      er1646v2EthOamLevelMismerge
         Integer32,
      er1646v2EthOamLevelUnexpectedMep
         Integer32,
      er1646v2EthOamLevelUnexpectedMegLevel
         Integer32,
      er1646v2EthOamLevelUnexpectedPeriod
         Integer32,
      er1646v2EthOamLevelRdi
         Integer32,
      er1646v2EthOamLevelAis
         Integer32,
      er1646v2EthOamLevelMacStatus
         Integer32,
      er1646v2EthOamLevelQualityMonitor
         Integer32
      }

er1646v2EthOamLevelGlobalIx OBJECT-TYPE
   SYNTAX      GlobalIndex
   MAX-ACCESS  not-accessible
   STATUS      current
   DESCRIPTION
      "The value of the tlsCntTreeGlobalIndex of the MANAGED OBJECT."
   ::= {er1646v2EthOamLevelEntry 10}

er1646v2EthOamLevelDelay OBJECT-TYPE
   SYNTAX      Integer32
   MAX-ACCESS  read-write
   STATUS      current
   DESCRIPTION
      "Path: ethOam.editConf.alarmLevel.delay"
   ::= {er1646v2EthOamLevelEntry 33554432}

er1646v2EthOamLevelJitter OBJECT-TYPE
   SYNTAX      Integer32
   MAX-ACCESS  read-write
   STATUS      current
   DESCRIPTION
      "Path: ethOam.editConf.alarmLevel.jitter"
   ::= {er1646v2EthOamLevelEntry 50331648}

er1646v2EthOamLevelLossOfContinuity OBJECT-TYPE
   SYNTAX      Integer32
   MAX-ACCESS  read-write
   STATUS      current
   DESCRIPTION
      "Path: ethOam.editConf.alarmLevel.lossOfContinuity"
   ::= {er1646v2EthOamLevelEntry 67108864}

er1646v2EthOamLevelMismerge OBJECT-TYPE
   SYNTAX      Integer32
   MAX-ACCESS  read-write
   STATUS      current
   DESCRIPTION
      "Path: ethOam.editConf.alarmLevel.mismerge"
   ::= {er1646v2EthOamLevelEntry 83886080}

er1646v2EthOamLevelUnexpectedMep OBJECT-TYPE
   SYNTAX      Integer32
   MAX-ACCESS  read-write
   STATUS      current
   DESCRIPTION
      "Path: ethOam.editConf.alarmLevel.unexpectedMep"
   ::= {er1646v2EthOamLevelEntry 100663296}

er1646v2EthOamLevelUnexpectedMegLevel OBJECT-TYPE
   SYNTAX      Integer32
   MAX-ACCESS  read-write
   STATUS      current
   DESCRIPTION
      "Path: ethOam.editConf.alarmLevel.unexpectedMegLevel"
   ::= {er1646v2EthOamLevelEntry 117440512}

er1646v2EthOamLevelUnexpectedPeriod OBJECT-TYPE
   SYNTAX      Integer32
   MAX-ACCESS  read-write
   STATUS      current
   DESCRIPTION
      "Path: ethOam.editConf.alarmLevel.unexpectedPeriod"
   ::= {er1646v2EthOamLevelEntry 134217728}

er1646v2EthOamLevelRdi OBJECT-TYPE
   SYNTAX      Integer32
   MAX-ACCESS  read-write
   STATUS      current
   DESCRIPTION
      "Path: ethOam.editConf.alarmLevel.rdi"
   ::= {er1646v2EthOamLevelEntry 150994944}

er1646v2EthOamLevelAis OBJECT-TYPE
   SYNTAX      Integer32
   MAX-ACCESS  read-write
   STATUS      current
   DESCRIPTION
      "Path: ethOam.editConf.alarmLevel.ais"
   ::= {er1646v2EthOamLevelEntry 167772160}

er1646v2EthOamLevelMacStatus OBJECT-TYPE
   SYNTAX      Integer32
   MAX-ACCESS  read-write
   STATUS      current
   DESCRIPTION
      "Path: ethOam.editConf.alarmLevel.macStatus"
   ::= {er1646v2EthOamLevelEntry 184549376}

er1646v2EthOamLevelQualityMonitor OBJECT-TYPE
   SYNTAX      Integer32
   MAX-ACCESS  read-write
   STATUS      current
   DESCRIPTION
      "Path: ethOam.editConf.alarmLevel.qualityMonitor"
   ::= {er1646v2EthOamLevelEntry 201326592}


er1646v2EthOamStartDelay OBJECT IDENTIFIER ::= {er1646v2EthOam 38}

er1646v2EthOamStartDelayTable OBJECT-TYPE
   SYNTAX      SEQUENCE OF Er1646v2EthOamStartDelayEntry
   MAX-ACCESS  not-accessible
   STATUS      current
   DESCRIPTION
      "the amount of time the OAM module waits before being started after a reboot of the device"
   ::= {er1646v2EthOamStartDelay 1}

er1646v2EthOamStartDelayEntry OBJECT-TYPE
   SYNTAX      Er1646v2EthOamStartDelayEntry
   MAX-ACCESS  not-accessible
   STATUS      current
   DESCRIPTION
      ""
   INDEX      { er1646v2EthOamStartDelayGlobalIx }
   ::= {er1646v2EthOamStartDelayTable 1}

Er1646v2EthOamStartDelayEntry ::=
   SEQUENCE
      {
      er1646v2EthOamStartDelayGlobalIx
         GlobalIndex,
      er1646v2EthOamStartDelayValue
         INTEGER
      }

er1646v2EthOamStartDelayGlobalIx OBJECT-TYPE
   SYNTAX      GlobalIndex
   MAX-ACCESS  not-accessible
   STATUS      current
   DESCRIPTION
      "The value of the tlsCntTreeGlobalIndex of the MANAGED OBJECT."
   ::= {er1646v2EthOamStartDelayEntry 10}

er1646v2EthOamStartDelayValue OBJECT-TYPE
   SYNTAX      INTEGER
               {
               disabled (0)
               }
   MAX-ACCESS  read-write
   STATUS      current
   DESCRIPTION
      "Path: ethOam.editConf.startDelay

       Possibilities:
               disabled   (0)"
   ::= {er1646v2EthOamStartDelayEntry 2147483648}


er1646v2EthOamLocDelay OBJECT IDENTIFIER ::= {er1646v2EthOam 36}

er1646v2EthOamLocDelayTable OBJECT-TYPE
   SYNTAX      SEQUENCE OF Er1646v2EthOamLocDelayEntry
   MAX-ACCESS  not-accessible
   STATUS      current
   DESCRIPTION
      "the amount of time a device waits for remote MEPs before the crosscheck operation is started"
   ::= {er1646v2EthOamLocDelay 1}

er1646v2EthOamLocDelayEntry OBJECT-TYPE
   SYNTAX      Er1646v2EthOamLocDelayEntry
   MAX-ACCESS  not-accessible
   STATUS      current
   DESCRIPTION
      ""
   INDEX      { er1646v2EthOamLocDelayGlobalIx }
   ::= {er1646v2EthOamLocDelayTable 1}

Er1646v2EthOamLocDelayEntry ::=
   SEQUENCE
      {
      er1646v2EthOamLocDelayGlobalIx
         GlobalIndex,
      er1646v2EthOamLocDelayValue
         INTEGER
      }

er1646v2EthOamLocDelayGlobalIx OBJECT-TYPE
   SYNTAX      GlobalIndex
   MAX-ACCESS  not-accessible
   STATUS      current
   DESCRIPTION
      "The value of the tlsCntTreeGlobalIndex of the MANAGED OBJECT."
   ::= {er1646v2EthOamLocDelayEntry 10}

er1646v2EthOamLocDelayValue OBJECT-TYPE
   SYNTAX      INTEGER
               {
               disabled (0)
               }
   MAX-ACCESS  read-write
   STATUS      current
   DESCRIPTION
      "Path: ethOam.editConf.locDelay

       Possibilities:
               disabled   (0)"
   ::= {er1646v2EthOamLocDelayEntry 2147483648}


er1646v2EthOamMode OBJECT IDENTIFIER ::= {er1646v2EthOam 12}

er1646v2EthOamModeTable OBJECT-TYPE
   SYNTAX      SEQUENCE OF Er1646v2EthOamModeEntry
   MAX-ACCESS  not-accessible
   STATUS      current
   DESCRIPTION
      "mode of the ETH OAM object"
   ::= {er1646v2EthOamMode 1}

er1646v2EthOamModeEntry OBJECT-TYPE
   SYNTAX      Er1646v2EthOamModeEntry
   MAX-ACCESS  not-accessible
   STATUS      current
   DESCRIPTION
      ""
   INDEX      { er1646v2EthOamModeGlobalIx }
   ::= {er1646v2EthOamModeTable 1}

Er1646v2EthOamModeEntry ::=
   SEQUENCE
      {
      er1646v2EthOamModeGlobalIx
         GlobalIndex,
      er1646v2EthOamModeValue
         INTEGER
      }

er1646v2EthOamModeGlobalIx OBJECT-TYPE
   SYNTAX      GlobalIndex
   MAX-ACCESS  not-accessible
   STATUS      current
   DESCRIPTION
      "The value of the tlsCntTreeGlobalIndex of the MANAGED OBJECT."
   ::= {er1646v2EthOamModeEntry 10}

er1646v2EthOamModeValue OBJECT-TYPE
   SYNTAX      INTEGER
               {
               disabled (0),
               enabled (1)
               }
   MAX-ACCESS  read-write
   STATUS      current
   DESCRIPTION
      "Path: ethOam.editConf.mode

       Possibilities:
               disabled   (0)
               enabled   (1)"
   ::= {er1646v2EthOamModeEntry 2147483648}



sr1646v2EthOam OBJECT IDENTIFIER ::= {r1646v2EthOam 14}


sr1646v2EthOamMeps OBJECT IDENTIFIER ::= {sr1646v2EthOam 15}

sr1646v2EthOamMepsSSCTable OBJECT-TYPE
   SYNTAX      SEQUENCE OF Sr1646v2EthOamMepsEntry
   MAX-ACCESS  not-accessible
   STATUS      current
   DESCRIPTION
      "ETH OAM Mep status"
   ::= {sr1646v2EthOamMeps 1}

sr1646v2EthOamMepsEntry OBJECT-TYPE
   SYNTAX      Sr1646v2EthOamMepsEntry
   MAX-ACCESS  not-accessible
   STATUS      current
   DESCRIPTION
      ""
   INDEX      { sr1646v2EthOamMepsGlobalIx,
                sr1646v2EthOamMepsTableIx }
   ::= {sr1646v2EthOamMepsSSCTable 1}

Sr1646v2EthOamMepsEntry ::=
   SEQUENCE
      {
      sr1646v2EthOamMepsGlobalIx
         GlobalIndex,
      sr1646v2EthOamMepsTableIx
         TableIndex,
      sr1646v2EthOamMepsMepName
         DisplayString,
      sr1646v2EthOamMepsMacAddress
         OCTET STRING,
      sr1646v2EthOamMepsMegLevel
         Integer32,
      sr1646v2EthOamMepsMegIdMaintDomainName
         DisplayString,
      sr1646v2EthOamMepsMegIdShortMaName
         DisplayString,
      sr1646v2EthOamMepsMepId
         Integer32,
      sr1646v2EthOamMepsCc
         INTEGER,
      sr1646v2EthOamMepsEfd
         INTEGER,
      sr1646v2EthOamMepsTxAis
         INTEGER,
      sr1646v2EthOamMepsTxRdi
         INTEGER,
      sr1646v2EthOamMepsAlarm
         Integer32
      }

sr1646v2EthOamMepsGlobalIx OBJECT-TYPE
   SYNTAX      GlobalIndex
   MAX-ACCESS  not-accessible
   STATUS      current
   DESCRIPTION
      "The value of the tlsCntTreeGlobalIndex of the MANAGED OBJECT."
   ::= {sr1646v2EthOamMepsEntry 10}

sr1646v2EthOamMepsTableIx OBJECT-TYPE
   SYNTAX      TableIndex
   MAX-ACCESS  not-accessible
   STATUS      current
   DESCRIPTION
      ""
   ::= {sr1646v2EthOamMepsEntry 11}

sr1646v2EthOamMepsMepName OBJECT-TYPE
   SYNTAX      DisplayString
   MAX-ACCESS  read-only
   STATUS      current
   DESCRIPTION
      "Path: ethOam.status.meps.mepName"
   ::= {sr1646v2EthOamMepsEntry 16777216}

sr1646v2EthOamMepsMacAddress OBJECT-TYPE
   SYNTAX      OCTET STRING
   MAX-ACCESS  read-only
   STATUS      current
   DESCRIPTION
      "Path: ethOam.status.meps.macAddress

       MAC address."
   ::= {sr1646v2EthOamMepsEntry 33554432}

sr1646v2EthOamMepsMegLevel OBJECT-TYPE
   SYNTAX      Integer32
   MAX-ACCESS  read-only
   STATUS      current
   DESCRIPTION
      "Path: ethOam.status.meps.megLevel"
   ::= {sr1646v2EthOamMepsEntry 50331648}

sr1646v2EthOamMepsMegIdMaintDomainName OBJECT-TYPE
   SYNTAX      DisplayString
   MAX-ACCESS  read-only
   STATUS      current
   DESCRIPTION
      "Path: ethOam.status.meps.megId.maintDomainName"
   ::= {sr1646v2EthOamMepsEntry 67174400}

sr1646v2EthOamMepsMegIdShortMaName OBJECT-TYPE
   SYNTAX      DisplayString
   MAX-ACCESS  read-only
   STATUS      current
   DESCRIPTION
      "Path: ethOam.status.meps.megId.shortMaName"
   ::= {sr1646v2EthOamMepsEntry 67239936}

sr1646v2EthOamMepsMepId OBJECT-TYPE
   SYNTAX      Integer32
   MAX-ACCESS  read-only
   STATUS      current
   DESCRIPTION
      "Path: ethOam.status.meps.mepId"
   ::= {sr1646v2EthOamMepsEntry 83886080}

sr1646v2EthOamMepsCc OBJECT-TYPE
   SYNTAX      INTEGER
               {
               inactive (0),
               active (1),
               disabled (2)
               }
   MAX-ACCESS  read-only
   STATUS      current
   DESCRIPTION
      "Path: ethOam.status.meps.cc

       Possibilities:
               inactive   (0)
               active   (1)
               disabled   (2)"
   ::= {sr1646v2EthOamMepsEntry 117440512}

sr1646v2EthOamMepsEfd OBJECT-TYPE
   SYNTAX      INTEGER
               {
               disabled (0),
               idle (1),
               triggered (2),
               triggeredLfp (3)
               }
   MAX-ACCESS  read-only
   STATUS      current
   DESCRIPTION
      "Path: ethOam.status.meps.efd

       Possibilities:
               disabled   (0)
               idle   (1)
               triggered   (2)
               triggeredLfp   (3)"
   ::= {sr1646v2EthOamMepsEntry 134217728}

sr1646v2EthOamMepsTxAis OBJECT-TYPE
   SYNTAX      INTEGER
               {
               inactive (0),
               active (1),
               disabled (2)
               }
   MAX-ACCESS  read-only
   STATUS      current
   DESCRIPTION
      "Path: ethOam.status.meps.txAis

       Possibilities:
               inactive   (0)
               active   (1)
               disabled   (2)"
   ::= {sr1646v2EthOamMepsEntry 167772160}

sr1646v2EthOamMepsTxRdi OBJECT-TYPE
   SYNTAX      INTEGER
               {
               no (0),
               yes (1)
               }
   MAX-ACCESS  read-only
   STATUS      current
   DESCRIPTION
      "Path: ethOam.status.meps.txRdi

       Possibilities:
               no   (0)
               yes   (1)"
   ::= {sr1646v2EthOamMepsEntry 184549376}

sr1646v2EthOamMepsAlarm OBJECT-TYPE
   SYNTAX      Integer32
   MAX-ACCESS  read-only
   STATUS      current
   DESCRIPTION
      "Path: ethOam.status.meps.alarm

       Bit meanings:
               bit 4 = mismerge,
               bit 5 = unexpectedMep,
               bit 6 = unexpectedMegLevel,
               bit 7 = unexpectedPeriod,
               bit 8 = rdi,
               bit 9 = ais,
               bit 10 = macStatus"
   ::= {sr1646v2EthOamMepsEntry 100663296}


sr1646v2EthOamDiscoveredMeps OBJECT IDENTIFIER ::= {sr1646v2EthOam 16}

sr1646v2EthOamDiscoveredMepsSSCTable OBJECT-TYPE
   SYNTAX      SEQUENCE OF Sr1646v2EthOamDiscoveredMepsEntry
   MAX-ACCESS  not-accessible
   STATUS      current
   DESCRIPTION
      "list of discovered MEPs"
   ::= {sr1646v2EthOamDiscoveredMeps 1}

sr1646v2EthOamDiscoveredMepsEntry OBJECT-TYPE
   SYNTAX      Sr1646v2EthOamDiscoveredMepsEntry
   MAX-ACCESS  not-accessible
   STATUS      current
   DESCRIPTION
      ""
   INDEX      { sr1646v2EthOamDiscoveredMepsGlobalIx,
                sr1646v2EthOamDiscoveredMepsTableIx }
   ::= {sr1646v2EthOamDiscoveredMepsSSCTable 1}

Sr1646v2EthOamDiscoveredMepsEntry ::=
   SEQUENCE
      {
      sr1646v2EthOamDiscoveredMepsGlobalIx
         GlobalIndex,
      sr1646v2EthOamDiscoveredMepsTableIx
         TableIndex,
      sr1646v2EthOamDiscoveredMepsInterface
         DisplayString,
      sr1646v2EthOamDiscoveredMepsVid
         INTEGER,
      sr1646v2EthOamDiscoveredMepsTpid
         INTEGER,
      sr1646v2EthOamDiscoveredMepsPriority
         Integer32,
      sr1646v2EthOamDiscoveredMepsPeriod
         INTEGER,
      sr1646v2EthOamDiscoveredMepsMegLevel
         Integer32,
      sr1646v2EthOamDiscoveredMepsMegIdMaintDomainName
         DisplayString,
      sr1646v2EthOamDiscoveredMepsMegIdShortMaName
         DisplayString,
      sr1646v2EthOamDiscoveredMepsMepId
         Integer32,
      sr1646v2EthOamDiscoveredMepsMacAddress
         OCTET STRING
      }

sr1646v2EthOamDiscoveredMepsGlobalIx OBJECT-TYPE
   SYNTAX      GlobalIndex
   MAX-ACCESS  not-accessible
   STATUS      current
   DESCRIPTION
      "The value of the tlsCntTreeGlobalIndex of the MANAGED OBJECT."
   ::= {sr1646v2EthOamDiscoveredMepsEntry 10}

sr1646v2EthOamDiscoveredMepsTableIx OBJECT-TYPE
   SYNTAX      TableIndex
   MAX-ACCESS  not-accessible
   STATUS      current
   DESCRIPTION
      ""
   ::= {sr1646v2EthOamDiscoveredMepsEntry 11}

sr1646v2EthOamDiscoveredMepsInterface OBJECT-TYPE
   SYNTAX      DisplayString
   MAX-ACCESS  read-only
   STATUS      current
   DESCRIPTION
      "Path: ethOam.status.discoveredMeps.interface"
   ::= {sr1646v2EthOamDiscoveredMepsEntry 16777216}

sr1646v2EthOamDiscoveredMepsVid OBJECT-TYPE
   SYNTAX      INTEGER
               {
               untagged (0)
               }
   MAX-ACCESS  read-only
   STATUS      current
   DESCRIPTION
      "Path: ethOam.status.discoveredMeps.vid

       Possibilities:
               untagged   (0)"
   ::= {sr1646v2EthOamDiscoveredMepsEntry 33554432}

sr1646v2EthOamDiscoveredMepsTpid OBJECT-TYPE
   SYNTAX      INTEGER
               {
               slOPTg (0),
               dot1Q (33024),
               dot1ad (34984),
               s0x9100 (37120),
               s0x9200 (37376),
               s0x9300 (37632)
               }
   MAX-ACCESS  read-only
   STATUS      current
   DESCRIPTION
      "Path: ethOam.status.discoveredMeps.tpid

       Possibilities:
               <OPT>   (0)
               dot1Q   (33024)
               dot1ad   (34984)
               0x9100   (37120)
               0x9200   (37376)
               0x9300   (37632)"
   ::= {sr1646v2EthOamDiscoveredMepsEntry 150994944}

sr1646v2EthOamDiscoveredMepsPriority OBJECT-TYPE
   SYNTAX      Integer32
   MAX-ACCESS  read-only
   STATUS      current
   DESCRIPTION
      "Path: ethOam.status.discoveredMeps.priority"
   ::= {sr1646v2EthOamDiscoveredMepsEntry 50331648}

sr1646v2EthOamDiscoveredMepsPeriod OBJECT-TYPE
   SYNTAX      INTEGER
               {
               unknown (0),
               s3d33ms (1),
               s10ms (2),
               s100ms (3),
               s1s (4),
               s10s (5),
               s1min (6),
               s10min (7)
               }
   MAX-ACCESS  read-only
   STATUS      current
   DESCRIPTION
      "Path: ethOam.status.discoveredMeps.period

       Possibilities:
               unknown   (0)
               3.33ms   (1)
               10ms   (2)
               100ms   (3)
               1s   (4)
               10s   (5)
               1min   (6)
               10min   (7)"
   ::= {sr1646v2EthOamDiscoveredMepsEntry 67108864}

sr1646v2EthOamDiscoveredMepsMegLevel OBJECT-TYPE
   SYNTAX      Integer32
   MAX-ACCESS  read-only
   STATUS      current
   DESCRIPTION
      "Path: ethOam.status.discoveredMeps.megLevel"
   ::= {sr1646v2EthOamDiscoveredMepsEntry 83886080}

sr1646v2EthOamDiscoveredMepsMegIdMaintDomainName OBJECT-TYPE
   SYNTAX      DisplayString
   MAX-ACCESS  read-only
   STATUS      current
   DESCRIPTION
      "Path: ethOam.status.discoveredMeps.megId.maintDomainName"
   ::= {sr1646v2EthOamDiscoveredMepsEntry 100728832}

sr1646v2EthOamDiscoveredMepsMegIdShortMaName OBJECT-TYPE
   SYNTAX      DisplayString
   MAX-ACCESS  read-only
   STATUS      current
   DESCRIPTION
      "Path: ethOam.status.discoveredMeps.megId.shortMaName"
   ::= {sr1646v2EthOamDiscoveredMepsEntry 100794368}

sr1646v2EthOamDiscoveredMepsMepId OBJECT-TYPE
   SYNTAX      Integer32
   MAX-ACCESS  read-only
   STATUS      current
   DESCRIPTION
      "Path: ethOam.status.discoveredMeps.mepId"
   ::= {sr1646v2EthOamDiscoveredMepsEntry 117440512}

sr1646v2EthOamDiscoveredMepsMacAddress OBJECT-TYPE
   SYNTAX      OCTET STRING
   MAX-ACCESS  read-only
   STATUS      current
   DESCRIPTION
      "Path: ethOam.status.discoveredMeps.macAddress

       MAC address."
   ::= {sr1646v2EthOamDiscoveredMepsEntry 134217728}


sr1646v2EthOamManagedMeps OBJECT IDENTIFIER ::= {sr1646v2EthOam 17}

sr1646v2EthOamManagedMepsSSCTable OBJECT-TYPE
   SYNTAX      SEQUENCE OF Sr1646v2EthOamManagedMepsEntry
   MAX-ACCESS  not-accessible
   STATUS      current
   DESCRIPTION
      "list of managed MEPs"
   ::= {sr1646v2EthOamManagedMeps 1}

sr1646v2EthOamManagedMepsEntry OBJECT-TYPE
   SYNTAX      Sr1646v2EthOamManagedMepsEntry
   MAX-ACCESS  not-accessible
   STATUS      current
   DESCRIPTION
      ""
   INDEX      { sr1646v2EthOamManagedMepsGlobalIx,
                sr1646v2EthOamManagedMepsTableIx }
   ::= {sr1646v2EthOamManagedMepsSSCTable 1}

Sr1646v2EthOamManagedMepsEntry ::=
   SEQUENCE
      {
      sr1646v2EthOamManagedMepsGlobalIx
         GlobalIndex,
      sr1646v2EthOamManagedMepsTableIx
         TableIndex,
      sr1646v2EthOamManagedMepsManagedMepName
         DisplayString,
      sr1646v2EthOamManagedMepsInterface
         DisplayString,
      sr1646v2EthOamManagedMepsVid
         INTEGER,
      sr1646v2EthOamManagedMepsTpid
         INTEGER,
      sr1646v2EthOamManagedMepsPriority
         Integer32,
      sr1646v2EthOamManagedMepsPeriod
         INTEGER,
      sr1646v2EthOamManagedMepsMegLevel
         Integer32,
      sr1646v2EthOamManagedMepsMegIdMaintDomainName
         DisplayString,
      sr1646v2EthOamManagedMepsMegIdShortMaName
         DisplayString,
      sr1646v2EthOamManagedMepsMepId
         Integer32,
      sr1646v2EthOamManagedMepsMacAddress
         OCTET STRING,
      sr1646v2EthOamManagedMepsIntfStatus
         INTEGER,
      sr1646v2EthOamManagedMepsPortStatus
         INTEGER,
      sr1646v2EthOamManagedMepsAlarm
         Integer32
      }

sr1646v2EthOamManagedMepsGlobalIx OBJECT-TYPE
   SYNTAX      GlobalIndex
   MAX-ACCESS  not-accessible
   STATUS      current
   DESCRIPTION
      "The value of the tlsCntTreeGlobalIndex of the MANAGED OBJECT."
   ::= {sr1646v2EthOamManagedMepsEntry 10}

sr1646v2EthOamManagedMepsTableIx OBJECT-TYPE
   SYNTAX      TableIndex
   MAX-ACCESS  not-accessible
   STATUS      current
   DESCRIPTION
      ""
   ::= {sr1646v2EthOamManagedMepsEntry 11}

sr1646v2EthOamManagedMepsManagedMepName OBJECT-TYPE
   SYNTAX      DisplayString
   MAX-ACCESS  read-only
   STATUS      current
   DESCRIPTION
      "Path: ethOam.status.managedMeps.managedMepName"
   ::= {sr1646v2EthOamManagedMepsEntry 201326592}

sr1646v2EthOamManagedMepsInterface OBJECT-TYPE
   SYNTAX      DisplayString
   MAX-ACCESS  read-only
   STATUS      current
   DESCRIPTION
      "Path: ethOam.status.managedMeps.interface"
   ::= {sr1646v2EthOamManagedMepsEntry 16777216}

sr1646v2EthOamManagedMepsVid OBJECT-TYPE
   SYNTAX      INTEGER
               {
               untagged (0)
               }
   MAX-ACCESS  read-only
   STATUS      current
   DESCRIPTION
      "Path: ethOam.status.managedMeps.vid

       Possibilities:
               untagged   (0)"
   ::= {sr1646v2EthOamManagedMepsEntry 33554432}

sr1646v2EthOamManagedMepsTpid OBJECT-TYPE
   SYNTAX      INTEGER
               {
               slOPTg (0),
               dot1Q (33024),
               dot1ad (34984),
               s0x9100 (37120),
               s0x9200 (37376),
               s0x9300 (37632)
               }
   MAX-ACCESS  read-only
   STATUS      current
   DESCRIPTION
      "Path: ethOam.status.managedMeps.tpid

       Possibilities:
               <OPT>   (0)
               dot1Q   (33024)
               dot1ad   (34984)
               0x9100   (37120)
               0x9200   (37376)
               0x9300   (37632)"
   ::= {sr1646v2EthOamManagedMepsEntry 218103808}

sr1646v2EthOamManagedMepsPriority OBJECT-TYPE
   SYNTAX      Integer32
   MAX-ACCESS  read-only
   STATUS      current
   DESCRIPTION
      "Path: ethOam.status.managedMeps.priority"
   ::= {sr1646v2EthOamManagedMepsEntry 50331648}

sr1646v2EthOamManagedMepsPeriod OBJECT-TYPE
   SYNTAX      INTEGER
               {
               unknown (0),
               s3d33ms (1),
               s10ms (2),
               s100ms (3),
               s1s (4),
               s10s (5),
               s1min (6),
               s10min (7)
               }
   MAX-ACCESS  read-only
   STATUS      current
   DESCRIPTION
      "Path: ethOam.status.managedMeps.period

       Possibilities:
               unknown   (0)
               3.33ms   (1)
               10ms   (2)
               100ms   (3)
               1s   (4)
               10s   (5)
               1min   (6)
               10min   (7)"
   ::= {sr1646v2EthOamManagedMepsEntry 67108864}

sr1646v2EthOamManagedMepsMegLevel OBJECT-TYPE
   SYNTAX      Integer32
   MAX-ACCESS  read-only
   STATUS      current
   DESCRIPTION
      "Path: ethOam.status.managedMeps.megLevel"
   ::= {sr1646v2EthOamManagedMepsEntry 83886080}

sr1646v2EthOamManagedMepsMegIdMaintDomainName OBJECT-TYPE
   SYNTAX      DisplayString
   MAX-ACCESS  read-only
   STATUS      current
   DESCRIPTION
      "Path: ethOam.status.managedMeps.megId.maintDomainName"
   ::= {sr1646v2EthOamManagedMepsEntry 100728832}

sr1646v2EthOamManagedMepsMegIdShortMaName OBJECT-TYPE
   SYNTAX      DisplayString
   MAX-ACCESS  read-only
   STATUS      current
   DESCRIPTION
      "Path: ethOam.status.managedMeps.megId.shortMaName"
   ::= {sr1646v2EthOamManagedMepsEntry 100794368}

sr1646v2EthOamManagedMepsMepId OBJECT-TYPE
   SYNTAX      Integer32
   MAX-ACCESS  read-only
   STATUS      current
   DESCRIPTION
      "Path: ethOam.status.managedMeps.mepId"
   ::= {sr1646v2EthOamManagedMepsEntry 117440512}

sr1646v2EthOamManagedMepsMacAddress OBJECT-TYPE
   SYNTAX      OCTET STRING
   MAX-ACCESS  read-only
   STATUS      current
   DESCRIPTION
      "Path: ethOam.status.managedMeps.macAddress

       MAC address."
   ::= {sr1646v2EthOamManagedMepsEntry 134217728}

sr1646v2EthOamManagedMepsIntfStatus OBJECT-TYPE
   SYNTAX      INTEGER
               {
               noTlv (0),
               up (1),
               down (2),
               testing (3),
               unknown (4),
               dormant (5),
               notPresent (6),
               lowerLayerDown (7)
               }
   MAX-ACCESS  read-only
   STATUS      current
   DESCRIPTION
      "Path: ethOam.status.managedMeps.intfStatus

       Possibilities:
               noTlv   (0)
               up   (1)
               down   (2)
               testing   (3)
               unknown   (4)
               dormant   (5)
               notPresent   (6)
               lowerLayerDown   (7)"
   ::= {sr1646v2EthOamManagedMepsEntry 167772160}

sr1646v2EthOamManagedMepsPortStatus OBJECT-TYPE
   SYNTAX      INTEGER
               {
               noTlv (0),
               blocked (1),
               up (2)
               }
   MAX-ACCESS  read-only
   STATUS      current
   DESCRIPTION
      "Path: ethOam.status.managedMeps.portStatus

       Possibilities:
               noTlv   (0)
               blocked   (1)
               up   (2)"
   ::= {sr1646v2EthOamManagedMepsEntry 184549376}

sr1646v2EthOamManagedMepsAlarm OBJECT-TYPE
   SYNTAX      Integer32
   MAX-ACCESS  read-only
   STATUS      current
   DESCRIPTION
      "Path: ethOam.status.managedMeps.alarm

       Bit meanings:
               bit 3 = lossOfContinuity"
   ::= {sr1646v2EthOamManagedMepsEntry 150994944}


sr1646v2EthOamDefectLog OBJECT IDENTIFIER ::= {sr1646v2EthOam 18}

sr1646v2EthOamDefectLogSSCTable OBJECT-TYPE
   SYNTAX      SEQUENCE OF Sr1646v2EthOamDefectLogEntry
   MAX-ACCESS  not-accessible
   STATUS      current
   DESCRIPTION
      "ETH OAM defect log"
   ::= {sr1646v2EthOamDefectLog 1}

sr1646v2EthOamDefectLogEntry OBJECT-TYPE
   SYNTAX      Sr1646v2EthOamDefectLogEntry
   MAX-ACCESS  not-accessible
   STATUS      current
   DESCRIPTION
      ""
   INDEX      { sr1646v2EthOamDefectLogGlobalIx,
                sr1646v2EthOamDefectLogTableIx }
   ::= {sr1646v2EthOamDefectLogSSCTable 1}

Sr1646v2EthOamDefectLogEntry ::=
   SEQUENCE
      {
      sr1646v2EthOamDefectLogGlobalIx
         GlobalIndex,
      sr1646v2EthOamDefectLogTableIx
         TableIndex,
      sr1646v2EthOamDefectLogSysUpTime
         TimeTicks,
      sr1646v2EthOamDefectLogType
         INTEGER,
      sr1646v2EthOamDefectLogMode
         INTEGER,
      sr1646v2EthOamDefectLogMepName
         DisplayString,
      sr1646v2EthOamDefectLogSourceMacAddress
         OCTET STRING,
      sr1646v2EthOamDefectLogMegLevel
         Integer32,
      sr1646v2EthOamDefectLogMegIdMaintDomainName
         DisplayString,
      sr1646v2EthOamDefectLogMegIdShortMaName
         DisplayString,
      sr1646v2EthOamDefectLogMepId
         INTEGER,
      sr1646v2EthOamDefectLogPeriod
         INTEGER,
      sr1646v2EthOamDefectLogVid
         INTEGER,
      sr1646v2EthOamDefectLogTpid
         INTEGER
      }

sr1646v2EthOamDefectLogGlobalIx OBJECT-TYPE
   SYNTAX      GlobalIndex
   MAX-ACCESS  not-accessible
   STATUS      current
   DESCRIPTION
      "The value of the tlsCntTreeGlobalIndex of the MANAGED OBJECT."
   ::= {sr1646v2EthOamDefectLogEntry 10}

sr1646v2EthOamDefectLogTableIx OBJECT-TYPE
   SYNTAX      TableIndex
   MAX-ACCESS  not-accessible
   STATUS      current
   DESCRIPTION
      ""
   ::= {sr1646v2EthOamDefectLogEntry 11}

sr1646v2EthOamDefectLogSysUpTime OBJECT-TYPE
   SYNTAX      TimeTicks
   MAX-ACCESS  read-only
   STATUS      current
   DESCRIPTION
      "Path: ethOam.status.defectLog.sysUpTime

       Time in centi-second."
   ::= {sr1646v2EthOamDefectLogEntry 16777216}

sr1646v2EthOamDefectLogType OBJECT-TYPE
   SYNTAX      INTEGER
               {
               mismerge (1),
               unexpectedMep (2),
               unexpectedMegLevel (3),
               unexpectedPeriod (4),
               aisFrame (5),
               wrongMacAddress (6)
               }
   MAX-ACCESS  read-only
   STATUS      current
   DESCRIPTION
      "Path: ethOam.status.defectLog.type

       Possibilities:
               mismerge   (1)
               unexpectedMep   (2)
               unexpectedMegLevel   (3)
               unexpectedPeriod   (4)
               aisFrame   (5)
               wrongMacAddress   (6)"
   ::= {sr1646v2EthOamDefectLogEntry 33554432}

sr1646v2EthOamDefectLogMode OBJECT-TYPE
   SYNTAX      INTEGER
               {
               ym1731 (1),
               s802m1ag (2),
               unknown (4)
               }
   MAX-ACCESS  read-only
   STATUS      current
   DESCRIPTION
      "Path: ethOam.status.defectLog.mode

       Possibilities:
               y-1731   (1)
               802-1ag   (2)
               unknown   (4)"
   ::= {sr1646v2EthOamDefectLogEntry 50331648}

sr1646v2EthOamDefectLogMepName OBJECT-TYPE
   SYNTAX      DisplayString
   MAX-ACCESS  read-only
   STATUS      current
   DESCRIPTION
      "Path: ethOam.status.defectLog.mepName"
   ::= {sr1646v2EthOamDefectLogEntry 67108864}

sr1646v2EthOamDefectLogSourceMacAddress OBJECT-TYPE
   SYNTAX      OCTET STRING
   MAX-ACCESS  read-only
   STATUS      current
   DESCRIPTION
      "Path: ethOam.status.defectLog.sourceMacAddress

       MAC address."
   ::= {sr1646v2EthOamDefectLogEntry 83886080}

sr1646v2EthOamDefectLogMegLevel OBJECT-TYPE
   SYNTAX      Integer32
   MAX-ACCESS  read-only
   STATUS      current
   DESCRIPTION
      "Path: ethOam.status.defectLog.megLevel"
   ::= {sr1646v2EthOamDefectLogEntry 100663296}

sr1646v2EthOamDefectLogMegIdMaintDomainName OBJECT-TYPE
   SYNTAX      DisplayString
   MAX-ACCESS  read-only
   STATUS      current
   DESCRIPTION
      "Path: ethOam.status.defectLog.megId.maintDomainName"
   ::= {sr1646v2EthOamDefectLogEntry 117506048}

sr1646v2EthOamDefectLogMegIdShortMaName OBJECT-TYPE
   SYNTAX      DisplayString
   MAX-ACCESS  read-only
   STATUS      current
   DESCRIPTION
      "Path: ethOam.status.defectLog.megId.shortMaName"
   ::= {sr1646v2EthOamDefectLogEntry 117571584}

sr1646v2EthOamDefectLogMepId OBJECT-TYPE
   SYNTAX      INTEGER
               {
               unknown (8192)
               }
   MAX-ACCESS  read-only
   STATUS      current
   DESCRIPTION
      "Path: ethOam.status.defectLog.mepId

       Possibilities:
               unknown   (8192)"
   ::= {sr1646v2EthOamDefectLogEntry 134217728}

sr1646v2EthOamDefectLogPeriod OBJECT-TYPE
   SYNTAX      INTEGER
               {
               unknown (0),
               s3d33ms (1),
               s10ms (2),
               s100ms (3),
               s1s (4),
               s10s (5),
               s1min (6),
               s10min (7)
               }
   MAX-ACCESS  read-only
   STATUS      current
   DESCRIPTION
      "Path: ethOam.status.defectLog.period

       Possibilities:
               unknown   (0)
               3.33ms   (1)
               10ms   (2)
               100ms   (3)
               1s   (4)
               10s   (5)
               1min   (6)
               10min   (7)"
   ::= {sr1646v2EthOamDefectLogEntry 150994944}

sr1646v2EthOamDefectLogVid OBJECT-TYPE
   SYNTAX      INTEGER
               {
               untagged (0)
               }
   MAX-ACCESS  read-only
   STATUS      current
   DESCRIPTION
      "Path: ethOam.status.defectLog.vid

       Possibilities:
               untagged   (0)"
   ::= {sr1646v2EthOamDefectLogEntry 167772160}

sr1646v2EthOamDefectLogTpid OBJECT-TYPE
   SYNTAX      INTEGER
               {
               slOPTg (0),
               dot1Q (33024),
               dot1ad (34984),
               s0x9100 (37120),
               s0x9200 (37376),
               s0x9300 (37632)
               }
   MAX-ACCESS  read-only
   STATUS      current
   DESCRIPTION
      "Path: ethOam.status.defectLog.tpid

       Possibilities:
               <OPT>   (0)
               dot1Q   (33024)
               dot1ad   (34984)
               0x9100   (37120)
               0x9200   (37376)
               0x9300   (37632)"
   ::= {sr1646v2EthOamDefectLogEntry 184549376}


sr1646v2EthOamOperStatus OBJECT IDENTIFIER ::= {sr1646v2EthOam 39}

sr1646v2EthOamOperStatusTable OBJECT-TYPE
   SYNTAX      SEQUENCE OF Sr1646v2EthOamOperStatusEntry
   MAX-ACCESS  not-accessible
   STATUS      current
   DESCRIPTION
      "OAM module operating status"
   ::= {sr1646v2EthOamOperStatus 1}

sr1646v2EthOamOperStatusEntry OBJECT-TYPE
   SYNTAX      Sr1646v2EthOamOperStatusEntry
   MAX-ACCESS  not-accessible
   STATUS      current
   DESCRIPTION
      ""
   INDEX      { sr1646v2EthOamOperStatusGlobalIx }
   ::= {sr1646v2EthOamOperStatusTable 1}

Sr1646v2EthOamOperStatusEntry ::=
   SEQUENCE
      {
      sr1646v2EthOamOperStatusGlobalIx
         GlobalIndex,
      sr1646v2EthOamOperStatusValue
         INTEGER
      }

sr1646v2EthOamOperStatusGlobalIx OBJECT-TYPE
   SYNTAX      GlobalIndex
   MAX-ACCESS  not-accessible
   STATUS      current
   DESCRIPTION
      "The value of the tlsCntTreeGlobalIndex of the MANAGED OBJECT."
   ::= {sr1646v2EthOamOperStatusEntry 10}

sr1646v2EthOamOperStatusValue OBJECT-TYPE
   SYNTAX      INTEGER
               {
               booting (0),
               disabled (1),
               startDelay (2),
               enabled (3)
               }
   MAX-ACCESS  read-only
   STATUS      current
   DESCRIPTION
      "Path: ethOam.status.operStatus

       Possibilities:
               booting   (0)
               disabled   (1)
               startDelay   (2)
               enabled   (3)"
   ::= {sr1646v2EthOamOperStatusEntry 2147483648}


sr1646v2EthOamSnmpIndex OBJECT IDENTIFIER ::= {sr1646v2EthOam 269}

sr1646v2EthOamSnmpIndexTable OBJECT-TYPE
   SYNTAX      SEQUENCE OF Sr1646v2EthOamSnmpIndexEntry
   MAX-ACCESS  not-accessible
   STATUS      current
   DESCRIPTION
      "SNMP index assigned to this object"
   ::= {sr1646v2EthOamSnmpIndex 1}

sr1646v2EthOamSnmpIndexEntry OBJECT-TYPE
   SYNTAX      Sr1646v2EthOamSnmpIndexEntry
   MAX-ACCESS  not-accessible
   STATUS      current
   DESCRIPTION
      ""
   INDEX      { sr1646v2EthOamSnmpIndexGlobalIx }
   ::= {sr1646v2EthOamSnmpIndexTable 1}

Sr1646v2EthOamSnmpIndexEntry ::=
   SEQUENCE
      {
      sr1646v2EthOamSnmpIndexGlobalIx
         GlobalIndex,
      sr1646v2EthOamSnmpIndexValue
         Integer32
      }

sr1646v2EthOamSnmpIndexGlobalIx OBJECT-TYPE
   SYNTAX      GlobalIndex
   MAX-ACCESS  not-accessible
   STATUS      current
   DESCRIPTION
      "The value of the tlsCntTreeGlobalIndex of the MANAGED OBJECT."
   ::= {sr1646v2EthOamSnmpIndexEntry 10}

sr1646v2EthOamSnmpIndexValue OBJECT-TYPE
   SYNTAX      Integer32
   MAX-ACCESS  read-only
   STATUS      current
   DESCRIPTION
      "Path: ethOam.status.snmpIndex"
   ::= {sr1646v2EthOamSnmpIndexEntry 2147483648}



pr1646v2EthOam OBJECT IDENTIFIER ::= {r1646v2EthOam 12}


pr1646v2EthOamLinkTrace OBJECT IDENTIFIER ::= {pr1646v2EthOam 19}

pr1646v2EthOamLinkTraceSSCTable OBJECT-TYPE
   SYNTAX      SEQUENCE OF Pr1646v2EthOamLinkTraceEntry
   MAX-ACCESS  not-accessible
   STATUS      current
   DESCRIPTION
      "link trace status"
   ::= {pr1646v2EthOamLinkTrace 1}

pr1646v2EthOamLinkTraceEntry OBJECT-TYPE
   SYNTAX      Pr1646v2EthOamLinkTraceEntry
   MAX-ACCESS  not-accessible
   STATUS      current
   DESCRIPTION
      ""
   INDEX      { pr1646v2EthOamLinkTraceGlobalIx,
                pr1646v2EthOamLinkTraceTableIx }
   ::= {pr1646v2EthOamLinkTraceSSCTable 1}

Pr1646v2EthOamLinkTraceEntry ::=
   SEQUENCE
      {
      pr1646v2EthOamLinkTraceGlobalIx
         GlobalIndex,
      pr1646v2EthOamLinkTraceTableIx
         TableIndex,
      pr1646v2EthOamLinkTraceSourceMepName
         DisplayString,
      pr1646v2EthOamLinkTraceTtl
         Integer32,
      pr1646v2EthOamLinkTraceRelayAction
         INTEGER,
      pr1646v2EthOamLinkTraceIngressAction
         INTEGER,
      pr1646v2EthOamLinkTraceIngressMacAddress
         OCTET STRING,
      pr1646v2EthOamLinkTraceEgressAction
         INTEGER,
      pr1646v2EthOamLinkTraceEgressMacAddress
         OCTET STRING
      }

pr1646v2EthOamLinkTraceGlobalIx OBJECT-TYPE
   SYNTAX      GlobalIndex
   MAX-ACCESS  not-accessible
   STATUS      current
   DESCRIPTION
      "The value of the tlsCntTreeGlobalIndex of the MANAGED OBJECT."
   ::= {pr1646v2EthOamLinkTraceEntry 10}

pr1646v2EthOamLinkTraceTableIx OBJECT-TYPE
   SYNTAX      TableIndex
   MAX-ACCESS  not-accessible
   STATUS      current
   DESCRIPTION
      ""
   ::= {pr1646v2EthOamLinkTraceEntry 11}

pr1646v2EthOamLinkTraceSourceMepName OBJECT-TYPE
   SYNTAX      DisplayString
   MAX-ACCESS  read-only
   STATUS      current
   DESCRIPTION
      "Path: ethOam.performance.linkTrace.sourceMepName"
   ::= {pr1646v2EthOamLinkTraceEntry 16777216}

pr1646v2EthOamLinkTraceTtl OBJECT-TYPE
   SYNTAX      Integer32
   MAX-ACCESS  read-only
   STATUS      current
   DESCRIPTION
      "Path: ethOam.performance.linkTrace.ttl"
   ::= {pr1646v2EthOamLinkTraceEntry 33554432}

pr1646v2EthOamLinkTraceRelayAction OBJECT-TYPE
   SYNTAX      INTEGER
               {
               rlyHit (1),
               rlyFdb (2),
               rlyMpdb (3)
               }
   MAX-ACCESS  read-only
   STATUS      current
   DESCRIPTION
      "Path: ethOam.performance.linkTrace.relayAction

       Possibilities:
               rlyHit   (1)
               rlyFdb   (2)
               rlyMpdb   (3)"
   ::= {pr1646v2EthOamLinkTraceEntry 50331648}

pr1646v2EthOamLinkTraceIngressAction OBJECT-TYPE
   SYNTAX      INTEGER
               {
               notPresent (0),
               ingOk (1),
               ingDown (2),
               ingBlocked (3),
               ingVid (4),
               ingY1731 (239)
               }
   MAX-ACCESS  read-only
   STATUS      current
   DESCRIPTION
      "Path: ethOam.performance.linkTrace.ingressAction

       Possibilities:
               notPresent   (0)
               ingOk   (1)
               ingDown   (2)
               ingBlocked   (3)
               ingVid   (4)
               ingY1731   (239)"
   ::= {pr1646v2EthOamLinkTraceEntry 67108864}

pr1646v2EthOamLinkTraceIngressMacAddress OBJECT-TYPE
   SYNTAX      OCTET STRING
   MAX-ACCESS  read-only
   STATUS      current
   DESCRIPTION
      "Path: ethOam.performance.linkTrace.ingressMacAddress

       MAC address."
   ::= {pr1646v2EthOamLinkTraceEntry 83886080}

pr1646v2EthOamLinkTraceEgressAction OBJECT-TYPE
   SYNTAX      INTEGER
               {
               notPresent (0),
               egrOk (1),
               egrDown (2),
               egrBlocked (3),
               egrVid (4),
               egrY1731 (239)
               }
   MAX-ACCESS  read-only
   STATUS      current
   DESCRIPTION
      "Path: ethOam.performance.linkTrace.egressAction

       Possibilities:
               notPresent   (0)
               egrOk   (1)
               egrDown   (2)
               egrBlocked   (3)
               egrVid   (4)
               egrY1731   (239)"
   ::= {pr1646v2EthOamLinkTraceEntry 100663296}

pr1646v2EthOamLinkTraceEgressMacAddress OBJECT-TYPE
   SYNTAX      OCTET STRING
   MAX-ACCESS  read-only
   STATUS      current
   DESCRIPTION
      "Path: ethOam.performance.linkTrace.egressMacAddress

       MAC address."
   ::= {pr1646v2EthOamLinkTraceEntry 117440512}


pr1646v2EthOamMulticastLoopback OBJECT IDENTIFIER ::= {pr1646v2EthOam 35}

pr1646v2EthOamMulticastLoopbackSSCTable OBJECT-TYPE
   SYNTAX      SEQUENCE OF Pr1646v2EthOamMulticastLoopbackEntry
   MAX-ACCESS  not-accessible
   STATUS      current
   DESCRIPTION
      "multicast loopback status"
   ::= {pr1646v2EthOamMulticastLoopback 1}

pr1646v2EthOamMulticastLoopbackEntry OBJECT-TYPE
   SYNTAX      Pr1646v2EthOamMulticastLoopbackEntry
   MAX-ACCESS  not-accessible
   STATUS      current
   DESCRIPTION
      ""
   INDEX      { pr1646v2EthOamMulticastLoopbackGlobalIx,
                pr1646v2EthOamMulticastLoopbackTableIx }
   ::= {pr1646v2EthOamMulticastLoopbackSSCTable 1}

Pr1646v2EthOamMulticastLoopbackEntry ::=
   SEQUENCE
      {
      pr1646v2EthOamMulticastLoopbackGlobalIx
         GlobalIndex,
      pr1646v2EthOamMulticastLoopbackTableIx
         TableIndex,
      pr1646v2EthOamMulticastLoopbackSourceMepName
         DisplayString,
      pr1646v2EthOamMulticastLoopbackRemoteMacAddress
         OCTET STRING,
      pr1646v2EthOamMulticastLoopbackStatus
         INTEGER,
      pr1646v2EthOamMulticastLoopbackMepId
         INTEGER,
      pr1646v2EthOamMulticastLoopbackDelay
         Integer32
      }

pr1646v2EthOamMulticastLoopbackGlobalIx OBJECT-TYPE
   SYNTAX      GlobalIndex
   MAX-ACCESS  not-accessible
   STATUS      current
   DESCRIPTION
      "The value of the tlsCntTreeGlobalIndex of the MANAGED OBJECT."
   ::= {pr1646v2EthOamMulticastLoopbackEntry 10}

pr1646v2EthOamMulticastLoopbackTableIx OBJECT-TYPE
   SYNTAX      TableIndex
   MAX-ACCESS  not-accessible
   STATUS      current
   DESCRIPTION
      ""
   ::= {pr1646v2EthOamMulticastLoopbackEntry 11}

pr1646v2EthOamMulticastLoopbackSourceMepName OBJECT-TYPE
   SYNTAX      DisplayString
   MAX-ACCESS  read-only
   STATUS      current
   DESCRIPTION
      "Path: ethOam.performance.multicastLoopback.sourceMepName"
   ::= {pr1646v2EthOamMulticastLoopbackEntry 16777216}

pr1646v2EthOamMulticastLoopbackRemoteMacAddress OBJECT-TYPE
   SYNTAX      OCTET STRING
   MAX-ACCESS  read-only
   STATUS      current
   DESCRIPTION
      "Path: ethOam.performance.multicastLoopback.remoteMacAddress

       MAC address."
   ::= {pr1646v2EthOamMulticastLoopbackEntry 33554432}

pr1646v2EthOamMulticastLoopbackStatus OBJECT-TYPE
   SYNTAX      INTEGER
               {
               managed (0),
               discovered (1),
               unknown (2)
               }
   MAX-ACCESS  read-only
   STATUS      current
   DESCRIPTION
      "Path: ethOam.performance.multicastLoopback.status

       Possibilities:
               managed   (0)
               discovered   (1)
               unknown   (2)"
   ::= {pr1646v2EthOamMulticastLoopbackEntry 50331648}

pr1646v2EthOamMulticastLoopbackMepId OBJECT-TYPE
   SYNTAX      INTEGER
               {
               unknown (8192)
               }
   MAX-ACCESS  read-only
   STATUS      current
   DESCRIPTION
      "Path: ethOam.performance.multicastLoopback.mepId

       Possibilities:
               unknown   (8192)"
   ::= {pr1646v2EthOamMulticastLoopbackEntry 67108864}

pr1646v2EthOamMulticastLoopbackDelay OBJECT-TYPE
   SYNTAX      Integer32
   MAX-ACCESS  read-only
   STATUS      current
   DESCRIPTION
      "Path: ethOam.performance.multicastLoopback.delay

       unit name = sec
       formula = 1000 / ; 1000 *"
   ::= {pr1646v2EthOamMulticastLoopbackEntry 83886080}


pr1646v2EthOamLoopback OBJECT IDENTIFIER ::= {pr1646v2EthOam 20}

pr1646v2EthOamLoopbackSSCTable OBJECT-TYPE
   SYNTAX      SEQUENCE OF Pr1646v2EthOamLoopbackEntry
   MAX-ACCESS  not-accessible
   STATUS      current
   DESCRIPTION
      "loopback performance table"
   ::= {pr1646v2EthOamLoopback 1}

pr1646v2EthOamLoopbackEntry OBJECT-TYPE
   SYNTAX      Pr1646v2EthOamLoopbackEntry
   MAX-ACCESS  not-accessible
   STATUS      current
   DESCRIPTION
      ""
   INDEX      { pr1646v2EthOamLoopbackGlobalIx,
                pr1646v2EthOamLoopbackTableIx }
   ::= {pr1646v2EthOamLoopbackSSCTable 1}

Pr1646v2EthOamLoopbackEntry ::=
   SEQUENCE
      {
      pr1646v2EthOamLoopbackGlobalIx
         GlobalIndex,
      pr1646v2EthOamLoopbackTableIx
         TableIndex,
      pr1646v2EthOamLoopbackMepName
         DisplayString,
      pr1646v2EthOamLoopbackMegLevel
         Integer32,
      pr1646v2EthOamLoopbackMegIdMaintDomainName
         DisplayString,
      pr1646v2EthOamLoopbackMegIdShortMaName
         DisplayString,
      pr1646v2EthOamLoopbackMepId
         INTEGER,
      pr1646v2EthOamLoopbackMacAddress
         OCTET STRING,
      pr1646v2EthOamLoopbackPriority
         Integer32,
      pr1646v2EthOamLoopbackNbrOfTxFrames
         Counter32,
      pr1646v2EthOamLoopbackNbrOfRxFrames
         Counter32,
      pr1646v2EthOamLoopbackNbrOfOutOfSeqFrames
         Counter32,
      pr1646v2EthOamLoopbackNbrOfLateFrames
         Counter32,
      pr1646v2EthOamLoopbackNbrOfBadDataFrames
         Counter32
      }

pr1646v2EthOamLoopbackGlobalIx OBJECT-TYPE
   SYNTAX      GlobalIndex
   MAX-ACCESS  not-accessible
   STATUS      current
   DESCRIPTION
      "The value of the tlsCntTreeGlobalIndex of the MANAGED OBJECT."
   ::= {pr1646v2EthOamLoopbackEntry 10}

pr1646v2EthOamLoopbackTableIx OBJECT-TYPE
   SYNTAX      TableIndex
   MAX-ACCESS  not-accessible
   STATUS      current
   DESCRIPTION
      ""
   ::= {pr1646v2EthOamLoopbackEntry 11}

pr1646v2EthOamLoopbackMepName OBJECT-TYPE
   SYNTAX      DisplayString
   MAX-ACCESS  read-only
   STATUS      current
   DESCRIPTION
      "Path: ethOam.performance.loopback.mepName"
   ::= {pr1646v2EthOamLoopbackEntry 16777216}

pr1646v2EthOamLoopbackMegLevel OBJECT-TYPE
   SYNTAX      Integer32
   MAX-ACCESS  read-only
   STATUS      current
   DESCRIPTION
      "Path: ethOam.performance.loopback.megLevel"
   ::= {pr1646v2EthOamLoopbackEntry 33554432}

pr1646v2EthOamLoopbackMegIdMaintDomainName OBJECT-TYPE
   SYNTAX      DisplayString
   MAX-ACCESS  read-only
   STATUS      current
   DESCRIPTION
      "Path: ethOam.performance.loopback.megId.maintDomainName"
   ::= {pr1646v2EthOamLoopbackEntry 50397184}

pr1646v2EthOamLoopbackMegIdShortMaName OBJECT-TYPE
   SYNTAX      DisplayString
   MAX-ACCESS  read-only
   STATUS      current
   DESCRIPTION
      "Path: ethOam.performance.loopback.megId.shortMaName"
   ::= {pr1646v2EthOamLoopbackEntry 50462720}

pr1646v2EthOamLoopbackMepId OBJECT-TYPE
   SYNTAX      INTEGER
               {
               unknown (8192)
               }
   MAX-ACCESS  read-only
   STATUS      current
   DESCRIPTION
      "Path: ethOam.performance.loopback.mepId

       Possibilities:
               unknown   (8192)"
   ::= {pr1646v2EthOamLoopbackEntry 67108864}

pr1646v2EthOamLoopbackMacAddress OBJECT-TYPE
   SYNTAX      OCTET STRING
   MAX-ACCESS  read-only
   STATUS      current
   DESCRIPTION
      "Path: ethOam.performance.loopback.macAddress

       MAC address."
   ::= {pr1646v2EthOamLoopbackEntry 83886080}

pr1646v2EthOamLoopbackPriority OBJECT-TYPE
   SYNTAX      Integer32
   MAX-ACCESS  read-only
   STATUS      current
   DESCRIPTION
      "Path: ethOam.performance.loopback.priority"
   ::= {pr1646v2EthOamLoopbackEntry 100663296}

pr1646v2EthOamLoopbackNbrOfTxFrames OBJECT-TYPE
   SYNTAX      Counter32
   MAX-ACCESS  read-only
   STATUS      current
   DESCRIPTION
      "Path: ethOam.performance.loopback.nbrOfTxFrames

       32 bit unsigned wrappable counter."
   ::= {pr1646v2EthOamLoopbackEntry 117440512}

pr1646v2EthOamLoopbackNbrOfRxFrames OBJECT-TYPE
   SYNTAX      Counter32
   MAX-ACCESS  read-only
   STATUS      current
   DESCRIPTION
      "Path: ethOam.performance.loopback.nbrOfRxFrames

       32 bit unsigned wrappable counter."
   ::= {pr1646v2EthOamLoopbackEntry 134217728}

pr1646v2EthOamLoopbackNbrOfOutOfSeqFrames OBJECT-TYPE
   SYNTAX      Counter32
   MAX-ACCESS  read-only
   STATUS      current
   DESCRIPTION
      "Path: ethOam.performance.loopback.nbrOfOutOfSeqFrames

       32 bit unsigned wrappable counter."
   ::= {pr1646v2EthOamLoopbackEntry 150994944}

pr1646v2EthOamLoopbackNbrOfLateFrames OBJECT-TYPE
   SYNTAX      Counter32
   MAX-ACCESS  read-only
   STATUS      current
   DESCRIPTION
      "Path: ethOam.performance.loopback.nbrOfLateFrames

       32 bit unsigned wrappable counter."
   ::= {pr1646v2EthOamLoopbackEntry 167772160}

pr1646v2EthOamLoopbackNbrOfBadDataFrames OBJECT-TYPE
   SYNTAX      Counter32
   MAX-ACCESS  read-only
   STATUS      current
   DESCRIPTION
      "Path: ethOam.performance.loopback.nbrOfBadDataFrames

       32 bit unsigned wrappable counter."
   ::= {pr1646v2EthOamLoopbackEntry 184549376}


pr1646v2EthOamQualityMonitor OBJECT IDENTIFIER ::= {pr1646v2EthOam 37}

pr1646v2EthOamQualityMonitorSSCTable OBJECT-TYPE
   SYNTAX      SEQUENCE OF Pr1646v2EthOamQualityMonitorEntry
   MAX-ACCESS  not-accessible
   STATUS      current
   DESCRIPTION
      "OAM quality monitor"
   ::= {pr1646v2EthOamQualityMonitor 1}

pr1646v2EthOamQualityMonitorEntry OBJECT-TYPE
   SYNTAX      Pr1646v2EthOamQualityMonitorEntry
   MAX-ACCESS  not-accessible
   STATUS      current
   DESCRIPTION
      ""
   INDEX      { pr1646v2EthOamQualityMonitorGlobalIx,
                pr1646v2EthOamQualityMonitorTableIx }
   ::= {pr1646v2EthOamQualityMonitorSSCTable 1}

Pr1646v2EthOamQualityMonitorEntry ::=
   SEQUENCE
      {
      pr1646v2EthOamQualityMonitorGlobalIx
         GlobalIndex,
      pr1646v2EthOamQualityMonitorTableIx
         TableIndex,
      pr1646v2EthOamQualityMonitorName
         DisplayString,
      pr1646v2EthOamQualityMonitorStatus
         INTEGER,
      pr1646v2EthOamQualityMonitorMepName
         DisplayString,
      pr1646v2EthOamQualityMonitorMegLevel
         Integer32,
      pr1646v2EthOamQualityMonitorMegIdMaintDomainName
         DisplayString,
      pr1646v2EthOamQualityMonitorMegIdShortMaName
         DisplayString,
      pr1646v2EthOamQualityMonitorMepId
         INTEGER,
      pr1646v2EthOamQualityMonitorMacAddress
         OCTET STRING,
      pr1646v2EthOamQualityMonitorPriority
         Integer32,
      pr1646v2EthOamQualityMonitorType
         INTEGER,
      pr1646v2EthOamQualityMonitorNbrTxPckt
         Counter32,
      pr1646v2EthOamQualityMonitorNbrRxPckt
         Counter32,
      pr1646v2EthOamQualityMonitorError
         Counter32,
      pr1646v2EthOamQualityMonitorDelay
         Integer32,
      pr1646v2EthOamQualityMonitorJitter
         Integer32,
      pr1646v2EthOamQualityMonitorLoss
         Counter32,
      pr1646v2EthOamQualityMonitorLossDelay
         Counter32,
      pr1646v2EthOamQualityMonitorDelayMin
         Integer32,
      pr1646v2EthOamQualityMonitorDelayAvrg
         Integer32,
      pr1646v2EthOamQualityMonitorDelayMax
         Integer32,
      pr1646v2EthOamQualityMonitorDelayBinsType
         INTEGER,
      pr1646v2EthOamQualityMonitorDelayBinsMinMin
         Counter32,
      pr1646v2EthOamQualityMonitorDelayBinsMin
         Integer32,
      pr1646v2EthOamQualityMonitorDelayBinsMinBin1
         Counter32,
      pr1646v2EthOamQualityMonitorDelayBinsBin2
         Counter32,
      pr1646v2EthOamQualityMonitorDelayBinsBin3
         Counter32,
      pr1646v2EthOamQualityMonitorDelayBinsBin4
         Counter32,
      pr1646v2EthOamQualityMonitorDelayBinsBin5
         Counter32,
      pr1646v2EthOamQualityMonitorDelayBinsBin6
         Counter32,
      pr1646v2EthOamQualityMonitorDelayBinsBin7
         Counter32,
      pr1646v2EthOamQualityMonitorDelayBinsMaxBin8
         Counter32,
      pr1646v2EthOamQualityMonitorDelayBinsMax
         Integer32,
      pr1646v2EthOamQualityMonitorDelayBinsPlusMax
         Counter32,
      pr1646v2EthOamQualityMonitorJitterNegMax
         Integer32,
      pr1646v2EthOamQualityMonitorJitterAvrg
         Integer32,
      pr1646v2EthOamQualityMonitorJitterPosMax
         Integer32,
      pr1646v2EthOamQualityMonitorJitterBinsType
         INTEGER,
      pr1646v2EthOamQualityMonitorJitterBinsMinMin
         Counter32,
      pr1646v2EthOamQualityMonitorJitterBinsMin
         Integer32,
      pr1646v2EthOamQualityMonitorJitterBinsMinBin1
         Counter32,
      pr1646v2EthOamQualityMonitorJitterBinsBin2
         Counter32,
      pr1646v2EthOamQualityMonitorJitterBinsBin3
         Counter32,
      pr1646v2EthOamQualityMonitorJitterBinsBin4
         Counter32,
      pr1646v2EthOamQualityMonitorJitterBinsBin5
         Counter32,
      pr1646v2EthOamQualityMonitorJitterBinsBin6
         Counter32,
      pr1646v2EthOamQualityMonitorJitterBinsBin7
         Counter32,
      pr1646v2EthOamQualityMonitorJitterBinsMaxBin8
         Counter32,
      pr1646v2EthOamQualityMonitorJitterBinsMax
         Integer32,
      pr1646v2EthOamQualityMonitorJitterBinsPlusMax
         Counter32,
      pr1646v2EthOamQualityMonitorUpDownStatus
         INTEGER,
      pr1646v2EthOamQualityMonitorUpDownLossUp
         Counter32,
      pr1646v2EthOamQualityMonitorUpDownLossDelayUp
         Counter32,
      pr1646v2EthOamQualityMonitorUpDownDelayUpMin
         Integer32,
      pr1646v2EthOamQualityMonitorUpDownDelayUpAvrg
         Integer32,
      pr1646v2EthOamQualityMonitorUpDownDelayUpMax
         Integer32,
      pr1646v2EthOamQualityMonitorUpDownDelayUpBinsType
         INTEGER,
      pr1646v2EthOamQualityMonitorUpDownDelayUpBinsMinMin
         Counter32,
      pr1646v2EthOamQualityMonitorUpDownDelayUpBinsMin
         Integer32,
      pr1646v2EthOamQualityMonitorUpDownDelayUpBinsMinBin1
         Counter32,
      pr1646v2EthOamQualityMonitorUpDownDelayUpBinsBin2
         Counter32,
      pr1646v2EthOamQualityMonitorUpDownDelayUpBinsBin3
         Counter32,
      pr1646v2EthOamQualityMonitorUpDownDelayUpBinsBin4
         Counter32,
      pr1646v2EthOamQualityMonitorUpDownDelayUpBinsBin5
         Counter32,
      pr1646v2EthOamQualityMonitorUpDownDelayUpBinsBin6
         Counter32,
      pr1646v2EthOamQualityMonitorUpDownDelayUpBinsBin7
         Counter32,
      pr1646v2EthOamQualityMonitorUpDownDelayUpBinsMaxBin8
         Counter32,
      pr1646v2EthOamQualityMonitorUpDownDelayUpBinsMax
         Integer32,
      pr1646v2EthOamQualityMonitorUpDownDelayUpBinsPlusMax
         Counter32,
      pr1646v2EthOamQualityMonitorUpDownJitterUp
         Integer32,
      pr1646v2EthOamQualityMonitorUpDownJitterUpNegMax
         Integer32,
      pr1646v2EthOamQualityMonitorUpDownJitterUpAvrg
         Integer32,
      pr1646v2EthOamQualityMonitorUpDownJitterUpPosMax
         Integer32,
      pr1646v2EthOamQualityMonitorUpDownJitterUpBinsType
         INTEGER,
      pr1646v2EthOamQualityMonitorUpDownJitterUpBinsMinMin
         Counter32,
      pr1646v2EthOamQualityMonitorUpDownJitterUpBinsMin
         Integer32,
      pr1646v2EthOamQualityMonitorUpDownJitterUpBinsMinBin1
         Counter32,
      pr1646v2EthOamQualityMonitorUpDownJitterUpBinsBin2
         Counter32,
      pr1646v2EthOamQualityMonitorUpDownJitterUpBinsBin3
         Counter32,
      pr1646v2EthOamQualityMonitorUpDownJitterUpBinsBin4
         Counter32,
      pr1646v2EthOamQualityMonitorUpDownJitterUpBinsBin5
         Counter32,
      pr1646v2EthOamQualityMonitorUpDownJitterUpBinsBin6
         Counter32,
      pr1646v2EthOamQualityMonitorUpDownJitterUpBinsBin7
         Counter32,
      pr1646v2EthOamQualityMonitorUpDownJitterUpBinsMaxBin8
         Counter32,
      pr1646v2EthOamQualityMonitorUpDownJitterUpBinsMax
         Integer32,
      pr1646v2EthOamQualityMonitorUpDownJitterUpBinsPlusMax
         Counter32,
      pr1646v2EthOamQualityMonitorUpDownLossDown
         Counter32,
      pr1646v2EthOamQualityMonitorUpDownLossDelayDown
         Counter32,
      pr1646v2EthOamQualityMonitorUpDownDelayDownMin
         Integer32,
      pr1646v2EthOamQualityMonitorUpDownDelayDownAvrg
         Integer32,
      pr1646v2EthOamQualityMonitorUpDownDelayDownMax
         Integer32,
      pr1646v2EthOamQualityMonitorUpDownDelayDownBinsType
         INTEGER,
      pr1646v2EthOamQualityMonitorUpDownDelayDownBinsMinMin
         Counter32,
      pr1646v2EthOamQualityMonitorUpDownDelayDownBinsMin
         Integer32,
      pr1646v2EthOamQualityMonitorUpDownDelayDownBinsMinBin1
         Counter32,
      pr1646v2EthOamQualityMonitorUpDownDelayDownBinsBin2
         Counter32,
      pr1646v2EthOamQualityMonitorUpDownDelayDownBinsBin3
         Counter32,
      pr1646v2EthOamQualityMonitorUpDownDelayDownBinsBin4
         Counter32,
      pr1646v2EthOamQualityMonitorUpDownDelayDownBinsBin5
         Counter32,
      pr1646v2EthOamQualityMonitorUpDownDelayDownBinsBin6
         Counter32,
      pr1646v2EthOamQualityMonitorUpDownDelayDownBinsBin7
         Counter32,
      pr1646v2EthOamQualityMonitorUpDownDelayDownBinsMaxBin8
         Counter32,
      pr1646v2EthOamQualityMonitorUpDownDelayDownBinsMax
         Integer32,
      pr1646v2EthOamQualityMonitorUpDownDelayDownBinsPlusMax
         Counter32,
      pr1646v2EthOamQualityMonitorUpDownJitterDown
         Integer32,
      pr1646v2EthOamQualityMonitorUpDownJitterDownNegMax
         Integer32,
      pr1646v2EthOamQualityMonitorUpDownJitterDownAvrg
         Integer32,
      pr1646v2EthOamQualityMonitorUpDownJitterDownPosMax
         Integer32,
      pr1646v2EthOamQualityMonitorUpDownJitterDownBinsType
         INTEGER,
      pr1646v2EthOamQualityMonitorUpDownJitterDownBinsMinMin
         Counter32,
      pr1646v2EthOamQualityMonitorUpDownJitterDownBinsMin
         Integer32,
      pr1646v2EthOamQualityMonitorUpDownJitterDownBinsMinBin1
         Counter32,
      pr1646v2EthOamQualityMonitorUpDownJitterDownBinsBin2
         Counter32,
      pr1646v2EthOamQualityMonitorUpDownJitterDownBinsBin3
         Counter32,
      pr1646v2EthOamQualityMonitorUpDownJitterDownBinsBin4
         Counter32,
      pr1646v2EthOamQualityMonitorUpDownJitterDownBinsBin5
         Counter32,
      pr1646v2EthOamQualityMonitorUpDownJitterDownBinsBin6
         Counter32,
      pr1646v2EthOamQualityMonitorUpDownJitterDownBinsBin7
         Counter32,
      pr1646v2EthOamQualityMonitorUpDownJitterDownBinsMaxBin8
         Counter32,
      pr1646v2EthOamQualityMonitorUpDownJitterDownBinsMax
         Integer32,
      pr1646v2EthOamQualityMonitorUpDownJitterDownBinsPlusMax
         Counter32,
      pr1646v2EthOamQualityMonitorLastLogSysUpTime
         TimeTicks,
      pr1646v2EthOamQualityMonitorLastLogNbrTxPckt
         Counter32,
      pr1646v2EthOamQualityMonitorLastLogNbrRxPckt
         Counter32,
      pr1646v2EthOamQualityMonitorLastLogError
         Counter32,
      pr1646v2EthOamQualityMonitorLastLogLoss
         Counter32,
      pr1646v2EthOamQualityMonitorLastLogLossDelay
         Counter32,
      pr1646v2EthOamQualityMonitorLastLogDelayMin
         Integer32,
      pr1646v2EthOamQualityMonitorLastLogDelayAvrg
         Integer32,
      pr1646v2EthOamQualityMonitorLastLogDelayMax
         Integer32,
      pr1646v2EthOamQualityMonitorLastLogJitterNegMax
         Integer32,
      pr1646v2EthOamQualityMonitorLastLogJitterAvrg
         Integer32,
      pr1646v2EthOamQualityMonitorLastLogJitterPosMax
         Integer32,
      pr1646v2EthOamQualityMonitorLastLogUpDownStatus
         INTEGER,
      pr1646v2EthOamQualityMonitorLastLogUpDownLossUp
         Counter32,
      pr1646v2EthOamQualityMonitorLastLogUpDownLossDelayUp
         Counter32,
      pr1646v2EthOamQualityMonitorLastLogUpDownDelayUpMin
         Integer32,
      pr1646v2EthOamQualityMonitorLastLogUpDownDelayUpAvrg
         Integer32,
      pr1646v2EthOamQualityMonitorLastLogUpDownDelayUpMax
         Integer32,
      pr1646v2EthOamQualityMonitorLastLogUpDownJitterUpNegMax
         Integer32,
      pr1646v2EthOamQualityMonitorLastLogUpDownJitterUpAvrg
         Integer32,
      pr1646v2EthOamQualityMonitorLastLogUpDownJitterUpPosMax
         Integer32,
      pr1646v2EthOamQualityMonitorLastLogUpDownLossDown
         Counter32,
      pr1646v2EthOamQualityMonitorLastLogUpDownLossDelayDown
         Counter32,
      pr1646v2EthOamQualityMonitorLastLogUpDownDelayDownMin
         Integer32,
      pr1646v2EthOamQualityMonitorLastLogUpDownDelayDownAvrg
         Integer32,
      pr1646v2EthOamQualityMonitorLastLogUpDownDelayDownMax
         Integer32,
      pr1646v2EthOamQualityMonitorLastLogUpDownJitterDownNegMax
         Integer32,
      pr1646v2EthOamQualityMonitorLastLogUpDownJitterDownAvrg
         Integer32,
      pr1646v2EthOamQualityMonitorLastLogUpDownJitterDownPosMax
         Integer32,
      pr1646v2EthOamQualityMonitorLastLogDate
         DisplayString,
      pr1646v2EthOamQualityMonitorAlarm
         Integer32
      }

pr1646v2EthOamQualityMonitorGlobalIx OBJECT-TYPE
   SYNTAX      GlobalIndex
   MAX-ACCESS  not-accessible
   STATUS      current
   DESCRIPTION
      "The value of the tlsCntTreeGlobalIndex of the MANAGED OBJECT."
   ::= {pr1646v2EthOamQualityMonitorEntry 10}

pr1646v2EthOamQualityMonitorTableIx OBJECT-TYPE
   SYNTAX      TableIndex
   MAX-ACCESS  not-accessible
   STATUS      current
   DESCRIPTION
      ""
   ::= {pr1646v2EthOamQualityMonitorEntry 11}

pr1646v2EthOamQualityMonitorName OBJECT-TYPE
   SYNTAX      DisplayString
   MAX-ACCESS  read-only
   STATUS      current
   DESCRIPTION
      "Path: ethOam.performance.qualityMonitor.name"
   ::= {pr1646v2EthOamQualityMonitorEntry 385875968}

pr1646v2EthOamQualityMonitorStatus OBJECT-TYPE
   SYNTAX      INTEGER
               {
               run (1),
               runOnDemand (3),
               halted (2),
               cleared (6),
               disabled (8),
               runIdle (9)
               }
   MAX-ACCESS  read-only
   STATUS      current
   DESCRIPTION
      "Path: ethOam.performance.qualityMonitor.status

       Possibilities:
               run   (1)
               runOnDemand   (3)
               halted   (2)
               cleared   (6)
               disabled   (8)
               runIdle   (9)"
   ::= {pr1646v2EthOamQualityMonitorEntry 402653184}

pr1646v2EthOamQualityMonitorMepName OBJECT-TYPE
   SYNTAX      DisplayString
   MAX-ACCESS  read-only
   STATUS      current
   DESCRIPTION
      "Path: ethOam.performance.qualityMonitor.mepName"
   ::= {pr1646v2EthOamQualityMonitorEntry 16777216}

pr1646v2EthOamQualityMonitorMegLevel OBJECT-TYPE
   SYNTAX      Integer32
   MAX-ACCESS  read-only
   STATUS      current
   DESCRIPTION
      "Path: ethOam.performance.qualityMonitor.megLevel"
   ::= {pr1646v2EthOamQualityMonitorEntry 33554432}

pr1646v2EthOamQualityMonitorMegIdMaintDomainName OBJECT-TYPE
   SYNTAX      DisplayString
   MAX-ACCESS  read-only
   STATUS      current
   DESCRIPTION
      "Path: ethOam.performance.qualityMonitor.megId.maintDomainName"
   ::= {pr1646v2EthOamQualityMonitorEntry 50397184}

pr1646v2EthOamQualityMonitorMegIdShortMaName OBJECT-TYPE
   SYNTAX      DisplayString
   MAX-ACCESS  read-only
   STATUS      current
   DESCRIPTION
      "Path: ethOam.performance.qualityMonitor.megId.shortMaName"
   ::= {pr1646v2EthOamQualityMonitorEntry 50462720}

pr1646v2EthOamQualityMonitorMepId OBJECT-TYPE
   SYNTAX      INTEGER
               {
               unknown (8192)
               }
   MAX-ACCESS  read-only
   STATUS      current
   DESCRIPTION
      "Path: ethOam.performance.qualityMonitor.mepId

       Possibilities:
               unknown   (8192)"
   ::= {pr1646v2EthOamQualityMonitorEntry 67108864}

pr1646v2EthOamQualityMonitorMacAddress OBJECT-TYPE
   SYNTAX      OCTET STRING
   MAX-ACCESS  read-only
   STATUS      current
   DESCRIPTION
      "Path: ethOam.performance.qualityMonitor.macAddress

       MAC address."
   ::= {pr1646v2EthOamQualityMonitorEntry 83886080}

pr1646v2EthOamQualityMonitorPriority OBJECT-TYPE
   SYNTAX      Integer32
   MAX-ACCESS  read-only
   STATUS      current
   DESCRIPTION
      "Path: ethOam.performance.qualityMonitor.priority"
   ::= {pr1646v2EthOamQualityMonitorEntry 100663296}

pr1646v2EthOamQualityMonitorType OBJECT-TYPE
   SYNTAX      INTEGER
               {
               loopback (4),
               synthLoss (6),
               delay (7)
               }
   MAX-ACCESS  read-only
   STATUS      current
   DESCRIPTION
      "Path: ethOam.performance.qualityMonitor.type

       Possibilities:
               loopback   (4)
               synthLoss   (6)
               delay   (7)"
   ::= {pr1646v2EthOamQualityMonitorEntry 520093696}

pr1646v2EthOamQualityMonitorNbrTxPckt OBJECT-TYPE
   SYNTAX      Counter32
   MAX-ACCESS  read-only
   STATUS      current
   DESCRIPTION
      "Path: ethOam.performance.qualityMonitor.nbrOfTxPackets

       32 bit unsigned wrappable counter."
   ::= {pr1646v2EthOamQualityMonitorEntry 117440512}

pr1646v2EthOamQualityMonitorNbrRxPckt OBJECT-TYPE
   SYNTAX      Counter32
   MAX-ACCESS  read-only
   STATUS      current
   DESCRIPTION
      "Path: ethOam.performance.qualityMonitor.nbrOfRxPackets

       32 bit unsigned wrappable counter."
   ::= {pr1646v2EthOamQualityMonitorEntry 134217728}

pr1646v2EthOamQualityMonitorError OBJECT-TYPE
   SYNTAX      Counter32
   MAX-ACCESS  read-only
   STATUS      current
   DESCRIPTION
      "Path: ethOam.performance.qualityMonitor.error

       32 bit unsigned wrappable counter."
   ::= {pr1646v2EthOamQualityMonitorEntry 150994944}

pr1646v2EthOamQualityMonitorDelay OBJECT-TYPE
   SYNTAX      Integer32
   MAX-ACCESS  read-only
   STATUS      current
   DESCRIPTION
      "Path: ethOam.performance.qualityMonitor.delay

       unit name = sec
       formula = 1000 / ; 1000 *"
   ::= {pr1646v2EthOamQualityMonitorEntry 167772160}

pr1646v2EthOamQualityMonitorJitter OBJECT-TYPE
   SYNTAX      Integer32
   MAX-ACCESS  read-only
   STATUS      current
   DESCRIPTION
      "Path: ethOam.performance.qualityMonitor.jitter

       unit name = sec
       formula = 1000 / ; 1000 *"
   ::= {pr1646v2EthOamQualityMonitorEntry 184549376}

pr1646v2EthOamQualityMonitorLoss OBJECT-TYPE
   SYNTAX      Counter32
   MAX-ACCESS  read-only
   STATUS      current
   DESCRIPTION
      "Path: ethOam.performance.qualityMonitor.loss

       32 bit unsigned wrappable counter."
   ::= {pr1646v2EthOamQualityMonitorEntry 201326592}

pr1646v2EthOamQualityMonitorLossDelay OBJECT-TYPE
   SYNTAX      Counter32
   MAX-ACCESS  read-only
   STATUS      current
   DESCRIPTION
      "Path: ethOam.performance.qualityMonitor.lossDelay

       32 bit unsigned wrappable counter."
   ::= {pr1646v2EthOamQualityMonitorEntry 218103808}

pr1646v2EthOamQualityMonitorDelayMin OBJECT-TYPE
   SYNTAX      Integer32
   MAX-ACCESS  read-only
   STATUS      current
   DESCRIPTION
      "Path: ethOam.performance.qualityMonitor.delayMin

       unit name = sec
       formula = 1000 / ; 1000 *"
   ::= {pr1646v2EthOamQualityMonitorEntry 234881024}

pr1646v2EthOamQualityMonitorDelayAvrg OBJECT-TYPE
   SYNTAX      Integer32
   MAX-ACCESS  read-only
   STATUS      current
   DESCRIPTION
      "Path: ethOam.performance.qualityMonitor.delayAvrg

       unit name = sec
       formula = 1000 / ; 1000 *"
   ::= {pr1646v2EthOamQualityMonitorEntry 251658240}

pr1646v2EthOamQualityMonitorDelayMax OBJECT-TYPE
   SYNTAX      Integer32
   MAX-ACCESS  read-only
   STATUS      current
   DESCRIPTION
      "Path: ethOam.performance.qualityMonitor.delayMax

       unit name = sec
       formula = 1000 / ; 1000 *"
   ::= {pr1646v2EthOamQualityMonitorEntry 268435456}

pr1646v2EthOamQualityMonitorDelayBinsType OBJECT-TYPE
   SYNTAX      INTEGER
               {
               fd (1),
               fdr (2),
               notInUse (3),
               ifdv (4)
               }
   MAX-ACCESS  read-only
   STATUS      current
   DESCRIPTION
      "Path: ethOam.performance.qualityMonitor.delayBins.type

       Possibilities:
               fd   (1)
               fdr   (2)
               notInUse   (3)
               ifdv   (4)"
   ::= {pr1646v2EthOamQualityMonitorEntry 420937728}

pr1646v2EthOamQualityMonitorDelayBinsMinMin OBJECT-TYPE
   SYNTAX      Counter32
   MAX-ACCESS  read-only
   STATUS      current
   DESCRIPTION
      "Path: ethOam.performance.qualityMonitor.delayBins.minMin

       32 bit unsigned wrappable counter."
   ::= {pr1646v2EthOamQualityMonitorEntry 419495936}

pr1646v2EthOamQualityMonitorDelayBinsMin OBJECT-TYPE
   SYNTAX      Integer32
   MAX-ACCESS  read-only
   STATUS      current
   DESCRIPTION
      "Path: ethOam.performance.qualityMonitor.delayBins.min

       unit name = sec
       formula = 1000 / ; 1000 *"
   ::= {pr1646v2EthOamQualityMonitorEntry 420806656}

pr1646v2EthOamQualityMonitorDelayBinsMinBin1 OBJECT-TYPE
   SYNTAX      Counter32
   MAX-ACCESS  read-only
   STATUS      current
   DESCRIPTION
      "Path: ethOam.performance.qualityMonitor.delayBins.minBin1

       32 bit unsigned wrappable counter."
   ::= {pr1646v2EthOamQualityMonitorEntry 419561472}

pr1646v2EthOamQualityMonitorDelayBinsBin2 OBJECT-TYPE
   SYNTAX      Counter32
   MAX-ACCESS  read-only
   STATUS      current
   DESCRIPTION
      "Path: ethOam.performance.qualityMonitor.delayBins.bin2

       32 bit unsigned wrappable counter."
   ::= {pr1646v2EthOamQualityMonitorEntry 419627008}

pr1646v2EthOamQualityMonitorDelayBinsBin3 OBJECT-TYPE
   SYNTAX      Counter32
   MAX-ACCESS  read-only
   STATUS      current
   DESCRIPTION
      "Path: ethOam.performance.qualityMonitor.delayBins.bin3

       32 bit unsigned wrappable counter."
   ::= {pr1646v2EthOamQualityMonitorEntry 419692544}

pr1646v2EthOamQualityMonitorDelayBinsBin4 OBJECT-TYPE
   SYNTAX      Counter32
   MAX-ACCESS  read-only
   STATUS      current
   DESCRIPTION
      "Path: ethOam.performance.qualityMonitor.delayBins.bin4

       32 bit unsigned wrappable counter."
   ::= {pr1646v2EthOamQualityMonitorEntry 419758080}

pr1646v2EthOamQualityMonitorDelayBinsBin5 OBJECT-TYPE
   SYNTAX      Counter32
   MAX-ACCESS  read-only
   STATUS      current
   DESCRIPTION
      "Path: ethOam.performance.qualityMonitor.delayBins.bin5

       32 bit unsigned wrappable counter."
   ::= {pr1646v2EthOamQualityMonitorEntry 419823616}

pr1646v2EthOamQualityMonitorDelayBinsBin6 OBJECT-TYPE
   SYNTAX      Counter32
   MAX-ACCESS  read-only
   STATUS      current
   DESCRIPTION
      "Path: ethOam.performance.qualityMonitor.delayBins.bin6

       32 bit unsigned wrappable counter."
   ::= {pr1646v2EthOamQualityMonitorEntry 419889152}

pr1646v2EthOamQualityMonitorDelayBinsBin7 OBJECT-TYPE
   SYNTAX      Counter32
   MAX-ACCESS  read-only
   STATUS      current
   DESCRIPTION
      "Path: ethOam.performance.qualityMonitor.delayBins.bin7

       32 bit unsigned wrappable counter."
   ::= {pr1646v2EthOamQualityMonitorEntry 419954688}

pr1646v2EthOamQualityMonitorDelayBinsMaxBin8 OBJECT-TYPE
   SYNTAX      Counter32
   MAX-ACCESS  read-only
   STATUS      current
   DESCRIPTION
      "Path: ethOam.performance.qualityMonitor.delayBins.maxBin8

       32 bit unsigned wrappable counter."
   ::= {pr1646v2EthOamQualityMonitorEntry 420020224}

pr1646v2EthOamQualityMonitorDelayBinsMax OBJECT-TYPE
   SYNTAX      Integer32
   MAX-ACCESS  read-only
   STATUS      current
   DESCRIPTION
      "Path: ethOam.performance.qualityMonitor.delayBins.max

       unit name = sec
       formula = 1000 / ; 1000 *"
   ::= {pr1646v2EthOamQualityMonitorEntry 420872192}

pr1646v2EthOamQualityMonitorDelayBinsPlusMax OBJECT-TYPE
   SYNTAX      Counter32
   MAX-ACCESS  read-only
   STATUS      current
   DESCRIPTION
      "Path: ethOam.performance.qualityMonitor.delayBins.plusMax

       32 bit unsigned wrappable counter."
   ::= {pr1646v2EthOamQualityMonitorEntry 420085760}

pr1646v2EthOamQualityMonitorJitterNegMax OBJECT-TYPE
   SYNTAX      Integer32
   MAX-ACCESS  read-only
   STATUS      current
   DESCRIPTION
      "Path: ethOam.performance.qualityMonitor.jitterNegMax

       unit name = sec
       formula = 1000 / ; 1000 *"
   ::= {pr1646v2EthOamQualityMonitorEntry 285212672}

pr1646v2EthOamQualityMonitorJitterAvrg OBJECT-TYPE
   SYNTAX      Integer32
   MAX-ACCESS  read-only
   STATUS      current
   DESCRIPTION
      "Path: ethOam.performance.qualityMonitor.jitterAvrg

       unit name = sec
       formula = 1000 / ; 1000 *"
   ::= {pr1646v2EthOamQualityMonitorEntry 301989888}

pr1646v2EthOamQualityMonitorJitterPosMax OBJECT-TYPE
   SYNTAX      Integer32
   MAX-ACCESS  read-only
   STATUS      current
   DESCRIPTION
      "Path: ethOam.performance.qualityMonitor.jitterPosMax

       unit name = sec
       formula = 1000 / ; 1000 *"
   ::= {pr1646v2EthOamQualityMonitorEntry 318767104}

pr1646v2EthOamQualityMonitorJitterBinsType OBJECT-TYPE
   SYNTAX      INTEGER
               {
               fd (1),
               fdr (2),
               notInUse (3),
               ifdv (4)
               }
   MAX-ACCESS  read-only
   STATUS      current
   DESCRIPTION
      "Path: ethOam.performance.qualityMonitor.jitterBins.type

       Possibilities:
               fd   (1)
               fdr   (2)
               notInUse   (3)
               ifdv   (4)"
   ::= {pr1646v2EthOamQualityMonitorEntry 437714944}

pr1646v2EthOamQualityMonitorJitterBinsMinMin OBJECT-TYPE
   SYNTAX      Counter32
   MAX-ACCESS  read-only
   STATUS      current
   DESCRIPTION
      "Path: ethOam.performance.qualityMonitor.jitterBins.minMin

       32 bit unsigned wrappable counter."
   ::= {pr1646v2EthOamQualityMonitorEntry 436273152}

pr1646v2EthOamQualityMonitorJitterBinsMin OBJECT-TYPE
   SYNTAX      Integer32
   MAX-ACCESS  read-only
   STATUS      current
   DESCRIPTION
      "Path: ethOam.performance.qualityMonitor.jitterBins.min

       unit name = sec
       formula = 1000 / ; 1000 *"
   ::= {pr1646v2EthOamQualityMonitorEntry 437583872}

pr1646v2EthOamQualityMonitorJitterBinsMinBin1 OBJECT-TYPE
   SYNTAX      Counter32
   MAX-ACCESS  read-only
   STATUS      current
   DESCRIPTION
      "Path: ethOam.performance.qualityMonitor.jitterBins.minBin1

       32 bit unsigned wrappable counter."
   ::= {pr1646v2EthOamQualityMonitorEntry 436338688}

pr1646v2EthOamQualityMonitorJitterBinsBin2 OBJECT-TYPE
   SYNTAX      Counter32
   MAX-ACCESS  read-only
   STATUS      current
   DESCRIPTION
      "Path: ethOam.performance.qualityMonitor.jitterBins.bin2

       32 bit unsigned wrappable counter."
   ::= {pr1646v2EthOamQualityMonitorEntry 436404224}

pr1646v2EthOamQualityMonitorJitterBinsBin3 OBJECT-TYPE
   SYNTAX      Counter32
   MAX-ACCESS  read-only
   STATUS      current
   DESCRIPTION
      "Path: ethOam.performance.qualityMonitor.jitterBins.bin3

       32 bit unsigned wrappable counter."
   ::= {pr1646v2EthOamQualityMonitorEntry 436469760}

pr1646v2EthOamQualityMonitorJitterBinsBin4 OBJECT-TYPE
   SYNTAX      Counter32
   MAX-ACCESS  read-only
   STATUS      current
   DESCRIPTION
      "Path: ethOam.performance.qualityMonitor.jitterBins.bin4

       32 bit unsigned wrappable counter."
   ::= {pr1646v2EthOamQualityMonitorEntry 436535296}

pr1646v2EthOamQualityMonitorJitterBinsBin5 OBJECT-TYPE
   SYNTAX      Counter32
   MAX-ACCESS  read-only
   STATUS      current
   DESCRIPTION
      "Path: ethOam.performance.qualityMonitor.jitterBins.bin5

       32 bit unsigned wrappable counter."
   ::= {pr1646v2EthOamQualityMonitorEntry 436600832}

pr1646v2EthOamQualityMonitorJitterBinsBin6 OBJECT-TYPE
   SYNTAX      Counter32
   MAX-ACCESS  read-only
   STATUS      current
   DESCRIPTION
      "Path: ethOam.performance.qualityMonitor.jitterBins.bin6

       32 bit unsigned wrappable counter."
   ::= {pr1646v2EthOamQualityMonitorEntry 436666368}

pr1646v2EthOamQualityMonitorJitterBinsBin7 OBJECT-TYPE
   SYNTAX      Counter32
   MAX-ACCESS  read-only
   STATUS      current
   DESCRIPTION
      "Path: ethOam.performance.qualityMonitor.jitterBins.bin7

       32 bit unsigned wrappable counter."
   ::= {pr1646v2EthOamQualityMonitorEntry 436731904}

pr1646v2EthOamQualityMonitorJitterBinsMaxBin8 OBJECT-TYPE
   SYNTAX      Counter32
   MAX-ACCESS  read-only
   STATUS      current
   DESCRIPTION
      "Path: ethOam.performance.qualityMonitor.jitterBins.maxBin8

       32 bit unsigned wrappable counter."
   ::= {pr1646v2EthOamQualityMonitorEntry 436797440}

pr1646v2EthOamQualityMonitorJitterBinsMax OBJECT-TYPE
   SYNTAX      Integer32
   MAX-ACCESS  read-only
   STATUS      current
   DESCRIPTION
      "Path: ethOam.performance.qualityMonitor.jitterBins.max

       unit name = sec
       formula = 1000 / ; 1000 *"
   ::= {pr1646v2EthOamQualityMonitorEntry 437649408}

pr1646v2EthOamQualityMonitorJitterBinsPlusMax OBJECT-TYPE
   SYNTAX      Counter32
   MAX-ACCESS  read-only
   STATUS      current
   DESCRIPTION
      "Path: ethOam.performance.qualityMonitor.jitterBins.plusMax

       32 bit unsigned wrappable counter."
   ::= {pr1646v2EthOamQualityMonitorEntry 436862976}

pr1646v2EthOamQualityMonitorUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: ethOam.performance.qualityMonitor.upDown.status

       Possibilities:
               notInUse   (3)
               onlyJitter   (1)
               jitterAndLoss   (2)
               all   (4)
               onlyLoss   (8)"
   ::= {pr1646v2EthOamQualityMonitorEntry 504627200}

pr1646v2EthOamQualityMonitorUpDownLossUp OBJECT-TYPE
   SYNTAX      Counter32
   MAX-ACCESS  read-only
   STATUS      current
   DESCRIPTION
      "Path: ethOam.performance.qualityMonitor.upDown.lossUp

       32 bit unsigned wrappable counter."
   ::= {pr1646v2EthOamQualityMonitorEntry 503971840}

pr1646v2EthOamQualityMonitorUpDownLossDelayUp OBJECT-TYPE
   SYNTAX      Counter32
   MAX-ACCESS  read-only
   STATUS      current
   DESCRIPTION
      "Path: ethOam.performance.qualityMonitor.upDown.lossDelayUp

       32 bit unsigned wrappable counter."
   ::= {pr1646v2EthOamQualityMonitorEntry 504037376}

pr1646v2EthOamQualityMonitorUpDownDelayUpMin OBJECT-TYPE
   SYNTAX      Integer32
   MAX-ACCESS  read-only
   STATUS      current
   DESCRIPTION
      "Path: ethOam.performance.qualityMonitor.upDown.delayUpMin

       unit name = sec
       formula = 1000 / ; 1000 *"
   ::= {pr1646v2EthOamQualityMonitorEntry 505282560}

pr1646v2EthOamQualityMonitorUpDownDelayUpAvrg OBJECT-TYPE
   SYNTAX      Integer32
   MAX-ACCESS  read-only
   STATUS      current
   DESCRIPTION
      "Path: ethOam.performance.qualityMonitor.upDown.delayUpAvrg

       unit name = sec
       formula = 1000 / ; 1000 *"
   ::= {pr1646v2EthOamQualityMonitorEntry 505348096}

pr1646v2EthOamQualityMonitorUpDownDelayUpMax OBJECT-TYPE
   SYNTAX      Integer32
   MAX-ACCESS  read-only
   STATUS      current
   DESCRIPTION
      "Path: ethOam.performance.qualityMonitor.upDown.delayUpMax

       unit name = sec
       formula = 1000 / ; 1000 *"
   ::= {pr1646v2EthOamQualityMonitorEntry 505413632}

pr1646v2EthOamQualityMonitorUpDownDelayUpBinsType OBJECT-TYPE
   SYNTAX      INTEGER
               {
               fd (1),
               fdr (2),
               notInUse (3),
               ifdv (4)
               }
   MAX-ACCESS  read-only
   STATUS      current
   DESCRIPTION
      "Path: ethOam.performance.qualityMonitor.upDown.delayUpBins.type

       Possibilities:
               fd   (1)
               fdr   (2)
               notInUse   (3)
               ifdv   (4)"
   ::= {pr1646v2EthOamQualityMonitorEntry 505943808}

pr1646v2EthOamQualityMonitorUpDownDelayUpBinsMinMin OBJECT-TYPE
   SYNTAX      Counter32
   MAX-ACCESS  read-only
   STATUS      current
   DESCRIPTION
      "Path: ethOam.performance.qualityMonitor.upDown.delayUpBins.minMin

       32 bit unsigned wrappable counter."
   ::= {pr1646v2EthOamQualityMonitorEntry 505938176}

pr1646v2EthOamQualityMonitorUpDownDelayUpBinsMin OBJECT-TYPE
   SYNTAX      Integer32
   MAX-ACCESS  read-only
   STATUS      current
   DESCRIPTION
      "Path: ethOam.performance.qualityMonitor.upDown.delayUpBins.min

       unit name = sec
       formula = 1000 / ; 1000 *"
   ::= {pr1646v2EthOamQualityMonitorEntry 505943296}

pr1646v2EthOamQualityMonitorUpDownDelayUpBinsMinBin1 OBJECT-TYPE
   SYNTAX      Counter32
   MAX-ACCESS  read-only
   STATUS      current
   DESCRIPTION
      "Path: ethOam.performance.qualityMonitor.upDown.delayUpBins.minBin1

       32 bit unsigned wrappable counter."
   ::= {pr1646v2EthOamQualityMonitorEntry 505938432}

pr1646v2EthOamQualityMonitorUpDownDelayUpBinsBin2 OBJECT-TYPE
   SYNTAX      Counter32
   MAX-ACCESS  read-only
   STATUS      current
   DESCRIPTION
      "Path: ethOam.performance.qualityMonitor.upDown.delayUpBins.bin2

       32 bit unsigned wrappable counter."
   ::= {pr1646v2EthOamQualityMonitorEntry 505938688}

pr1646v2EthOamQualityMonitorUpDownDelayUpBinsBin3 OBJECT-TYPE
   SYNTAX      Counter32
   MAX-ACCESS  read-only
   STATUS      current
   DESCRIPTION
      "Path: ethOam.performance.qualityMonitor.upDown.delayUpBins.bin3

       32 bit unsigned wrappable counter."
   ::= {pr1646v2EthOamQualityMonitorEntry 505938944}

pr1646v2EthOamQualityMonitorUpDownDelayUpBinsBin4 OBJECT-TYPE
   SYNTAX      Counter32
   MAX-ACCESS  read-only
   STATUS      current
   DESCRIPTION
      "Path: ethOam.performance.qualityMonitor.upDown.delayUpBins.bin4

       32 bit unsigned wrappable counter."
   ::= {pr1646v2EthOamQualityMonitorEntry 505939200}

pr1646v2EthOamQualityMonitorUpDownDelayUpBinsBin5 OBJECT-TYPE
   SYNTAX      Counter32
   MAX-ACCESS  read-only
   STATUS      current
   DESCRIPTION
      "Path: ethOam.performance.qualityMonitor.upDown.delayUpBins.bin5

       32 bit unsigned wrappable counter."
   ::= {pr1646v2EthOamQualityMonitorEntry 505939456}

pr1646v2EthOamQualityMonitorUpDownDelayUpBinsBin6 OBJECT-TYPE
   SYNTAX      Counter32
   MAX-ACCESS  read-only
   STATUS      current
   DESCRIPTION
      "Path: ethOam.performance.qualityMonitor.upDown.delayUpBins.bin6

       32 bit unsigned wrappable counter."
   ::= {pr1646v2EthOamQualityMonitorEntry 505939712}

pr1646v2EthOamQualityMonitorUpDownDelayUpBinsBin7 OBJECT-TYPE
   SYNTAX      Counter32
   MAX-ACCESS  read-only
   STATUS      current
   DESCRIPTION
      "Path: ethOam.performance.qualityMonitor.upDown.delayUpBins.bin7

       32 bit unsigned wrappable counter."
   ::= {pr1646v2EthOamQualityMonitorEntry 505939968}

pr1646v2EthOamQualityMonitorUpDownDelayUpBinsMaxBin8 OBJECT-TYPE
   SYNTAX      Counter32
   MAX-ACCESS  read-only
   STATUS      current
   DESCRIPTION
      "Path: ethOam.performance.qualityMonitor.upDown.delayUpBins.maxBin8

       32 bit unsigned wrappable counter."
   ::= {pr1646v2EthOamQualityMonitorEntry 505940224}

pr1646v2EthOamQualityMonitorUpDownDelayUpBinsMax OBJECT-TYPE
   SYNTAX      Integer32
   MAX-ACCESS  read-only
   STATUS      current
   DESCRIPTION
      "Path: ethOam.performance.qualityMonitor.upDown.delayUpBins.max

       unit name = sec
       formula = 1000 / ; 1000 *"
   ::= {pr1646v2EthOamQualityMonitorEntry 505943552}

pr1646v2EthOamQualityMonitorUpDownDelayUpBinsPlusMax OBJECT-TYPE
   SYNTAX      Counter32
   MAX-ACCESS  read-only
   STATUS      current
   DESCRIPTION
      "Path: ethOam.performance.qualityMonitor.upDown.delayUpBins.plusMax

       32 bit unsigned wrappable counter."
   ::= {pr1646v2EthOamQualityMonitorEntry 505940480}

pr1646v2EthOamQualityMonitorUpDownJitterUp OBJECT-TYPE
   SYNTAX      Integer32
   MAX-ACCESS  read-only
   STATUS      current
   DESCRIPTION
      "Path: ethOam.performance.qualityMonitor.upDown.jitterUp

       unit name = sec
       formula = 1000 / ; 1000 *"
   ::= {pr1646v2EthOamQualityMonitorEntry 503775232}

pr1646v2EthOamQualityMonitorUpDownJitterUpNegMax OBJECT-TYPE
   SYNTAX      Integer32
   MAX-ACCESS  read-only
   STATUS      current
   DESCRIPTION
      "Path: ethOam.performance.qualityMonitor.upDown.jitterUpNegMax

       unit name = sec
       formula = 1000 / ; 1000 *"
   ::= {pr1646v2EthOamQualityMonitorEntry 503382016}

pr1646v2EthOamQualityMonitorUpDownJitterUpAvrg OBJECT-TYPE
   SYNTAX      Integer32
   MAX-ACCESS  read-only
   STATUS      current
   DESCRIPTION
      "Path: ethOam.performance.qualityMonitor.upDown.jitterUpAvrg

       unit name = sec
       formula = 1000 / ; 1000 *"
   ::= {pr1646v2EthOamQualityMonitorEntry 503447552}

pr1646v2EthOamQualityMonitorUpDownJitterUpPosMax OBJECT-TYPE
   SYNTAX      Integer32
   MAX-ACCESS  read-only
   STATUS      current
   DESCRIPTION
      "Path: ethOam.performance.qualityMonitor.upDown.jitterUpPosMax

       unit name = sec
       formula = 1000 / ; 1000 *"
   ::= {pr1646v2EthOamQualityMonitorEntry 503513088}

pr1646v2EthOamQualityMonitorUpDownJitterUpBinsType OBJECT-TYPE
   SYNTAX      INTEGER
               {
               fd (1),
               fdr (2),
               notInUse (3),
               ifdv (4)
               }
   MAX-ACCESS  read-only
   STATUS      current
   DESCRIPTION
      "Path: ethOam.performance.qualityMonitor.upDown.jitterUpBins.type

       Possibilities:
               fd   (1)
               fdr   (2)
               notInUse   (3)
               ifdv   (4)"
   ::= {pr1646v2EthOamQualityMonitorEntry 506074880}

pr1646v2EthOamQualityMonitorUpDownJitterUpBinsMinMin OBJECT-TYPE
   SYNTAX      Counter32
   MAX-ACCESS  read-only
   STATUS      current
   DESCRIPTION
      "Path: ethOam.performance.qualityMonitor.upDown.jitterUpBins.minMin

       32 bit unsigned wrappable counter."
   ::= {pr1646v2EthOamQualityMonitorEntry 506069248}

pr1646v2EthOamQualityMonitorUpDownJitterUpBinsMin OBJECT-TYPE
   SYNTAX      Integer32
   MAX-ACCESS  read-only
   STATUS      current
   DESCRIPTION
      "Path: ethOam.performance.qualityMonitor.upDown.jitterUpBins.min

       unit name = sec
       formula = 1000 / ; 1000 *"
   ::= {pr1646v2EthOamQualityMonitorEntry 506074368}

pr1646v2EthOamQualityMonitorUpDownJitterUpBinsMinBin1 OBJECT-TYPE
   SYNTAX      Counter32
   MAX-ACCESS  read-only
   STATUS      current
   DESCRIPTION
      "Path: ethOam.performance.qualityMonitor.upDown.jitterUpBins.minBin1

       32 bit unsigned wrappable counter."
   ::= {pr1646v2EthOamQualityMonitorEntry 506069504}

pr1646v2EthOamQualityMonitorUpDownJitterUpBinsBin2 OBJECT-TYPE
   SYNTAX      Counter32
   MAX-ACCESS  read-only
   STATUS      current
   DESCRIPTION
      "Path: ethOam.performance.qualityMonitor.upDown.jitterUpBins.bin2

       32 bit unsigned wrappable counter."
   ::= {pr1646v2EthOamQualityMonitorEntry 506069760}

pr1646v2EthOamQualityMonitorUpDownJitterUpBinsBin3 OBJECT-TYPE
   SYNTAX      Counter32
   MAX-ACCESS  read-only
   STATUS      current
   DESCRIPTION
      "Path: ethOam.performance.qualityMonitor.upDown.jitterUpBins.bin3

       32 bit unsigned wrappable counter."
   ::= {pr1646v2EthOamQualityMonitorEntry 506070016}

pr1646v2EthOamQualityMonitorUpDownJitterUpBinsBin4 OBJECT-TYPE
   SYNTAX      Counter32
   MAX-ACCESS  read-only
   STATUS      current
   DESCRIPTION
      "Path: ethOam.performance.qualityMonitor.upDown.jitterUpBins.bin4

       32 bit unsigned wrappable counter."
   ::= {pr1646v2EthOamQualityMonitorEntry 506070272}

pr1646v2EthOamQualityMonitorUpDownJitterUpBinsBin5 OBJECT-TYPE
   SYNTAX      Counter32
   MAX-ACCESS  read-only
   STATUS      current
   DESCRIPTION
      "Path: ethOam.performance.qualityMonitor.upDown.jitterUpBins.bin5

       32 bit unsigned wrappable counter."
   ::= {pr1646v2EthOamQualityMonitorEntry 506070528}

pr1646v2EthOamQualityMonitorUpDownJitterUpBinsBin6 OBJECT-TYPE
   SYNTAX      Counter32
   MAX-ACCESS  read-only
   STATUS      current
   DESCRIPTION
      "Path: ethOam.performance.qualityMonitor.upDown.jitterUpBins.bin6

       32 bit unsigned wrappable counter."
   ::= {pr1646v2EthOamQualityMonitorEntry 506070784}

pr1646v2EthOamQualityMonitorUpDownJitterUpBinsBin7 OBJECT-TYPE
   SYNTAX      Counter32
   MAX-ACCESS  read-only
   STATUS      current
   DESCRIPTION
      "Path: ethOam.performance.qualityMonitor.upDown.jitterUpBins.bin7

       32 bit unsigned wrappable counter."
   ::= {pr1646v2EthOamQualityMonitorEntry 506071040}

pr1646v2EthOamQualityMonitorUpDownJitterUpBinsMaxBin8 OBJECT-TYPE
   SYNTAX      Counter32
   MAX-ACCESS  read-only
   STATUS      current
   DESCRIPTION
      "Path: ethOam.performance.qualityMonitor.upDown.jitterUpBins.maxBin8

       32 bit unsigned wrappable counter."
   ::= {pr1646v2EthOamQualityMonitorEntry 506071296}

pr1646v2EthOamQualityMonitorUpDownJitterUpBinsMax OBJECT-TYPE
   SYNTAX      Integer32
   MAX-ACCESS  read-only
   STATUS      current
   DESCRIPTION
      "Path: ethOam.performance.qualityMonitor.upDown.jitterUpBins.max

       unit name = sec
       formula = 1000 / ; 1000 *"
   ::= {pr1646v2EthOamQualityMonitorEntry 506074624}

pr1646v2EthOamQualityMonitorUpDownJitterUpBinsPlusMax OBJECT-TYPE
   SYNTAX      Counter32
   MAX-ACCESS  read-only
   STATUS      current
   DESCRIPTION
      "Path: ethOam.performance.qualityMonitor.upDown.jitterUpBins.plusMax

       32 bit unsigned wrappable counter."
   ::= {pr1646v2EthOamQualityMonitorEntry 506071552}

pr1646v2EthOamQualityMonitorUpDownLossDown OBJECT-TYPE
   SYNTAX      Counter32
   MAX-ACCESS  read-only
   STATUS      current
   DESCRIPTION
      "Path: ethOam.performance.qualityMonitor.upDown.lossDown

       32 bit unsigned wrappable counter."
   ::= {pr1646v2EthOamQualityMonitorEntry 504102912}

pr1646v2EthOamQualityMonitorUpDownLossDelayDown OBJECT-TYPE
   SYNTAX      Counter32
   MAX-ACCESS  read-only
   STATUS      current
   DESCRIPTION
      "Path: ethOam.performance.qualityMonitor.upDown.lossDelayDown

       32 bit unsigned wrappable counter."
   ::= {pr1646v2EthOamQualityMonitorEntry 504168448}

pr1646v2EthOamQualityMonitorUpDownDelayDownMin OBJECT-TYPE
   SYNTAX      Integer32
   MAX-ACCESS  read-only
   STATUS      current
   DESCRIPTION
      "Path: ethOam.performance.qualityMonitor.upDown.delayDownMin

       unit name = sec
       formula = 1000 / ; 1000 *"
   ::= {pr1646v2EthOamQualityMonitorEntry 505610240}

pr1646v2EthOamQualityMonitorUpDownDelayDownAvrg OBJECT-TYPE
   SYNTAX      Integer32
   MAX-ACCESS  read-only
   STATUS      current
   DESCRIPTION
      "Path: ethOam.performance.qualityMonitor.upDown.delayDownAvrg

       unit name = sec
       formula = 1000 / ; 1000 *"
   ::= {pr1646v2EthOamQualityMonitorEntry 505675776}

pr1646v2EthOamQualityMonitorUpDownDelayDownMax OBJECT-TYPE
   SYNTAX      Integer32
   MAX-ACCESS  read-only
   STATUS      current
   DESCRIPTION
      "Path: ethOam.performance.qualityMonitor.upDown.delayDownMax

       unit name = sec
       formula = 1000 / ; 1000 *"
   ::= {pr1646v2EthOamQualityMonitorEntry 505741312}

pr1646v2EthOamQualityMonitorUpDownDelayDownBinsType OBJECT-TYPE
   SYNTAX      INTEGER
               {
               fd (1),
               fdr (2),
               notInUse (3),
               ifdv (4)
               }
   MAX-ACCESS  read-only
   STATUS      current
   DESCRIPTION
      "Path: ethOam.performance.qualityMonitor.upDown.delayDownBins.type

       Possibilities:
               fd   (1)
               fdr   (2)
               notInUse   (3)
               ifdv   (4)"
   ::= {pr1646v2EthOamQualityMonitorEntry 506009344}

pr1646v2EthOamQualityMonitorUpDownDelayDownBinsMinMin OBJECT-TYPE
   SYNTAX      Counter32
   MAX-ACCESS  read-only
   STATUS      current
   DESCRIPTION
      "Path: ethOam.performance.qualityMonitor.upDown.delayDownBins.minMin

       32 bit unsigned wrappable counter."
   ::= {pr1646v2EthOamQualityMonitorEntry 506003712}

pr1646v2EthOamQualityMonitorUpDownDelayDownBinsMin OBJECT-TYPE
   SYNTAX      Integer32
   MAX-ACCESS  read-only
   STATUS      current
   DESCRIPTION
      "Path: ethOam.performance.qualityMonitor.upDown.delayDownBins.min

       unit name = sec
       formula = 1000 / ; 1000 *"
   ::= {pr1646v2EthOamQualityMonitorEntry 506008832}

pr1646v2EthOamQualityMonitorUpDownDelayDownBinsMinBin1 OBJECT-TYPE
   SYNTAX      Counter32
   MAX-ACCESS  read-only
   STATUS      current
   DESCRIPTION
      "Path: ethOam.performance.qualityMonitor.upDown.delayDownBins.minBin1

       32 bit unsigned wrappable counter."
   ::= {pr1646v2EthOamQualityMonitorEntry 506003968}

pr1646v2EthOamQualityMonitorUpDownDelayDownBinsBin2 OBJECT-TYPE
   SYNTAX      Counter32
   MAX-ACCESS  read-only
   STATUS      current
   DESCRIPTION
      "Path: ethOam.performance.qualityMonitor.upDown.delayDownBins.bin2

       32 bit unsigned wrappable counter."
   ::= {pr1646v2EthOamQualityMonitorEntry 506004224}

pr1646v2EthOamQualityMonitorUpDownDelayDownBinsBin3 OBJECT-TYPE
   SYNTAX      Counter32
   MAX-ACCESS  read-only
   STATUS      current
   DESCRIPTION
      "Path: ethOam.performance.qualityMonitor.upDown.delayDownBins.bin3

       32 bit unsigned wrappable counter."
   ::= {pr1646v2EthOamQualityMonitorEntry 506004480}

pr1646v2EthOamQualityMonitorUpDownDelayDownBinsBin4 OBJECT-TYPE
   SYNTAX      Counter32
   MAX-ACCESS  read-only
   STATUS      current
   DESCRIPTION
      "Path: ethOam.performance.qualityMonitor.upDown.delayDownBins.bin4

       32 bit unsigned wrappable counter."
   ::= {pr1646v2EthOamQualityMonitorEntry 506004736}

pr1646v2EthOamQualityMonitorUpDownDelayDownBinsBin5 OBJECT-TYPE
   SYNTAX      Counter32
   MAX-ACCESS  read-only
   STATUS      current
   DESCRIPTION
      "Path: ethOam.performance.qualityMonitor.upDown.delayDownBins.bin5

       32 bit unsigned wrappable counter."
   ::= {pr1646v2EthOamQualityMonitorEntry 506004992}

pr1646v2EthOamQualityMonitorUpDownDelayDownBinsBin6 OBJECT-TYPE
   SYNTAX      Counter32
   MAX-ACCESS  read-only
   STATUS      current
   DESCRIPTION
      "Path: ethOam.performance.qualityMonitor.upDown.delayDownBins.bin6

       32 bit unsigned wrappable counter."
   ::= {pr1646v2EthOamQualityMonitorEntry 506005248}

pr1646v2EthOamQualityMonitorUpDownDelayDownBinsBin7 OBJECT-TYPE
   SYNTAX      Counter32
   MAX-ACCESS  read-only
   STATUS      current
   DESCRIPTION
      "Path: ethOam.performance.qualityMonitor.upDown.delayDownBins.bin7

       32 bit unsigned wrappable counter."
   ::= {pr1646v2EthOamQualityMonitorEntry 506005504}

pr1646v2EthOamQualityMonitorUpDownDelayDownBinsMaxBin8 OBJECT-TYPE
   SYNTAX      Counter32
   MAX-ACCESS  read-only
   STATUS      current
   DESCRIPTION
      "Path: ethOam.performance.qualityMonitor.upDown.delayDownBins.maxBin8

       32 bit unsigned wrappable counter."
   ::= {pr1646v2EthOamQualityMonitorEntry 506005760}

pr1646v2EthOamQualityMonitorUpDownDelayDownBinsMax OBJECT-TYPE
   SYNTAX      Integer32
   MAX-ACCESS  read-only
   STATUS      current
   DESCRIPTION
      "Path: ethOam.performance.qualityMonitor.upDown.delayDownBins.max

       unit name = sec
       formula = 1000 / ; 1000 *"
   ::= {pr1646v2EthOamQualityMonitorEntry 506009088}

pr1646v2EthOamQualityMonitorUpDownDelayDownBinsPlusMax OBJECT-TYPE
   SYNTAX      Counter32
   MAX-ACCESS  read-only
   STATUS      current
   DESCRIPTION
      "Path: ethOam.performance.qualityMonitor.upDown.delayDownBins.plusMax

       32 bit unsigned wrappable counter."
   ::= {pr1646v2EthOamQualityMonitorEntry 506006016}

pr1646v2EthOamQualityMonitorUpDownJitterDown OBJECT-TYPE
   SYNTAX      Integer32
   MAX-ACCESS  read-only
   STATUS      current
   DESCRIPTION
      "Path: ethOam.performance.qualityMonitor.upDown.jitterDown

       unit name = sec
       formula = 1000 / ; 1000 *"
   ::= {pr1646v2EthOamQualityMonitorEntry 503840768}

pr1646v2EthOamQualityMonitorUpDownJitterDownNegMax OBJECT-TYPE
   SYNTAX      Integer32
   MAX-ACCESS  read-only
   STATUS      current
   DESCRIPTION
      "Path: ethOam.performance.qualityMonitor.upDown.jitterDownNegMax

       unit name = sec
       formula = 1000 / ; 1000 *"
   ::= {pr1646v2EthOamQualityMonitorEntry 503578624}

pr1646v2EthOamQualityMonitorUpDownJitterDownAvrg OBJECT-TYPE
   SYNTAX      Integer32
   MAX-ACCESS  read-only
   STATUS      current
   DESCRIPTION
      "Path: ethOam.performance.qualityMonitor.upDown.jitterDownAvrg

       unit name = sec
       formula = 1000 / ; 1000 *"
   ::= {pr1646v2EthOamQualityMonitorEntry 503644160}

pr1646v2EthOamQualityMonitorUpDownJitterDownPosMax OBJECT-TYPE
   SYNTAX      Integer32
   MAX-ACCESS  read-only
   STATUS      current
   DESCRIPTION
      "Path: ethOam.performance.qualityMonitor.upDown.jitterDownPosMax

       unit name = sec
       formula = 1000 / ; 1000 *"
   ::= {pr1646v2EthOamQualityMonitorEntry 503709696}

pr1646v2EthOamQualityMonitorUpDownJitterDownBinsType OBJECT-TYPE
   SYNTAX      INTEGER
               {
               fd (1),
               fdr (2),
               notInUse (3),
               ifdv (4)
               }
   MAX-ACCESS  read-only
   STATUS      current
   DESCRIPTION
      "Path: ethOam.performance.qualityMonitor.upDown.jitterDownBins.type

       Possibilities:
               fd   (1)
               fdr   (2)
               notInUse   (3)
               ifdv   (4)"
   ::= {pr1646v2EthOamQualityMonitorEntry 506205952}

pr1646v2EthOamQualityMonitorUpDownJitterDownBinsMinMin OBJECT-TYPE
   SYNTAX      Counter32
   MAX-ACCESS  read-only
   STATUS      current
   DESCRIPTION
      "Path: ethOam.performance.qualityMonitor.upDown.jitterDownBins.minMin

       32 bit unsigned wrappable counter."
   ::= {pr1646v2EthOamQualityMonitorEntry 506200320}

pr1646v2EthOamQualityMonitorUpDownJitterDownBinsMin OBJECT-TYPE
   SYNTAX      Integer32
   MAX-ACCESS  read-only
   STATUS      current
   DESCRIPTION
      "Path: ethOam.performance.qualityMonitor.upDown.jitterDownBins.min

       unit name = sec
       formula = 1000 / ; 1000 *"
   ::= {pr1646v2EthOamQualityMonitorEntry 506205440}

pr1646v2EthOamQualityMonitorUpDownJitterDownBinsMinBin1 OBJECT-TYPE
   SYNTAX      Counter32
   MAX-ACCESS  read-only
   STATUS      current
   DESCRIPTION
      "Path: ethOam.performance.qualityMonitor.upDown.jitterDownBins.minBin1

       32 bit unsigned wrappable counter."
   ::= {pr1646v2EthOamQualityMonitorEntry 506200576}

pr1646v2EthOamQualityMonitorUpDownJitterDownBinsBin2 OBJECT-TYPE
   SYNTAX      Counter32
   MAX-ACCESS  read-only
   STATUS      current
   DESCRIPTION
      "Path: ethOam.performance.qualityMonitor.upDown.jitterDownBins.bin2

       32 bit unsigned wrappable counter."
   ::= {pr1646v2EthOamQualityMonitorEntry 506200832}

pr1646v2EthOamQualityMonitorUpDownJitterDownBinsBin3 OBJECT-TYPE
   SYNTAX      Counter32
   MAX-ACCESS  read-only
   STATUS      current
   DESCRIPTION
      "Path: ethOam.performance.qualityMonitor.upDown.jitterDownBins.bin3

       32 bit unsigned wrappable counter."
   ::= {pr1646v2EthOamQualityMonitorEntry 506201088}

pr1646v2EthOamQualityMonitorUpDownJitterDownBinsBin4 OBJECT-TYPE
   SYNTAX      Counter32
   MAX-ACCESS  read-only
   STATUS      current
   DESCRIPTION
      "Path: ethOam.performance.qualityMonitor.upDown.jitterDownBins.bin4

       32 bit unsigned wrappable counter."
   ::= {pr1646v2EthOamQualityMonitorEntry 506201344}

pr1646v2EthOamQualityMonitorUpDownJitterDownBinsBin5 OBJECT-TYPE
   SYNTAX      Counter32
   MAX-ACCESS  read-only
   STATUS      current
   DESCRIPTION
      "Path: ethOam.performance.qualityMonitor.upDown.jitterDownBins.bin5

       32 bit unsigned wrappable counter."
   ::= {pr1646v2EthOamQualityMonitorEntry 506201600}

pr1646v2EthOamQualityMonitorUpDownJitterDownBinsBin6 OBJECT-TYPE
   SYNTAX      Counter32
   MAX-ACCESS  read-only
   STATUS      current
   DESCRIPTION
      "Path: ethOam.performance.qualityMonitor.upDown.jitterDownBins.bin6

       32 bit unsigned wrappable counter."
   ::= {pr1646v2EthOamQualityMonitorEntry 506201856}

pr1646v2EthOamQualityMonitorUpDownJitterDownBinsBin7 OBJECT-TYPE
   SYNTAX      Counter32
   MAX-ACCESS  read-only
   STATUS      current
   DESCRIPTION
      "Path: ethOam.performance.qualityMonitor.upDown.jitterDownBins.bin7

       32 bit unsigned wrappable counter."
   ::= {pr1646v2EthOamQualityMonitorEntry 506202112}

pr1646v2EthOamQualityMonitorUpDownJitterDownBinsMaxBin8 OBJECT-TYPE
   SYNTAX      Counter32
   MAX-ACCESS  read-only
   STATUS      current
   DESCRIPTION
      "Path: ethOam.performance.qualityMonitor.upDown.jitterDownBins.maxBin8

       32 bit unsigned wrappable counter."
   ::= {pr1646v2EthOamQualityMonitorEntry 506202368}

pr1646v2EthOamQualityMonitorUpDownJitterDownBinsMax OBJECT-TYPE
   SYNTAX      Integer32
   MAX-ACCESS  read-only
   STATUS      current
   DESCRIPTION
      "Path: ethOam.performance.qualityMonitor.upDown.jitterDownBins.max

       unit name = sec
       formula = 1000 / ; 1000 *"
   ::= {pr1646v2EthOamQualityMonitorEntry 506205696}

pr1646v2EthOamQualityMonitorUpDownJitterDownBinsPlusMax OBJECT-TYPE
   SYNTAX      Counter32
   MAX-ACCESS  read-only
   STATUS      current
   DESCRIPTION
      "Path: ethOam.performance.qualityMonitor.upDown.jitterDownBins.plusMax

       32 bit unsigned wrappable counter."
   ::= {pr1646v2EthOamQualityMonitorEntry 506202624}

pr1646v2EthOamQualityMonitorLastLogSysUpTime OBJECT-TYPE
   SYNTAX      TimeTicks
   MAX-ACCESS  read-only
   STATUS      current
   DESCRIPTION
      "Path: ethOam.performance.qualityMonitor.lastLog.sysUpTime

       Time in centi-second."
   ::= {pr1646v2EthOamQualityMonitorEntry 671154176}

pr1646v2EthOamQualityMonitorLastLogNbrTxPckt OBJECT-TYPE
   SYNTAX      Counter32
   MAX-ACCESS  read-only
   STATUS      current
   DESCRIPTION
      "Path: ethOam.performance.qualityMonitor.lastLog.nbrOfTxPackets

       32 bit unsigned wrappable counter."
   ::= {pr1646v2EthOamQualityMonitorEntry 671285248}

pr1646v2EthOamQualityMonitorLastLogNbrRxPckt OBJECT-TYPE
   SYNTAX      Counter32
   MAX-ACCESS  read-only
   STATUS      current
   DESCRIPTION
      "Path: ethOam.performance.qualityMonitor.lastLog.nbrOfRxPackets

       32 bit unsigned wrappable counter."
   ::= {pr1646v2EthOamQualityMonitorEntry 671350784}

pr1646v2EthOamQualityMonitorLastLogError OBJECT-TYPE
   SYNTAX      Counter32
   MAX-ACCESS  read-only
   STATUS      current
   DESCRIPTION
      "Path: ethOam.performance.qualityMonitor.lastLog.error

       32 bit unsigned wrappable counter."
   ::= {pr1646v2EthOamQualityMonitorEntry 672202752}

pr1646v2EthOamQualityMonitorLastLogLoss OBJECT-TYPE
   SYNTAX      Counter32
   MAX-ACCESS  read-only
   STATUS      current
   DESCRIPTION
      "Path: ethOam.performance.qualityMonitor.lastLog.loss

       32 bit unsigned wrappable counter."
   ::= {pr1646v2EthOamQualityMonitorEntry 671481856}

pr1646v2EthOamQualityMonitorLastLogLossDelay OBJECT-TYPE
   SYNTAX      Counter32
   MAX-ACCESS  read-only
   STATUS      current
   DESCRIPTION
      "Path: ethOam.performance.qualityMonitor.lastLog.lossDelay

       32 bit unsigned wrappable counter."
   ::= {pr1646v2EthOamQualityMonitorEntry 672137216}

pr1646v2EthOamQualityMonitorLastLogDelayMin OBJECT-TYPE
   SYNTAX      Integer32
   MAX-ACCESS  read-only
   STATUS      current
   DESCRIPTION
      "Path: ethOam.performance.qualityMonitor.lastLog.delayMin

       unit name = sec
       formula = 1000 / ; 1000 *"
   ::= {pr1646v2EthOamQualityMonitorEntry 671809536}

pr1646v2EthOamQualityMonitorLastLogDelayAvrg OBJECT-TYPE
   SYNTAX      Integer32
   MAX-ACCESS  read-only
   STATUS      current
   DESCRIPTION
      "Path: ethOam.performance.qualityMonitor.lastLog.delayAvrg

       unit name = sec
       formula = 1000 / ; 1000 *"
   ::= {pr1646v2EthOamQualityMonitorEntry 671547392}

pr1646v2EthOamQualityMonitorLastLogDelayMax OBJECT-TYPE
   SYNTAX      Integer32
   MAX-ACCESS  read-only
   STATUS      current
   DESCRIPTION
      "Path: ethOam.performance.qualityMonitor.lastLog.delayMax

       unit name = sec
       formula = 1000 / ; 1000 *"
   ::= {pr1646v2EthOamQualityMonitorEntry 671612928}

pr1646v2EthOamQualityMonitorLastLogJitterNegMax OBJECT-TYPE
   SYNTAX      Integer32
   MAX-ACCESS  read-only
   STATUS      current
   DESCRIPTION
      "Path: ethOam.performance.qualityMonitor.lastLog.jitterNegMax

       unit name = sec
       formula = 1000 / ; 1000 *"
   ::= {pr1646v2EthOamQualityMonitorEntry 672006144}

pr1646v2EthOamQualityMonitorLastLogJitterAvrg OBJECT-TYPE
   SYNTAX      Integer32
   MAX-ACCESS  read-only
   STATUS      current
   DESCRIPTION
      "Path: ethOam.performance.qualityMonitor.lastLog.jitterAvrg

       unit name = sec
       formula = 1000 / ; 1000 *"
   ::= {pr1646v2EthOamQualityMonitorEntry 671678464}

pr1646v2EthOamQualityMonitorLastLogJitterPosMax OBJECT-TYPE
   SYNTAX      Integer32
   MAX-ACCESS  read-only
   STATUS      current
   DESCRIPTION
      "Path: ethOam.performance.qualityMonitor.lastLog.jitterPosMax

       unit name = sec
       formula = 1000 / ; 1000 *"
   ::= {pr1646v2EthOamQualityMonitorEntry 671744000}

pr1646v2EthOamQualityMonitorLastLogUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: ethOam.performance.qualityMonitor.lastLog.upDown.status

       Possibilities:
               notInUse   (3)
               onlyJitter   (1)
               jitterAndLoss   (2)
               all   (4)
               onlyLoss   (8)"
   ::= {pr1646v2EthOamQualityMonitorEntry 673059840}

pr1646v2EthOamQualityMonitorLastLogUpDownLossUp OBJECT-TYPE
   SYNTAX      Counter32
   MAX-ACCESS  read-only
   STATUS      current
   DESCRIPTION
      "Path: ethOam.performance.qualityMonitor.lastLog.upDown.lossUp

       32 bit unsigned wrappable counter."
   ::= {pr1646v2EthOamQualityMonitorEntry 673057280}

pr1646v2EthOamQualityMonitorLastLogUpDownLossDelayUp OBJECT-TYPE
   SYNTAX      Counter32
   MAX-ACCESS  read-only
   STATUS      current
   DESCRIPTION
      "Path: ethOam.performance.qualityMonitor.lastLog.upDown.lossDelayUp

       32 bit unsigned wrappable counter."
   ::= {pr1646v2EthOamQualityMonitorEntry 673057536}

pr1646v2EthOamQualityMonitorLastLogUpDownDelayUpMin OBJECT-TYPE
   SYNTAX      Integer32
   MAX-ACCESS  read-only
   STATUS      current
   DESCRIPTION
      "Path: ethOam.performance.qualityMonitor.lastLog.upDown.delayUpMin

       unit name = sec
       formula = 1000 / ; 1000 *"
   ::= {pr1646v2EthOamQualityMonitorEntry 673062400}

pr1646v2EthOamQualityMonitorLastLogUpDownDelayUpAvrg OBJECT-TYPE
   SYNTAX      Integer32
   MAX-ACCESS  read-only
   STATUS      current
   DESCRIPTION
      "Path: ethOam.performance.qualityMonitor.lastLog.upDown.delayUpAvrg

       unit name = sec
       formula = 1000 / ; 1000 *"
   ::= {pr1646v2EthOamQualityMonitorEntry 673062656}

pr1646v2EthOamQualityMonitorLastLogUpDownDelayUpMax OBJECT-TYPE
   SYNTAX      Integer32
   MAX-ACCESS  read-only
   STATUS      current
   DESCRIPTION
      "Path: ethOam.performance.qualityMonitor.lastLog.upDown.delayUpMax

       unit name = sec
       formula = 1000 / ; 1000 *"
   ::= {pr1646v2EthOamQualityMonitorEntry 673062912}

pr1646v2EthOamQualityMonitorLastLogUpDownJitterUpNegMax OBJECT-TYPE
   SYNTAX      Integer32
   MAX-ACCESS  read-only
   STATUS      current
   DESCRIPTION
      "Path: ethOam.performance.qualityMonitor.lastLog.upDown.jitterUpNegMax

       unit name = sec
       formula = 1000 / ; 1000 *"
   ::= {pr1646v2EthOamQualityMonitorEntry 673054976}

pr1646v2EthOamQualityMonitorLastLogUpDownJitterUpAvrg OBJECT-TYPE
   SYNTAX      Integer32
   MAX-ACCESS  read-only
   STATUS      current
   DESCRIPTION
      "Path: ethOam.performance.qualityMonitor.lastLog.upDown.jitterUpAvrg

       unit name = sec
       formula = 1000 / ; 1000 *"
   ::= {pr1646v2EthOamQualityMonitorEntry 673055232}

pr1646v2EthOamQualityMonitorLastLogUpDownJitterUpPosMax OBJECT-TYPE
   SYNTAX      Integer32
   MAX-ACCESS  read-only
   STATUS      current
   DESCRIPTION
      "Path: ethOam.performance.qualityMonitor.lastLog.upDown.jitterUpPosMax

       unit name = sec
       formula = 1000 / ; 1000 *"
   ::= {pr1646v2EthOamQualityMonitorEntry 673055488}

pr1646v2EthOamQualityMonitorLastLogUpDownLossDown OBJECT-TYPE
   SYNTAX      Counter32
   MAX-ACCESS  read-only
   STATUS      current
   DESCRIPTION
      "Path: ethOam.performance.qualityMonitor.lastLog.upDown.lossDown

       32 bit unsigned wrappable counter."
   ::= {pr1646v2EthOamQualityMonitorEntry 673057792}

pr1646v2EthOamQualityMonitorLastLogUpDownLossDelayDown OBJECT-TYPE
   SYNTAX      Counter32
   MAX-ACCESS  read-only
   STATUS      current
   DESCRIPTION
      "Path: ethOam.performance.qualityMonitor.lastLog.upDown.lossDelayDown

       32 bit unsigned wrappable counter."
   ::= {pr1646v2EthOamQualityMonitorEntry 673058048}

pr1646v2EthOamQualityMonitorLastLogUpDownDelayDownMin OBJECT-TYPE
   SYNTAX      Integer32
   MAX-ACCESS  read-only
   STATUS      current
   DESCRIPTION
      "Path: ethOam.performance.qualityMonitor.lastLog.upDown.delayDownMin

       unit name = sec
       formula = 1000 / ; 1000 *"
   ::= {pr1646v2EthOamQualityMonitorEntry 673063680}

pr1646v2EthOamQualityMonitorLastLogUpDownDelayDownAvrg OBJECT-TYPE
   SYNTAX      Integer32
   MAX-ACCESS  read-only
   STATUS      current
   DESCRIPTION
      "Path: ethOam.performance.qualityMonitor.lastLog.upDown.delayDownAvrg

       unit name = sec
       formula = 1000 / ; 1000 *"
   ::= {pr1646v2EthOamQualityMonitorEntry 673063936}

pr1646v2EthOamQualityMonitorLastLogUpDownDelayDownMax OBJECT-TYPE
   SYNTAX      Integer32
   MAX-ACCESS  read-only
   STATUS      current
   DESCRIPTION
      "Path: ethOam.performance.qualityMonitor.lastLog.upDown.delayDownMax

       unit name = sec
       formula = 1000 / ; 1000 *"
   ::= {pr1646v2EthOamQualityMonitorEntry 673064192}

pr1646v2EthOamQualityMonitorLastLogUpDownJitterDownNegMax OBJECT-TYPE
   SYNTAX      Integer32
   MAX-ACCESS  read-only
   STATUS      current
   DESCRIPTION
      "Path: ethOam.performance.qualityMonitor.lastLog.upDown.jitterDownNegMax

       unit name = sec
       formula = 1000 / ; 1000 *"
   ::= {pr1646v2EthOamQualityMonitorEntry 673055744}

pr1646v2EthOamQualityMonitorLastLogUpDownJitterDownAvrg OBJECT-TYPE
   SYNTAX      Integer32
   MAX-ACCESS  read-only
   STATUS      current
   DESCRIPTION
      "Path: ethOam.performance.qualityMonitor.lastLog.upDown.jitterDownAvrg

       unit name = sec
       formula = 1000 / ; 1000 *"
   ::= {pr1646v2EthOamQualityMonitorEntry 673056000}

pr1646v2EthOamQualityMonitorLastLogUpDownJitterDownPosMax OBJECT-TYPE
   SYNTAX      Integer32
   MAX-ACCESS  read-only
   STATUS      current
   DESCRIPTION
      "Path: ethOam.performance.qualityMonitor.lastLog.upDown.jitterDownPosMax

       unit name = sec
       formula = 1000 / ; 1000 *"
   ::= {pr1646v2EthOamQualityMonitorEntry 673056256}

pr1646v2EthOamQualityMonitorLastLogDate OBJECT-TYPE
   SYNTAX      DisplayString
   MAX-ACCESS  read-only
   STATUS      current
   DESCRIPTION
      "Path: ethOam.performance.qualityMonitor.lastLog.date"
   ::= {pr1646v2EthOamQualityMonitorEntry 673120256}

pr1646v2EthOamQualityMonitorAlarm OBJECT-TYPE
   SYNTAX      Integer32
   MAX-ACCESS  read-only
   STATUS      current
   DESCRIPTION
      "Path: ethOam.performance.qualityMonitor.alarm

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {pr1646v2EthOamQualityMonitorEntry 369098752}

pr1646v2EthOamQualityMonitorLogging OBJECT-TYPE
   SYNTAX      SEQUENCE OF Pr1646v2EthOamQualityMonitorLoggingEntry
   MAX-ACCESS  not-accessible
   STATUS      current
   DESCRIPTION
      ""
   ::= {pr1646v2EthOamQualityMonitor 335544320}

pr1646v2EthOamQualityMonitorLoggingEntry OBJECT-TYPE
   SYNTAX      Pr1646v2EthOamQualityMonitorLoggingEntry
   MAX-ACCESS  not-accessible
   STATUS      current
   DESCRIPTION
      ""
   INDEX      { pr1646v2EthOamQualityMonitorLoggingGlobalIx,
                pr1646v2EthOamQualityMonitorTableIx,
                pr1646v2EthOamQualityMonitorLoggingTableIx }
   ::= {pr1646v2EthOamQualityMonitorLogging 1}

Pr1646v2EthOamQualityMonitorLoggingEntry ::=
   SEQUENCE
      {
      pr1646v2EthOamQualityMonitorLoggingGlobalIx
         GlobalIndex,
      pr1646v2EthOamQualityMonitorLoggingTableIx
         TableIndex,
      pr1646v2EthOamQualityMonitorLoggingSysUpTime
         TimeTicks,
      pr1646v2EthOamQualityMonitorLoggingNbrTxPckt
         Counter32,
      pr1646v2EthOamQualityMonitorLoggingNbrRxPckt
         Counter32,
      pr1646v2EthOamQualityMonitorLoggingError
         Counter32,
      pr1646v2EthOamQualityMonitorLoggingLoss
         Counter32,
      pr1646v2EthOamQualityMonitorLoggingLossDelay
         Counter32,
      pr1646v2EthOamQualityMonitorLoggingDelayMin
         Integer32,
      pr1646v2EthOamQualityMonitorLoggingDelayAvrg
         Integer32,
      pr1646v2EthOamQualityMonitorLoggingDelayMax
         Integer32,
      pr1646v2EthOamQualityMonitorLoggingJitterNegMax
         Integer32,
      pr1646v2EthOamQualityMonitorLoggingJitterAvrg
         Integer32,
      pr1646v2EthOamQualityMonitorLoggingJitterPosMax
         Integer32,
      pr1646v2EthOamQualityMonitorLoggingUpDownStatus
         INTEGER,
      pr1646v2EthOamQualityMonitorLoggingUpDownLossUp
         Counter32,
      pr1646v2EthOamQualityMonitorLoggingUpDownLossDelayUp
         Counter32,
      pr1646v2EthOamQualityMonitorLoggingUpDownDelayUpMin
         Integer32,
      pr1646v2EthOamQualityMonitorLoggingUpDownDelayUpAvrg
         Integer32,
      pr1646v2EthOamQualityMonitorLoggingUpDownDelayUpMax
         Integer32,
      pr1646v2EthOamQualityMonitorLoggingUpDownJitterUpNegMax
         Integer32,
      pr1646v2EthOamQualityMonitorLoggingUpDownJitterUpAvrg
         Integer32,
      pr1646v2EthOamQualityMonitorLoggingUpDownJitterUpPosMax
         Integer32,
      pr1646v2EthOamQualityMonitorLoggingUpDownLossDown
         Counter32,
      pr1646v2EthOamQualityMonitorLoggingUpDownLossDelayDown
         Counter32,
      pr1646v2EthOamQualityMonitorLoggingUpDownDelayDownMin
         Integer32,
      pr1646v2EthOamQualityMonitorLoggingUpDownDelayDownAvrg
         Integer32,
      pr1646v2EthOamQualityMonitorLoggingUpDownDelayDownMax
         Integer32,
      pr1646v2EthOamQualityMonitorLoggingUpDownJitterDownNegMax
         Integer32,
      pr1646v2EthOamQualityMonitorLoggingUpDownJitterDownAvrg
         Integer32,
      pr1646v2EthOamQualityMonitorLoggingUpDownJitterDownPosMax
         Integer32,
      pr1646v2EthOamQualityMonitorLoggingDate
         DisplayString
      }

pr1646v2EthOamQualityMonitorLoggingGlobalIx OBJECT-TYPE
   SYNTAX      GlobalIndex
   MAX-ACCESS  not-accessible
   STATUS      current
   DESCRIPTION
      "The value of the tlsCntTreeGlobalIndex of the MANAGED OBJECT."
   ::= {pr1646v2EthOamQualityMonitorLoggingEntry 10}

pr1646v2EthOamQualityMonitorLoggingTableIx OBJECT-TYPE
   SYNTAX      TableIndex
   MAX-ACCESS  not-accessible
   STATUS      current
   DESCRIPTION
      ""
   ::= {pr1646v2EthOamQualityMonitorLoggingEntry 11}

pr1646v2EthOamQualityMonitorLoggingSysUpTime OBJECT-TYPE
   SYNTAX      TimeTicks
   MAX-ACCESS  read-only
   STATUS      current
   DESCRIPTION
      "Path: ethOam.performance.qualityMonitor.logging.sysUpTime

       Time in centi-second."
   ::= {pr1646v2EthOamQualityMonitorLoggingEntry 16777216}

pr1646v2EthOamQualityMonitorLoggingNbrTxPckt OBJECT-TYPE
   SYNTAX      Counter32
   MAX-ACCESS  read-only
   STATUS      current
   DESCRIPTION
      "Path: ethOam.performance.qualityMonitor.logging.nbrOfTxPackets

       32 bit unsigned wrappable counter."
   ::= {pr1646v2EthOamQualityMonitorLoggingEntry 50331648}

pr1646v2EthOamQualityMonitorLoggingNbrRxPckt OBJECT-TYPE
   SYNTAX      Counter32
   MAX-ACCESS  read-only
   STATUS      current
   DESCRIPTION
      "Path: ethOam.performance.qualityMonitor.logging.nbrOfRxPackets

       32 bit unsigned wrappable counter."
   ::= {pr1646v2EthOamQualityMonitorLoggingEntry 67108864}

pr1646v2EthOamQualityMonitorLoggingError OBJECT-TYPE
   SYNTAX      Counter32
   MAX-ACCESS  read-only
   STATUS      current
   DESCRIPTION
      "Path: ethOam.performance.qualityMonitor.logging.error

       32 bit unsigned wrappable counter."
   ::= {pr1646v2EthOamQualityMonitorLoggingEntry 285212672}

pr1646v2EthOamQualityMonitorLoggingLoss OBJECT-TYPE
   SYNTAX      Counter32
   MAX-ACCESS  read-only
   STATUS      current
   DESCRIPTION
      "Path: ethOam.performance.qualityMonitor.logging.loss

       32 bit unsigned wrappable counter."
   ::= {pr1646v2EthOamQualityMonitorLoggingEntry 100663296}

pr1646v2EthOamQualityMonitorLoggingLossDelay OBJECT-TYPE
   SYNTAX      Counter32
   MAX-ACCESS  read-only
   STATUS      current
   DESCRIPTION
      "Path: ethOam.performance.qualityMonitor.logging.lossDelay

       32 bit unsigned wrappable counter."
   ::= {pr1646v2EthOamQualityMonitorLoggingEntry 268435456}

pr1646v2EthOamQualityMonitorLoggingDelayMin OBJECT-TYPE
   SYNTAX      Integer32
   MAX-ACCESS  read-only
   STATUS      current
   DESCRIPTION
      "Path: ethOam.performance.qualityMonitor.logging.delayMin

       unit name = sec
       formula = 1000 / ; 1000 *"
   ::= {pr1646v2EthOamQualityMonitorLoggingEntry 184549376}

pr1646v2EthOamQualityMonitorLoggingDelayAvrg OBJECT-TYPE
   SYNTAX      Integer32
   MAX-ACCESS  read-only
   STATUS      current
   DESCRIPTION
      "Path: ethOam.performance.qualityMonitor.logging.delayAvrg

       unit name = sec
       formula = 1000 / ; 1000 *"
   ::= {pr1646v2EthOamQualityMonitorLoggingEntry 117440512}

pr1646v2EthOamQualityMonitorLoggingDelayMax OBJECT-TYPE
   SYNTAX      Integer32
   MAX-ACCESS  read-only
   STATUS      current
   DESCRIPTION
      "Path: ethOam.performance.qualityMonitor.logging.delayMax

       unit name = sec
       formula = 1000 / ; 1000 *"
   ::= {pr1646v2EthOamQualityMonitorLoggingEntry 134217728}

pr1646v2EthOamQualityMonitorLoggingJitterNegMax OBJECT-TYPE
   SYNTAX      Integer32
   MAX-ACCESS  read-only
   STATUS      current
   DESCRIPTION
      "Path: ethOam.performance.qualityMonitor.logging.jitterNegMax

       unit name = sec
       formula = 1000 / ; 1000 *"
   ::= {pr1646v2EthOamQualityMonitorLoggingEntry 234881024}

pr1646v2EthOamQualityMonitorLoggingJitterAvrg OBJECT-TYPE
   SYNTAX      Integer32
   MAX-ACCESS  read-only
   STATUS      current
   DESCRIPTION
      "Path: ethOam.performance.qualityMonitor.logging.jitterAvrg

       unit name = sec
       formula = 1000 / ; 1000 *"
   ::= {pr1646v2EthOamQualityMonitorLoggingEntry 150994944}

pr1646v2EthOamQualityMonitorLoggingJitterPosMax OBJECT-TYPE
   SYNTAX      Integer32
   MAX-ACCESS  read-only
   STATUS      current
   DESCRIPTION
      "Path: ethOam.performance.qualityMonitor.logging.jitterPosMax

       unit name = sec
       formula = 1000 / ; 1000 *"
   ::= {pr1646v2EthOamQualityMonitorLoggingEntry 167772160}

pr1646v2EthOamQualityMonitorLoggingUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: ethOam.performance.qualityMonitor.logging.upDown.status

       Possibilities:
               notInUse   (3)
               onlyJitter   (1)
               jitterAndLoss   (2)
               all   (4)
               onlyLoss   (8)"
   ::= {pr1646v2EthOamQualityMonitorLoggingEntry 504627200}

pr1646v2EthOamQualityMonitorLoggingUpDownLossUp OBJECT-TYPE
   SYNTAX      Counter32
   MAX-ACCESS  read-only
   STATUS      current
   DESCRIPTION
      "Path: ethOam.performance.qualityMonitor.logging.upDown.lossUp

       32 bit unsigned wrappable counter."
   ::= {pr1646v2EthOamQualityMonitorLoggingEntry 503971840}

pr1646v2EthOamQualityMonitorLoggingUpDownLossDelayUp OBJECT-TYPE
   SYNTAX      Counter32
   MAX-ACCESS  read-only
   STATUS      current
   DESCRIPTION
      "Path: ethOam.performance.qualityMonitor.logging.upDown.lossDelayUp

       32 bit unsigned wrappable counter."
   ::= {pr1646v2EthOamQualityMonitorLoggingEntry 504037376}

pr1646v2EthOamQualityMonitorLoggingUpDownDelayUpMin OBJECT-TYPE
   SYNTAX      Integer32
   MAX-ACCESS  read-only
   STATUS      current
   DESCRIPTION
      "Path: ethOam.performance.qualityMonitor.logging.upDown.delayUpMin

       unit name = sec
       formula = 1000 / ; 1000 *"
   ::= {pr1646v2EthOamQualityMonitorLoggingEntry 505282560}

pr1646v2EthOamQualityMonitorLoggingUpDownDelayUpAvrg OBJECT-TYPE
   SYNTAX      Integer32
   MAX-ACCESS  read-only
   STATUS      current
   DESCRIPTION
      "Path: ethOam.performance.qualityMonitor.logging.upDown.delayUpAvrg

       unit name = sec
       formula = 1000 / ; 1000 *"
   ::= {pr1646v2EthOamQualityMonitorLoggingEntry 505348096}

pr1646v2EthOamQualityMonitorLoggingUpDownDelayUpMax OBJECT-TYPE
   SYNTAX      Integer32
   MAX-ACCESS  read-only
   STATUS      current
   DESCRIPTION
      "Path: ethOam.performance.qualityMonitor.logging.upDown.delayUpMax

       unit name = sec
       formula = 1000 / ; 1000 *"
   ::= {pr1646v2EthOamQualityMonitorLoggingEntry 505413632}

pr1646v2EthOamQualityMonitorLoggingUpDownJitterUpNegMax OBJECT-TYPE
   SYNTAX      Integer32
   MAX-ACCESS  read-only
   STATUS      current
   DESCRIPTION
      "Path: ethOam.performance.qualityMonitor.logging.upDown.jitterUpNegMax

       unit name = sec
       formula = 1000 / ; 1000 *"
   ::= {pr1646v2EthOamQualityMonitorLoggingEntry 503382016}

pr1646v2EthOamQualityMonitorLoggingUpDownJitterUpAvrg OBJECT-TYPE
   SYNTAX      Integer32
   MAX-ACCESS  read-only
   STATUS      current
   DESCRIPTION
      "Path: ethOam.performance.qualityMonitor.logging.upDown.jitterUpAvrg

       unit name = sec
       formula = 1000 / ; 1000 *"
   ::= {pr1646v2EthOamQualityMonitorLoggingEntry 503447552}

pr1646v2EthOamQualityMonitorLoggingUpDownJitterUpPosMax OBJECT-TYPE
   SYNTAX      Integer32
   MAX-ACCESS  read-only
   STATUS      current
   DESCRIPTION
      "Path: ethOam.performance.qualityMonitor.logging.upDown.jitterUpPosMax

       unit name = sec
       formula = 1000 / ; 1000 *"
   ::= {pr1646v2EthOamQualityMonitorLoggingEntry 503513088}

pr1646v2EthOamQualityMonitorLoggingUpDownLossDown OBJECT-TYPE
   SYNTAX      Counter32
   MAX-ACCESS  read-only
   STATUS      current
   DESCRIPTION
      "Path: ethOam.performance.qualityMonitor.logging.upDown.lossDown

       32 bit unsigned wrappable counter."
   ::= {pr1646v2EthOamQualityMonitorLoggingEntry 504102912}

pr1646v2EthOamQualityMonitorLoggingUpDownLossDelayDown OBJECT-TYPE
   SYNTAX      Counter32
   MAX-ACCESS  read-only
   STATUS      current
   DESCRIPTION
      "Path: ethOam.performance.qualityMonitor.logging.upDown.lossDelayDown

       32 bit unsigned wrappable counter."
   ::= {pr1646v2EthOamQualityMonitorLoggingEntry 504168448}

pr1646v2EthOamQualityMonitorLoggingUpDownDelayDownMin OBJECT-TYPE
   SYNTAX      Integer32
   MAX-ACCESS  read-only
   STATUS      current
   DESCRIPTION
      "Path: ethOam.performance.qualityMonitor.logging.upDown.delayDownMin

       unit name = sec
       formula = 1000 / ; 1000 *"
   ::= {pr1646v2EthOamQualityMonitorLoggingEntry 505610240}

pr1646v2EthOamQualityMonitorLoggingUpDownDelayDownAvrg OBJECT-TYPE
   SYNTAX      Integer32
   MAX-ACCESS  read-only
   STATUS      current
   DESCRIPTION
      "Path: ethOam.performance.qualityMonitor.logging.upDown.delayDownAvrg

       unit name = sec
       formula = 1000 / ; 1000 *"
   ::= {pr1646v2EthOamQualityMonitorLoggingEntry 505675776}

pr1646v2EthOamQualityMonitorLoggingUpDownDelayDownMax OBJECT-TYPE
   SYNTAX      Integer32
   MAX-ACCESS  read-only
   STATUS      current
   DESCRIPTION
      "Path: ethOam.performance.qualityMonitor.logging.upDown.delayDownMax

       unit name = sec
       formula = 1000 / ; 1000 *"
   ::= {pr1646v2EthOamQualityMonitorLoggingEntry 505741312}

pr1646v2EthOamQualityMonitorLoggingUpDownJitterDownNegMax OBJECT-TYPE
   SYNTAX      Integer32
   MAX-ACCESS  read-only
   STATUS      current
   DESCRIPTION
      "Path: ethOam.performance.qualityMonitor.logging.upDown.jitterDownNegMax

       unit name = sec
       formula = 1000 / ; 1000 *"
   ::= {pr1646v2EthOamQualityMonitorLoggingEntry 503578624}

pr1646v2EthOamQualityMonitorLoggingUpDownJitterDownAvrg OBJECT-TYPE
   SYNTAX      Integer32
   MAX-ACCESS  read-only
   STATUS      current
   DESCRIPTION
      "Path: ethOam.performance.qualityMonitor.logging.upDown.jitterDownAvrg

       unit name = sec
       formula = 1000 / ; 1000 *"
   ::= {pr1646v2EthOamQualityMonitorLoggingEntry 503644160}

pr1646v2EthOamQualityMonitorLoggingUpDownJitterDownPosMax OBJECT-TYPE
   SYNTAX      Integer32
   MAX-ACCESS  read-only
   STATUS      current
   DESCRIPTION
      "Path: ethOam.performance.qualityMonitor.logging.upDown.jitterDownPosMax

       unit name = sec
       formula = 1000 / ; 1000 *"
   ::= {pr1646v2EthOamQualityMonitorLoggingEntry 503709696}

pr1646v2EthOamQualityMonitorLoggingDate OBJECT-TYPE
   SYNTAX      DisplayString
   MAX-ACCESS  read-only
   STATUS      current
   DESCRIPTION
      "Path: ethOam.performance.qualityMonitor.logging.date"
   ::= {pr1646v2EthOamQualityMonitorLoggingEntry 520093696}

pr1646v2EthOamQualityMonitorLoggingBin OBJECT-TYPE
   SYNTAX      SEQUENCE OF Pr1646v2EthOamQualityMonitorLoggingBinEntry
   MAX-ACCESS  not-accessible
   STATUS      current
   DESCRIPTION
      ""
   ::= {pr1646v2EthOamQualityMonitor 337641472}

pr1646v2EthOamQualityMonitorLoggingBinEntry OBJECT-TYPE
   SYNTAX      Pr1646v2EthOamQualityMonitorLoggingBinEntry
   MAX-ACCESS  not-accessible
   STATUS      current
   DESCRIPTION
      ""
   INDEX      { pr1646v2EthOamQualityMonitorLoggingBinGlobalIx,
                pr1646v2EthOamQualityMonitorTableIx,
                pr1646v2EthOamQualityMonitorLoggingTableIx,
                pr1646v2EthOamQualityMonitorLoggingBinTableIx }
   ::= {pr1646v2EthOamQualityMonitorLoggingBin 1}

Pr1646v2EthOamQualityMonitorLoggingBinEntry ::=
   SEQUENCE
      {
      pr1646v2EthOamQualityMonitorLoggingBinGlobalIx
         GlobalIndex,
      pr1646v2EthOamQualityMonitorLoggingBinTableIx
         TableIndex,
      pr1646v2EthOamQualityMonitorLoggingBinName
         INTEGER,
      pr1646v2EthOamQualityMonitorLoggingBinType
         INTEGER,
      pr1646v2EthOamQualityMonitorLoggingBinMinMin
         Counter32,
      pr1646v2EthOamQualityMonitorLoggingBinMin
         Integer32,
      pr1646v2EthOamQualityMonitorLoggingBinMinBin1
         Counter32,
      pr1646v2EthOamQualityMonitorLoggingBinBin2
         Counter32,
      pr1646v2EthOamQualityMonitorLoggingBinBin3
         Counter32,
      pr1646v2EthOamQualityMonitorLoggingBinBin4
         Counter32,
      pr1646v2EthOamQualityMonitorLoggingBinBin5
         Counter32,
      pr1646v2EthOamQualityMonitorLoggingBinBin6
         Counter32,
      pr1646v2EthOamQualityMonitorLoggingBinBin7
         Counter32,
      pr1646v2EthOamQualityMonitorLoggingBinMaxBin8
         Counter32,
      pr1646v2EthOamQualityMonitorLoggingBinMax
         Integer32,
      pr1646v2EthOamQualityMonitorLoggingBinPlusMax
         Counter32
      }

pr1646v2EthOamQualityMonitorLoggingBinGlobalIx OBJECT-TYPE
   SYNTAX      GlobalIndex
   MAX-ACCESS  not-accessible
   STATUS      current
   DESCRIPTION
      "The value of the tlsCntTreeGlobalIndex of the MANAGED OBJECT."
   ::= {pr1646v2EthOamQualityMonitorLoggingBinEntry 10}

pr1646v2EthOamQualityMonitorLoggingBinTableIx OBJECT-TYPE
   SYNTAX      TableIndex
   MAX-ACCESS  not-accessible
   STATUS      current
   DESCRIPTION
      ""
   ::= {pr1646v2EthOamQualityMonitorLoggingBinEntry 11}

pr1646v2EthOamQualityMonitorLoggingBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: ethOam.performance.qualityMonitor.logging.bin.name

       Possibilities:
               delay   (1)
               delayUp   (2)
               delayDown   (3)
               jitter   (4)
               jitterUp   (5)
               jitterDown   (6)"
   ::= {pr1646v2EthOamQualityMonitorLoggingBinEntry 503316480}

pr1646v2EthOamQualityMonitorLoggingBinType OBJECT-TYPE
   SYNTAX      INTEGER
               {
               fd (1),
               fdr (2),
               notInUse (3),
               ifdv (4)
               }
   MAX-ACCESS  read-only
   STATUS      current
   DESCRIPTION
      "Path: ethOam.performance.qualityMonitor.logging.bin.type

       Possibilities:
               fd   (1)
               fdr   (2)
               notInUse   (3)
               ifdv   (4)"
   ::= {pr1646v2EthOamQualityMonitorLoggingBinEntry 520093696}

pr1646v2EthOamQualityMonitorLoggingBinMinMin OBJECT-TYPE
   SYNTAX      Counter32
   MAX-ACCESS  read-only
   STATUS      current
   DESCRIPTION
      "Path: ethOam.performance.qualityMonitor.logging.bin.minMin

       32 bit unsigned wrappable counter."
   ::= {pr1646v2EthOamQualityMonitorLoggingBinEntry 16777216}

pr1646v2EthOamQualityMonitorLoggingBinMin OBJECT-TYPE
   SYNTAX      Integer32
   MAX-ACCESS  read-only
   STATUS      current
   DESCRIPTION
      "Path: ethOam.performance.qualityMonitor.logging.bin.min

       unit name = sec
       formula = 1000 / ; 1000 *"
   ::= {pr1646v2EthOamQualityMonitorLoggingBinEntry 352321536}

pr1646v2EthOamQualityMonitorLoggingBinMinBin1 OBJECT-TYPE
   SYNTAX      Counter32
   MAX-ACCESS  read-only
   STATUS      current
   DESCRIPTION
      "Path: ethOam.performance.qualityMonitor.logging.bin.minBin1

       32 bit unsigned wrappable counter."
   ::= {pr1646v2EthOamQualityMonitorLoggingBinEntry 33554432}

pr1646v2EthOamQualityMonitorLoggingBinBin2 OBJECT-TYPE
   SYNTAX      Counter32
   MAX-ACCESS  read-only
   STATUS      current
   DESCRIPTION
      "Path: ethOam.performance.qualityMonitor.logging.bin.bin2

       32 bit unsigned wrappable counter."
   ::= {pr1646v2EthOamQualityMonitorLoggingBinEntry 50331648}

pr1646v2EthOamQualityMonitorLoggingBinBin3 OBJECT-TYPE
   SYNTAX      Counter32
   MAX-ACCESS  read-only
   STATUS      current
   DESCRIPTION
      "Path: ethOam.performance.qualityMonitor.logging.bin.bin3

       32 bit unsigned wrappable counter."
   ::= {pr1646v2EthOamQualityMonitorLoggingBinEntry 67108864}

pr1646v2EthOamQualityMonitorLoggingBinBin4 OBJECT-TYPE
   SYNTAX      Counter32
   MAX-ACCESS  read-only
   STATUS      current
   DESCRIPTION
      "Path: ethOam.performance.qualityMonitor.logging.bin.bin4

       32 bit unsigned wrappable counter."
   ::= {pr1646v2EthOamQualityMonitorLoggingBinEntry 83886080}

pr1646v2EthOamQualityMonitorLoggingBinBin5 OBJECT-TYPE
   SYNTAX      Counter32
   MAX-ACCESS  read-only
   STATUS      current
   DESCRIPTION
      "Path: ethOam.performance.qualityMonitor.logging.bin.bin5

       32 bit unsigned wrappable counter."
   ::= {pr1646v2EthOamQualityMonitorLoggingBinEntry 100663296}

pr1646v2EthOamQualityMonitorLoggingBinBin6 OBJECT-TYPE
   SYNTAX      Counter32
   MAX-ACCESS  read-only
   STATUS      current
   DESCRIPTION
      "Path: ethOam.performance.qualityMonitor.logging.bin.bin6

       32 bit unsigned wrappable counter."
   ::= {pr1646v2EthOamQualityMonitorLoggingBinEntry 117440512}

pr1646v2EthOamQualityMonitorLoggingBinBin7 OBJECT-TYPE
   SYNTAX      Counter32
   MAX-ACCESS  read-only
   STATUS      current
   DESCRIPTION
      "Path: ethOam.performance.qualityMonitor.logging.bin.bin7

       32 bit unsigned wrappable counter."
   ::= {pr1646v2EthOamQualityMonitorLoggingBinEntry 134217728}

pr1646v2EthOamQualityMonitorLoggingBinMaxBin8 OBJECT-TYPE
   SYNTAX      Counter32
   MAX-ACCESS  read-only
   STATUS      current
   DESCRIPTION
      "Path: ethOam.performance.qualityMonitor.logging.bin.maxBin8

       32 bit unsigned wrappable counter."
   ::= {pr1646v2EthOamQualityMonitorLoggingBinEntry 150994944}

pr1646v2EthOamQualityMonitorLoggingBinMax OBJECT-TYPE
   SYNTAX      Integer32
   MAX-ACCESS  read-only
   STATUS      current
   DESCRIPTION
      "Path: ethOam.performance.qualityMonitor.logging.bin.max

       unit name = sec
       formula = 1000 / ; 1000 *"
   ::= {pr1646v2EthOamQualityMonitorLoggingBinEntry 369098752}

pr1646v2EthOamQualityMonitorLoggingBinPlusMax OBJECT-TYPE
   SYNTAX      Counter32
   MAX-ACCESS  read-only
   STATUS      current
   DESCRIPTION
      "Path: ethOam.performance.qualityMonitor.logging.bin.plusMax

       32 bit unsigned wrappable counter."
   ::= {pr1646v2EthOamQualityMonitorLoggingBinEntry 167772160}

pr1646v2EthOamQualityMonitorLastLogBin OBJECT-TYPE
   SYNTAX      SEQUENCE OF Pr1646v2EthOamQualityMonitorLastLogBinEntry
   MAX-ACCESS  not-accessible
   STATUS      current
   DESCRIPTION
      ""
   ::= {pr1646v2EthOamQualityMonitor 673185792}

pr1646v2EthOamQualityMonitorLastLogBinEntry OBJECT-TYPE
   SYNTAX      Pr1646v2EthOamQualityMonitorLastLogBinEntry
   MAX-ACCESS  not-accessible
   STATUS      current
   DESCRIPTION
      ""
   INDEX      { pr1646v2EthOamQualityMonitorLastLogBinGlobalIx,
                pr1646v2EthOamQualityMonitorTableIx,
                pr1646v2EthOamQualityMonitorLastLogBinTableIx }
   ::= {pr1646v2EthOamQualityMonitorLastLogBin 1}

Pr1646v2EthOamQualityMonitorLastLogBinEntry ::=
   SEQUENCE
      {
      pr1646v2EthOamQualityMonitorLastLogBinGlobalIx
         GlobalIndex,
      pr1646v2EthOamQualityMonitorLastLogBinTableIx
         TableIndex,
      pr1646v2EthOamQualityMonitorLastLogBinName
         INTEGER,
      pr1646v2EthOamQualityMonitorLastLogBinType
         INTEGER,
      pr1646v2EthOamQualityMonitorLastLogBinMinMin
         Counter32,
      pr1646v2EthOamQualityMonitorLastLogBinMin
         Integer32,
      pr1646v2EthOamQualityMonitorLastLogBinMinBin1
         Counter32,
      pr1646v2EthOamQualityMonitorLastLogBinBin2
         Counter32,
      pr1646v2EthOamQualityMonitorLastLogBinBin3
         Counter32,
      pr1646v2EthOamQualityMonitorLastLogBinBin4
         Counter32,
      pr1646v2EthOamQualityMonitorLastLogBinBin5
         Counter32,
      pr1646v2EthOamQualityMonitorLastLogBinBin6
         Counter32,
      pr1646v2EthOamQualityMonitorLastLogBinBin7
         Counter32,
      pr1646v2EthOamQualityMonitorLastLogBinMaxBin8
         Counter32,
      pr1646v2EthOamQualityMonitorLastLogBinMax
         Integer32,
      pr1646v2EthOamQualityMonitorLastLogBinPlusMax
         Counter32
      }

pr1646v2EthOamQualityMonitorLastLogBinGlobalIx OBJECT-TYPE
   SYNTAX      GlobalIndex
   MAX-ACCESS  not-accessible
   STATUS      current
   DESCRIPTION
      "The value of the tlsCntTreeGlobalIndex of the MANAGED OBJECT."
   ::= {pr1646v2EthOamQualityMonitorLastLogBinEntry 10}

pr1646v2EthOamQualityMonitorLastLogBinTableIx OBJECT-TYPE
   SYNTAX      TableIndex
   MAX-ACCESS  not-accessible
   STATUS      current
   DESCRIPTION
      ""
   ::= {pr1646v2EthOamQualityMonitorLastLogBinEntry 11}

pr1646v2EthOamQualityMonitorLastLogBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: ethOam.performance.qualityMonitor.lastLog.bin.name

       Possibilities:
               delay   (1)
               delayUp   (2)
               delayDown   (3)
               jitter   (4)
               jitterUp   (5)
               jitterDown   (6)"
   ::= {pr1646v2EthOamQualityMonitorLastLogBinEntry 503316480}

pr1646v2EthOamQualityMonitorLastLogBinType OBJECT-TYPE
   SYNTAX      INTEGER
               {
               fd (1),
               fdr (2),
               notInUse (3),
               ifdv (4)
               }
   MAX-ACCESS  read-only
   STATUS      current
   DESCRIPTION
      "Path: ethOam.performance.qualityMonitor.lastLog.bin.type

       Possibilities:
               fd   (1)
               fdr   (2)
               notInUse   (3)
               ifdv   (4)"
   ::= {pr1646v2EthOamQualityMonitorLastLogBinEntry 520093696}

pr1646v2EthOamQualityMonitorLastLogBinMinMin OBJECT-TYPE
   SYNTAX      Counter32
   MAX-ACCESS  read-only
   STATUS      current
   DESCRIPTION
      "Path: ethOam.performance.qualityMonitor.lastLog.bin.minMin

       32 bit unsigned wrappable counter."
   ::= {pr1646v2EthOamQualityMonitorLastLogBinEntry 16777216}

pr1646v2EthOamQualityMonitorLastLogBinMin OBJECT-TYPE
   SYNTAX      Integer32
   MAX-ACCESS  read-only
   STATUS      current
   DESCRIPTION
      "Path: ethOam.performance.qualityMonitor.lastLog.bin.min

       unit name = sec
       formula = 1000 / ; 1000 *"
   ::= {pr1646v2EthOamQualityMonitorLastLogBinEntry 352321536}

pr1646v2EthOamQualityMonitorLastLogBinMinBin1 OBJECT-TYPE
   SYNTAX      Counter32
   MAX-ACCESS  read-only
   STATUS      current
   DESCRIPTION
      "Path: ethOam.performance.qualityMonitor.lastLog.bin.minBin1

       32 bit unsigned wrappable counter."
   ::= {pr1646v2EthOamQualityMonitorLastLogBinEntry 33554432}

pr1646v2EthOamQualityMonitorLastLogBinBin2 OBJECT-TYPE
   SYNTAX      Counter32
   MAX-ACCESS  read-only
   STATUS      current
   DESCRIPTION
      "Path: ethOam.performance.qualityMonitor.lastLog.bin.bin2

       32 bit unsigned wrappable counter."
   ::= {pr1646v2EthOamQualityMonitorLastLogBinEntry 50331648}

pr1646v2EthOamQualityMonitorLastLogBinBin3 OBJECT-TYPE
   SYNTAX      Counter32
   MAX-ACCESS  read-only
   STATUS      current
   DESCRIPTION
      "Path: ethOam.performance.qualityMonitor.lastLog.bin.bin3

       32 bit unsigned wrappable counter."
   ::= {pr1646v2EthOamQualityMonitorLastLogBinEntry 67108864}

pr1646v2EthOamQualityMonitorLastLogBinBin4 OBJECT-TYPE
   SYNTAX      Counter32
   MAX-ACCESS  read-only
   STATUS      current
   DESCRIPTION
      "Path: ethOam.performance.qualityMonitor.lastLog.bin.bin4

       32 bit unsigned wrappable counter."
   ::= {pr1646v2EthOamQualityMonitorLastLogBinEntry 83886080}

pr1646v2EthOamQualityMonitorLastLogBinBin5 OBJECT-TYPE
   SYNTAX      Counter32
   MAX-ACCESS  read-only
   STATUS      current
   DESCRIPTION
      "Path: ethOam.performance.qualityMonitor.lastLog.bin.bin5

       32 bit unsigned wrappable counter."
   ::= {pr1646v2EthOamQualityMonitorLastLogBinEntry 100663296}

pr1646v2EthOamQualityMonitorLastLogBinBin6 OBJECT-TYPE
   SYNTAX      Counter32
   MAX-ACCESS  read-only
   STATUS      current
   DESCRIPTION
      "Path: ethOam.performance.qualityMonitor.lastLog.bin.bin6

       32 bit unsigned wrappable counter."
   ::= {pr1646v2EthOamQualityMonitorLastLogBinEntry 117440512}

pr1646v2EthOamQualityMonitorLastLogBinBin7 OBJECT-TYPE
   SYNTAX      Counter32
   MAX-ACCESS  read-only
   STATUS      current
   DESCRIPTION
      "Path: ethOam.performance.qualityMonitor.lastLog.bin.bin7

       32 bit unsigned wrappable counter."
   ::= {pr1646v2EthOamQualityMonitorLastLogBinEntry 134217728}

pr1646v2EthOamQualityMonitorLastLogBinMaxBin8 OBJECT-TYPE
   SYNTAX      Counter32
   MAX-ACCESS  read-only
   STATUS      current
   DESCRIPTION
      "Path: ethOam.performance.qualityMonitor.lastLog.bin.maxBin8

       32 bit unsigned wrappable counter."
   ::= {pr1646v2EthOamQualityMonitorLastLogBinEntry 150994944}

pr1646v2EthOamQualityMonitorLastLogBinMax OBJECT-TYPE
   SYNTAX      Integer32
   MAX-ACCESS  read-only
   STATUS      current
   DESCRIPTION
      "Path: ethOam.performance.qualityMonitor.lastLog.bin.max

       unit name = sec
       formula = 1000 / ; 1000 *"
   ::= {pr1646v2EthOamQualityMonitorLastLogBinEntry 369098752}

pr1646v2EthOamQualityMonitorLastLogBinPlusMax OBJECT-TYPE
   SYNTAX      Counter32
   MAX-ACCESS  read-only
   STATUS      current
   DESCRIPTION
      "Path: ethOam.performance.qualityMonitor.lastLog.bin.plusMax

       32 bit unsigned wrappable counter."
   ::= {pr1646v2EthOamQualityMonitorLastLogBinEntry 167772160}


pr1646v2EthOamLoss OBJECT IDENTIFIER ::= {pr1646v2EthOam 21}

pr1646v2EthOamLossSSCTable OBJECT-TYPE
   SYNTAX      SEQUENCE OF Pr1646v2EthOamLossEntry
   MAX-ACCESS  not-accessible
   STATUS      current
   DESCRIPTION
      "frame loss performance table"
   ::= {pr1646v2EthOamLoss 1}

pr1646v2EthOamLossEntry OBJECT-TYPE
   SYNTAX      Pr1646v2EthOamLossEntry
   MAX-ACCESS  not-accessible
   STATUS      current
   DESCRIPTION
      ""
   INDEX      { pr1646v2EthOamLossGlobalIx,
                pr1646v2EthOamLossTableIx }
   ::= {pr1646v2EthOamLossSSCTable 1}

Pr1646v2EthOamLossEntry ::=
   SEQUENCE
      {
      pr1646v2EthOamLossGlobalIx
         GlobalIndex,
      pr1646v2EthOamLossTableIx
         TableIndex,
      pr1646v2EthOamLossMepName
         DisplayString,
      pr1646v2EthOamLossMegLevel
         Integer32,
      pr1646v2EthOamLossMegIdMaintDomainName
         DisplayString,
      pr1646v2EthOamLossMegIdShortMaName
         DisplayString,
      pr1646v2EthOamLossMepId
         INTEGER,
      pr1646v2EthOamLossMacAddress
         OCTET STRING,
      pr1646v2EthOamLossPriority
         Integer32,
      pr1646v2EthOamLossNbrOfTxFrames
         Counter32,
      pr1646v2EthOamLossNbrOfRxFrames
         Counter32,
      pr1646v2EthOamLossLoss
         Counter32,
      pr1646v2EthOamLossNearEndDrops
         Integer32,
      pr1646v2EthOamLossFarEndDrops
         Integer32
      }

pr1646v2EthOamLossGlobalIx OBJECT-TYPE
   SYNTAX      GlobalIndex
   MAX-ACCESS  not-accessible
   STATUS      current
   DESCRIPTION
      "The value of the tlsCntTreeGlobalIndex of the MANAGED OBJECT."
   ::= {pr1646v2EthOamLossEntry 10}

pr1646v2EthOamLossTableIx OBJECT-TYPE
   SYNTAX      TableIndex
   MAX-ACCESS  not-accessible
   STATUS      current
   DESCRIPTION
      ""
   ::= {pr1646v2EthOamLossEntry 11}

pr1646v2EthOamLossMepName OBJECT-TYPE
   SYNTAX      DisplayString
   MAX-ACCESS  read-only
   STATUS      current
   DESCRIPTION
      "Path: ethOam.performance.loss.mepName"
   ::= {pr1646v2EthOamLossEntry 16777216}

pr1646v2EthOamLossMegLevel OBJECT-TYPE
   SYNTAX      Integer32
   MAX-ACCESS  read-only
   STATUS      current
   DESCRIPTION
      "Path: ethOam.performance.loss.megLevel"
   ::= {pr1646v2EthOamLossEntry 33554432}

pr1646v2EthOamLossMegIdMaintDomainName OBJECT-TYPE
   SYNTAX      DisplayString
   MAX-ACCESS  read-only
   STATUS      current
   DESCRIPTION
      "Path: ethOam.performance.loss.megId.maintDomainName"
   ::= {pr1646v2EthOamLossEntry 50397184}

pr1646v2EthOamLossMegIdShortMaName OBJECT-TYPE
   SYNTAX      DisplayString
   MAX-ACCESS  read-only
   STATUS      current
   DESCRIPTION
      "Path: ethOam.performance.loss.megId.shortMaName"
   ::= {pr1646v2EthOamLossEntry 50462720}

pr1646v2EthOamLossMepId OBJECT-TYPE
   SYNTAX      INTEGER
               {
               unknown (8192)
               }
   MAX-ACCESS  read-only
   STATUS      current
   DESCRIPTION
      "Path: ethOam.performance.loss.mepId

       Possibilities:
               unknown   (8192)"
   ::= {pr1646v2EthOamLossEntry 67108864}

pr1646v2EthOamLossMacAddress OBJECT-TYPE
   SYNTAX      OCTET STRING
   MAX-ACCESS  read-only
   STATUS      current
   DESCRIPTION
      "Path: ethOam.performance.loss.macAddress

       MAC address."
   ::= {pr1646v2EthOamLossEntry 83886080}

pr1646v2EthOamLossPriority OBJECT-TYPE
   SYNTAX      Integer32
   MAX-ACCESS  read-only
   STATUS      current
   DESCRIPTION
      "Path: ethOam.performance.loss.priority"
   ::= {pr1646v2EthOamLossEntry 100663296}

pr1646v2EthOamLossNbrOfTxFrames OBJECT-TYPE
   SYNTAX      Counter32
   MAX-ACCESS  read-only
   STATUS      current
   DESCRIPTION
      "Path: ethOam.performance.loss.nbrOfTxFrames

       32 bit unsigned wrappable counter."
   ::= {pr1646v2EthOamLossEntry 117440512}

pr1646v2EthOamLossNbrOfRxFrames OBJECT-TYPE
   SYNTAX      Counter32
   MAX-ACCESS  read-only
   STATUS      current
   DESCRIPTION
      "Path: ethOam.performance.loss.nbrOfRxFrames

       32 bit unsigned wrappable counter."
   ::= {pr1646v2EthOamLossEntry 134217728}

pr1646v2EthOamLossLoss OBJECT-TYPE
   SYNTAX      Counter32
   MAX-ACCESS  read-only
   STATUS      current
   DESCRIPTION
      "Path: ethOam.performance.loss.loss

       32 bit unsigned wrappable counter."
   ::= {pr1646v2EthOamLossEntry 201326592}

pr1646v2EthOamLossNearEndDrops OBJECT-TYPE
   SYNTAX      Integer32
   MAX-ACCESS  read-only
   STATUS      current
   DESCRIPTION
      "Path: ethOam.performance.loss.nearEndDrops"
   ::= {pr1646v2EthOamLossEntry 150994944}

pr1646v2EthOamLossFarEndDrops OBJECT-TYPE
   SYNTAX      Integer32
   MAX-ACCESS  read-only
   STATUS      current
   DESCRIPTION
      "Path: ethOam.performance.loss.farEndDrops"
   ::= {pr1646v2EthOamLossEntry 167772160}

pr1646v2EthOamLossLogging OBJECT-TYPE
   SYNTAX      SEQUENCE OF Pr1646v2EthOamLossLoggingEntry
   MAX-ACCESS  not-accessible
   STATUS      current
   DESCRIPTION
      ""
   ::= {pr1646v2EthOamLoss 184549376}

pr1646v2EthOamLossLoggingEntry OBJECT-TYPE
   SYNTAX      Pr1646v2EthOamLossLoggingEntry
   MAX-ACCESS  not-accessible
   STATUS      current
   DESCRIPTION
      ""
   INDEX      { pr1646v2EthOamLossLoggingGlobalIx,
                pr1646v2EthOamLossTableIx,
                pr1646v2EthOamLossLoggingTableIx }
   ::= {pr1646v2EthOamLossLogging 1}

Pr1646v2EthOamLossLoggingEntry ::=
   SEQUENCE
      {
      pr1646v2EthOamLossLoggingGlobalIx
         GlobalIndex,
      pr1646v2EthOamLossLoggingTableIx
         TableIndex,
      pr1646v2EthOamLossLoggingSysUpTime
         TimeTicks,
      pr1646v2EthOamLossLoggingNbrTxFrm
         Counter32,
      pr1646v2EthOamLossLoggingNbrRxFrm
         Counter32,
      pr1646v2EthOamLossLoggingLoss
         Counter32,
      pr1646v2EthOamLossLoggingNearEndDrops
         Integer32,
      pr1646v2EthOamLossLoggingFarEndDrops
         Integer32
      }

pr1646v2EthOamLossLoggingGlobalIx OBJECT-TYPE
   SYNTAX      GlobalIndex
   MAX-ACCESS  not-accessible
   STATUS      current
   DESCRIPTION
      "The value of the tlsCntTreeGlobalIndex of the MANAGED OBJECT."
   ::= {pr1646v2EthOamLossLoggingEntry 10}

pr1646v2EthOamLossLoggingTableIx OBJECT-TYPE
   SYNTAX      TableIndex
   MAX-ACCESS  not-accessible
   STATUS      current
   DESCRIPTION
      ""
   ::= {pr1646v2EthOamLossLoggingEntry 11}

pr1646v2EthOamLossLoggingSysUpTime OBJECT-TYPE
   SYNTAX      TimeTicks
   MAX-ACCESS  read-only
   STATUS      current
   DESCRIPTION
      "Path: ethOam.performance.loss.logging.sysUpTime

       Time in centi-second."
   ::= {pr1646v2EthOamLossLoggingEntry 16777216}

pr1646v2EthOamLossLoggingNbrTxFrm OBJECT-TYPE
   SYNTAX      Counter32
   MAX-ACCESS  read-only
   STATUS      current
   DESCRIPTION
      "Path: ethOam.performance.loss.logging.nbrOfTxFrames

       32 bit unsigned wrappable counter."
   ::= {pr1646v2EthOamLossLoggingEntry 33554432}

pr1646v2EthOamLossLoggingNbrRxFrm OBJECT-TYPE
   SYNTAX      Counter32
   MAX-ACCESS  read-only
   STATUS      current
   DESCRIPTION
      "Path: ethOam.performance.loss.logging.nbrOfRxFrames

       32 bit unsigned wrappable counter."
   ::= {pr1646v2EthOamLossLoggingEntry 50331648}

pr1646v2EthOamLossLoggingLoss OBJECT-TYPE
   SYNTAX      Counter32
   MAX-ACCESS  read-only
   STATUS      current
   DESCRIPTION
      "Path: ethOam.performance.loss.logging.loss

       32 bit unsigned wrappable counter."
   ::= {pr1646v2EthOamLossLoggingEntry 67108864}

pr1646v2EthOamLossLoggingNearEndDrops OBJECT-TYPE
   SYNTAX      Integer32
   MAX-ACCESS  read-only
   STATUS      current
   DESCRIPTION
      "Path: ethOam.performance.loss.logging.nearEndDrops"
   ::= {pr1646v2EthOamLossLoggingEntry 150994944}

pr1646v2EthOamLossLoggingFarEndDrops OBJECT-TYPE
   SYNTAX      Integer32
   MAX-ACCESS  read-only
   STATUS      current
   DESCRIPTION
      "Path: ethOam.performance.loss.logging.farEndDrops"
   ::= {pr1646v2EthOamLossLoggingEntry 167772160}


pr1646v2EthOamDelay OBJECT IDENTIFIER ::= {pr1646v2EthOam 22}

pr1646v2EthOamDelaySSCTable OBJECT-TYPE
   SYNTAX      SEQUENCE OF Pr1646v2EthOamDelayEntry
   MAX-ACCESS  not-accessible
   STATUS      current
   DESCRIPTION
      "frame delay performance table"
   ::= {pr1646v2EthOamDelay 1}

pr1646v2EthOamDelayEntry OBJECT-TYPE
   SYNTAX      Pr1646v2EthOamDelayEntry
   MAX-ACCESS  not-accessible
   STATUS      current
   DESCRIPTION
      ""
   INDEX      { pr1646v2EthOamDelayGlobalIx,
                pr1646v2EthOamDelayTableIx }
   ::= {pr1646v2EthOamDelaySSCTable 1}

Pr1646v2EthOamDelayEntry ::=
   SEQUENCE
      {
      pr1646v2EthOamDelayGlobalIx
         GlobalIndex,
      pr1646v2EthOamDelayTableIx
         TableIndex,
      pr1646v2EthOamDelayMepName
         DisplayString,
      pr1646v2EthOamDelayMegLevel
         Integer32,
      pr1646v2EthOamDelayMegIdMaintDomainName
         DisplayString,
      pr1646v2EthOamDelayMegIdShortMaName
         DisplayString,
      pr1646v2EthOamDelayMepId
         INTEGER,
      pr1646v2EthOamDelayMacAddress
         OCTET STRING,
      pr1646v2EthOamDelayPriority
         Integer32,
      pr1646v2EthOamDelayNbrOfTxFrames
         Counter32,
      pr1646v2EthOamDelayNbrOfRxFrames
         Counter32,
      pr1646v2EthOamDelayLoss
         Counter32,
      pr1646v2EthOamDelayDelayMin
         Integer32,
      pr1646v2EthOamDelayDelayAvrg
         Integer32,
      pr1646v2EthOamDelayDelayMax
         Integer32,
      pr1646v2EthOamDelayJitterNegMax
         Integer32,
      pr1646v2EthOamDelayJitterAvrg
         Integer32,
      pr1646v2EthOamDelayJitterPosMax
         Integer32
      }

pr1646v2EthOamDelayGlobalIx OBJECT-TYPE
   SYNTAX      GlobalIndex
   MAX-ACCESS  not-accessible
   STATUS      current
   DESCRIPTION
      "The value of the tlsCntTreeGlobalIndex of the MANAGED OBJECT."
   ::= {pr1646v2EthOamDelayEntry 10}

pr1646v2EthOamDelayTableIx OBJECT-TYPE
   SYNTAX      TableIndex
   MAX-ACCESS  not-accessible
   STATUS      current
   DESCRIPTION
      ""
   ::= {pr1646v2EthOamDelayEntry 11}

pr1646v2EthOamDelayMepName OBJECT-TYPE
   SYNTAX      DisplayString
   MAX-ACCESS  read-only
   STATUS      current
   DESCRIPTION
      "Path: ethOam.performance.delay.mepName"
   ::= {pr1646v2EthOamDelayEntry 16777216}

pr1646v2EthOamDelayMegLevel OBJECT-TYPE
   SYNTAX      Integer32
   MAX-ACCESS  read-only
   STATUS      current
   DESCRIPTION
      "Path: ethOam.performance.delay.megLevel"
   ::= {pr1646v2EthOamDelayEntry 33554432}

pr1646v2EthOamDelayMegIdMaintDomainName OBJECT-TYPE
   SYNTAX      DisplayString
   MAX-ACCESS  read-only
   STATUS      current
   DESCRIPTION
      "Path: ethOam.performance.delay.megId.maintDomainName"
   ::= {pr1646v2EthOamDelayEntry 50397184}

pr1646v2EthOamDelayMegIdShortMaName OBJECT-TYPE
   SYNTAX      DisplayString
   MAX-ACCESS  read-only
   STATUS      current
   DESCRIPTION
      "Path: ethOam.performance.delay.megId.shortMaName"
   ::= {pr1646v2EthOamDelayEntry 50462720}

pr1646v2EthOamDelayMepId OBJECT-TYPE
   SYNTAX      INTEGER
               {
               unknown (8192)
               }
   MAX-ACCESS  read-only
   STATUS      current
   DESCRIPTION
      "Path: ethOam.performance.delay.mepId

       Possibilities:
               unknown   (8192)"
   ::= {pr1646v2EthOamDelayEntry 67108864}

pr1646v2EthOamDelayMacAddress OBJECT-TYPE
   SYNTAX      OCTET STRING
   MAX-ACCESS  read-only
   STATUS      current
   DESCRIPTION
      "Path: ethOam.performance.delay.macAddress

       MAC address."
   ::= {pr1646v2EthOamDelayEntry 83886080}

pr1646v2EthOamDelayPriority OBJECT-TYPE
   SYNTAX      Integer32
   MAX-ACCESS  read-only
   STATUS      current
   DESCRIPTION
      "Path: ethOam.performance.delay.priority"
   ::= {pr1646v2EthOamDelayEntry 100663296}

pr1646v2EthOamDelayNbrOfTxFrames OBJECT-TYPE
   SYNTAX      Counter32
   MAX-ACCESS  read-only
   STATUS      current
   DESCRIPTION
      "Path: ethOam.performance.delay.nbrOfTxFrames

       32 bit unsigned wrappable counter."
   ::= {pr1646v2EthOamDelayEntry 117440512}

pr1646v2EthOamDelayNbrOfRxFrames OBJECT-TYPE
   SYNTAX      Counter32
   MAX-ACCESS  read-only
   STATUS      current
   DESCRIPTION
      "Path: ethOam.performance.delay.nbrOfRxFrames

       32 bit unsigned wrappable counter."
   ::= {pr1646v2EthOamDelayEntry 134217728}

pr1646v2EthOamDelayLoss OBJECT-TYPE
   SYNTAX      Counter32
   MAX-ACCESS  read-only
   STATUS      current
   DESCRIPTION
      "Path: ethOam.performance.delay.loss

       32 bit unsigned wrappable counter."
   ::= {pr1646v2EthOamDelayEntry 150994944}

pr1646v2EthOamDelayDelayMin OBJECT-TYPE
   SYNTAX      Integer32
   MAX-ACCESS  read-only
   STATUS      current
   DESCRIPTION
      "Path: ethOam.performance.delay.delayMin

       unit name = sec
       formula = 1000 / ; 1000 *"
   ::= {pr1646v2EthOamDelayEntry 184549376}

pr1646v2EthOamDelayDelayAvrg OBJECT-TYPE
   SYNTAX      Integer32
   MAX-ACCESS  read-only
   STATUS      current
   DESCRIPTION
      "Path: ethOam.performance.delay.delayAvrg

       unit name = sec
       formula = 1000 / ; 1000 *"
   ::= {pr1646v2EthOamDelayEntry 201326592}

pr1646v2EthOamDelayDelayMax OBJECT-TYPE
   SYNTAX      Integer32
   MAX-ACCESS  read-only
   STATUS      current
   DESCRIPTION
      "Path: ethOam.performance.delay.delayMax

       unit name = sec
       formula = 1000 / ; 1000 *"
   ::= {pr1646v2EthOamDelayEntry 218103808}

pr1646v2EthOamDelayJitterNegMax OBJECT-TYPE
   SYNTAX      Integer32
   MAX-ACCESS  read-only
   STATUS      current
   DESCRIPTION
      "Path: ethOam.performance.delay.jitterNegMax

       unit name = sec
       formula = 1000 / ; 1000 *"
   ::= {pr1646v2EthOamDelayEntry 234881024}

pr1646v2EthOamDelayJitterAvrg OBJECT-TYPE
   SYNTAX      Integer32
   MAX-ACCESS  read-only
   STATUS      current
   DESCRIPTION
      "Path: ethOam.performance.delay.jitterAvrg

       unit name = sec
       formula = 1000 / ; 1000 *"
   ::= {pr1646v2EthOamDelayEntry 251658240}

pr1646v2EthOamDelayJitterPosMax OBJECT-TYPE
   SYNTAX      Integer32
   MAX-ACCESS  read-only
   STATUS      current
   DESCRIPTION
      "Path: ethOam.performance.delay.jitterPosMax

       unit name = sec
       formula = 1000 / ; 1000 *"
   ::= {pr1646v2EthOamDelayEntry 268435456}

pr1646v2EthOamDelayLogging OBJECT-TYPE
   SYNTAX      SEQUENCE OF Pr1646v2EthOamDelayLoggingEntry
   MAX-ACCESS  not-accessible
   STATUS      current
   DESCRIPTION
      ""
   ::= {pr1646v2EthOamDelay 285212672}

pr1646v2EthOamDelayLoggingEntry OBJECT-TYPE
   SYNTAX      Pr1646v2EthOamDelayLoggingEntry
   MAX-ACCESS  not-accessible
   STATUS      current
   DESCRIPTION
      ""
   INDEX      { pr1646v2EthOamDelayLoggingGlobalIx,
                pr1646v2EthOamDelayTableIx,
                pr1646v2EthOamDelayLoggingTableIx }
   ::= {pr1646v2EthOamDelayLogging 1}

Pr1646v2EthOamDelayLoggingEntry ::=
   SEQUENCE
      {
      pr1646v2EthOamDelayLoggingGlobalIx
         GlobalIndex,
      pr1646v2EthOamDelayLoggingTableIx
         TableIndex,
      pr1646v2EthOamDelayLoggingSysUpTime
         TimeTicks,
      pr1646v2EthOamDelayLoggingNbrTxFrm
         Counter32,
      pr1646v2EthOamDelayLoggingNbrRxFrm
         Counter32,
      pr1646v2EthOamDelayLoggingLoss
         Counter32,
      pr1646v2EthOamDelayLoggingDelayMin
         Integer32,
      pr1646v2EthOamDelayLoggingDelayAvrg
         Integer32,
      pr1646v2EthOamDelayLoggingDelayMax
         Integer32,
      pr1646v2EthOamDelayLoggingJitterNegMax
         Integer32,
      pr1646v2EthOamDelayLoggingJitterAvrg
         Integer32,
      pr1646v2EthOamDelayLoggingJitterPosMax
         Integer32
      }

pr1646v2EthOamDelayLoggingGlobalIx OBJECT-TYPE
   SYNTAX      GlobalIndex
   MAX-ACCESS  not-accessible
   STATUS      current
   DESCRIPTION
      "The value of the tlsCntTreeGlobalIndex of the MANAGED OBJECT."
   ::= {pr1646v2EthOamDelayLoggingEntry 10}

pr1646v2EthOamDelayLoggingTableIx OBJECT-TYPE
   SYNTAX      TableIndex
   MAX-ACCESS  not-accessible
   STATUS      current
   DESCRIPTION
      ""
   ::= {pr1646v2EthOamDelayLoggingEntry 11}

pr1646v2EthOamDelayLoggingSysUpTime OBJECT-TYPE
   SYNTAX      TimeTicks
   MAX-ACCESS  read-only
   STATUS      current
   DESCRIPTION
      "Path: ethOam.performance.delay.logging.sysUpTime

       Time in centi-second."
   ::= {pr1646v2EthOamDelayLoggingEntry 16777216}

pr1646v2EthOamDelayLoggingNbrTxFrm OBJECT-TYPE
   SYNTAX      Counter32
   MAX-ACCESS  read-only
   STATUS      current
   DESCRIPTION
      "Path: ethOam.performance.delay.logging.nbrOfTxFrames

       32 bit unsigned wrappable counter."
   ::= {pr1646v2EthOamDelayLoggingEntry 33554432}

pr1646v2EthOamDelayLoggingNbrRxFrm OBJECT-TYPE
   SYNTAX      Counter32
   MAX-ACCESS  read-only
   STATUS      current
   DESCRIPTION
      "Path: ethOam.performance.delay.logging.nbrOfRxFrames

       32 bit unsigned wrappable counter."
   ::= {pr1646v2EthOamDelayLoggingEntry 50331648}

pr1646v2EthOamDelayLoggingLoss OBJECT-TYPE
   SYNTAX      Counter32
   MAX-ACCESS  read-only
   STATUS      current
   DESCRIPTION
      "Path: ethOam.performance.delay.logging.loss

       32 bit unsigned wrappable counter."
   ::= {pr1646v2EthOamDelayLoggingEntry 67108864}

pr1646v2EthOamDelayLoggingDelayMin OBJECT-TYPE
   SYNTAX      Integer32
   MAX-ACCESS  read-only
   STATUS      current
   DESCRIPTION
      "Path: ethOam.performance.delay.logging.delayMin

       unit name = sec
       formula = 1000 / ; 1000 *"
   ::= {pr1646v2EthOamDelayLoggingEntry 100663296}

pr1646v2EthOamDelayLoggingDelayAvrg OBJECT-TYPE
   SYNTAX      Integer32
   MAX-ACCESS  read-only
   STATUS      current
   DESCRIPTION
      "Path: ethOam.performance.delay.logging.delayAvrg

       unit name = sec
       formula = 1000 / ; 1000 *"
   ::= {pr1646v2EthOamDelayLoggingEntry 117440512}

pr1646v2EthOamDelayLoggingDelayMax OBJECT-TYPE
   SYNTAX      Integer32
   MAX-ACCESS  read-only
   STATUS      current
   DESCRIPTION
      "Path: ethOam.performance.delay.logging.delayMax

       unit name = sec
       formula = 1000 / ; 1000 *"
   ::= {pr1646v2EthOamDelayLoggingEntry 134217728}

pr1646v2EthOamDelayLoggingJitterNegMax OBJECT-TYPE
   SYNTAX      Integer32
   MAX-ACCESS  read-only
   STATUS      current
   DESCRIPTION
      "Path: ethOam.performance.delay.logging.jitterNegMax

       unit name = sec
       formula = 1000 / ; 1000 *"
   ::= {pr1646v2EthOamDelayLoggingEntry 150994944}

pr1646v2EthOamDelayLoggingJitterAvrg OBJECT-TYPE
   SYNTAX      Integer32
   MAX-ACCESS  read-only
   STATUS      current
   DESCRIPTION
      "Path: ethOam.performance.delay.logging.jitterAvrg

       unit name = sec
       formula = 1000 / ; 1000 *"
   ::= {pr1646v2EthOamDelayLoggingEntry 167772160}

pr1646v2EthOamDelayLoggingJitterPosMax OBJECT-TYPE
   SYNTAX      Integer32
   MAX-ACCESS  read-only
   STATUS      current
   DESCRIPTION
      "Path: ethOam.performance.delay.logging.jitterPosMax

       unit name = sec
       formula = 1000 / ; 1000 *"
   ::= {pr1646v2EthOamDelayLoggingEntry 184549376}


pr1646v2EthOamSlmPerf OBJECT IDENTIFIER ::= {pr1646v2EthOam 41}

pr1646v2EthOamSlmPerfSSCTable OBJECT-TYPE
   SYNTAX      SEQUENCE OF Pr1646v2EthOamSlmPerfEntry
   MAX-ACCESS  not-accessible
   STATUS      current
   DESCRIPTION
      "synthetic loss performance table"
   ::= {pr1646v2EthOamSlmPerf 1}

pr1646v2EthOamSlmPerfEntry OBJECT-TYPE
   SYNTAX      Pr1646v2EthOamSlmPerfEntry
   MAX-ACCESS  not-accessible
   STATUS      current
   DESCRIPTION
      ""
   INDEX      { pr1646v2EthOamSlmPerfGlobalIx,
                pr1646v2EthOamSlmPerfTableIx }
   ::= {pr1646v2EthOamSlmPerfSSCTable 1}

Pr1646v2EthOamSlmPerfEntry ::=
   SEQUENCE
      {
      pr1646v2EthOamSlmPerfGlobalIx
         GlobalIndex,
      pr1646v2EthOamSlmPerfTableIx
         TableIndex,
      pr1646v2EthOamSlmPerfName
         DisplayString,
      pr1646v2EthOamSlmPerfStatus
         INTEGER,
      pr1646v2EthOamSlmPerfMepName
         DisplayString,
      pr1646v2EthOamSlmPerfMegLevel
         Integer32,
      pr1646v2EthOamSlmPerfMegIdMaintDomainName
         DisplayString,
      pr1646v2EthOamSlmPerfMegIdShortMaName
         DisplayString,
      pr1646v2EthOamSlmPerfMepId
         INTEGER,
      pr1646v2EthOamSlmPerfMacAddress
         OCTET STRING,
      pr1646v2EthOamSlmPerfPriority
         Integer32,
      pr1646v2EthOamSlmPerfRsltSingleCurrentTx
         Counter32,
      pr1646v2EthOamSlmPerfRsltSingleCurrentRx
         Counter32,
      pr1646v2EthOamSlmPerfRsltSingleCurrentBad
         Counter32,
      pr1646v2EthOamSlmPerfRsltSingleCurrentLate
         Counter32,
      pr1646v2EthOamSlmPerfRsltSingleCurrentTxfcf
         Counter32,
      pr1646v2EthOamSlmPerfRsltSingleCurrentDupslm
         Counter32,
      pr1646v2EthOamSlmPerfRsltSingleCurrentDupslr
         Counter32,
      pr1646v2EthOamSlmPerfRsltSingleCurrentSeqslm
         Counter32,
      pr1646v2EthOamSlmPerfRsltSingleCurrentSeqslr
         Counter32,
      pr1646v2EthOamSlmPerfRsltSingleCurrentNeLoss
         INTEGER,
      pr1646v2EthOamSlmPerfRsltSingleCurrentFeLoss
         INTEGER,
      pr1646v2EthOamSlmPerfRsltSingleOverallTx
         Counter32,
      pr1646v2EthOamSlmPerfRsltSingleOverallRx
         Counter32,
      pr1646v2EthOamSlmPerfRsltSingleOverallBad
         Counter32,
      pr1646v2EthOamSlmPerfRsltSingleOverallLate
         Counter32,
      pr1646v2EthOamSlmPerfRsltSingleOverallTxfcf
         Counter32,
      pr1646v2EthOamSlmPerfRsltSingleOverallDupslm
         Counter32,
      pr1646v2EthOamSlmPerfRsltSingleOverallDupslr
         Counter32,
      pr1646v2EthOamSlmPerfRsltSingleOverallSeqslm
         Counter32,
      pr1646v2EthOamSlmPerfRsltSingleOverallSeqslr
         Counter32,
      pr1646v2EthOamSlmPerfRsltSingleOverallFail
         Counter32,
      pr1646v2EthOamSlmPerfRsltSingleOverallNeLoss
         INTEGER,
      pr1646v2EthOamSlmPerfRsltSingleOverallFeLoss
         INTEGER,
      pr1646v2EthOamSlmPerfRsltDualNbrOfTxFrames
         Counter32,
      pr1646v2EthOamSlmPerfRsltDualNbrOfTxFramesOverall
         Counter32
      }

pr1646v2EthOamSlmPerfGlobalIx OBJECT-TYPE
   SYNTAX      GlobalIndex
   MAX-ACCESS  not-accessible
   STATUS      current
   DESCRIPTION
      "The value of the tlsCntTreeGlobalIndex of the MANAGED OBJECT."
   ::= {pr1646v2EthOamSlmPerfEntry 10}

pr1646v2EthOamSlmPerfTableIx OBJECT-TYPE
   SYNTAX      TableIndex
   MAX-ACCESS  not-accessible
   STATUS      current
   DESCRIPTION
      ""
   ::= {pr1646v2EthOamSlmPerfEntry 11}

pr1646v2EthOamSlmPerfName OBJECT-TYPE
   SYNTAX      DisplayString
   MAX-ACCESS  read-only
   STATUS      current
   DESCRIPTION
      "Path: ethOam.performance.synthLoss.name"
   ::= {pr1646v2EthOamSlmPerfEntry 134217728}

pr1646v2EthOamSlmPerfStatus OBJECT-TYPE
   SYNTAX      INTEGER
               {
               running (1),
               notRunning (2),
               waiting (3)
               }
   MAX-ACCESS  read-only
   STATUS      current
   DESCRIPTION
      "Path: ethOam.performance.synthLoss.status

       Possibilities:
               running   (1)
               notRunning   (2)
               waiting   (3)"
   ::= {pr1646v2EthOamSlmPerfEntry 150994944}

pr1646v2EthOamSlmPerfMepName OBJECT-TYPE
   SYNTAX      DisplayString
   MAX-ACCESS  read-only
   STATUS      current
   DESCRIPTION
      "Path: ethOam.performance.synthLoss.mepName"
   ::= {pr1646v2EthOamSlmPerfEntry 16777216}

pr1646v2EthOamSlmPerfMegLevel OBJECT-TYPE
   SYNTAX      Integer32
   MAX-ACCESS  read-only
   STATUS      current
   DESCRIPTION
      "Path: ethOam.performance.synthLoss.megLevel"
   ::= {pr1646v2EthOamSlmPerfEntry 33554432}

pr1646v2EthOamSlmPerfMegIdMaintDomainName OBJECT-TYPE
   SYNTAX      DisplayString
   MAX-ACCESS  read-only
   STATUS      current
   DESCRIPTION
      "Path: ethOam.performance.synthLoss.megId.maintDomainName"
   ::= {pr1646v2EthOamSlmPerfEntry 50397184}

pr1646v2EthOamSlmPerfMegIdShortMaName OBJECT-TYPE
   SYNTAX      DisplayString
   MAX-ACCESS  read-only
   STATUS      current
   DESCRIPTION
      "Path: ethOam.performance.synthLoss.megId.shortMaName"
   ::= {pr1646v2EthOamSlmPerfEntry 50462720}

pr1646v2EthOamSlmPerfMepId OBJECT-TYPE
   SYNTAX      INTEGER
               {
               unknown (8192)
               }
   MAX-ACCESS  read-only
   STATUS      current
   DESCRIPTION
      "Path: ethOam.performance.synthLoss.mepId

       Possibilities:
               unknown   (8192)"
   ::= {pr1646v2EthOamSlmPerfEntry 67108864}

pr1646v2EthOamSlmPerfMacAddress OBJECT-TYPE
   SYNTAX      OCTET STRING
   MAX-ACCESS  read-only
   STATUS      current
   DESCRIPTION
      "Path: ethOam.performance.synthLoss.macAddress

       MAC address."
   ::= {pr1646v2EthOamSlmPerfEntry 83886080}

pr1646v2EthOamSlmPerfPriority OBJECT-TYPE
   SYNTAX      Integer32
   MAX-ACCESS  read-only
   STATUS      current
   DESCRIPTION
      "Path: ethOam.performance.synthLoss.priority"
   ::= {pr1646v2EthOamSlmPerfEntry 100663296}

pr1646v2EthOamSlmPerfRsltSingleCurrentTx OBJECT-TYPE
   SYNTAX      Counter32
   MAX-ACCESS  read-only
   STATUS      current
   DESCRIPTION
      "Path: ethOam.performance.synthLoss.result.singleEnded.current.nbrOfTxFrames

       32 bit unsigned wrappable counter."
   ::= {pr1646v2EthOamSlmPerfEntry 117506305}

pr1646v2EthOamSlmPerfRsltSingleCurrentRx OBJECT-TYPE
   SYNTAX      Counter32
   MAX-ACCESS  read-only
   STATUS      current
   DESCRIPTION
      "Path: ethOam.performance.synthLoss.result.singleEnded.current.nbrOfRxFrames

       32 bit unsigned wrappable counter."
   ::= {pr1646v2EthOamSlmPerfEntry 117506306}

pr1646v2EthOamSlmPerfRsltSingleCurrentBad OBJECT-TYPE
   SYNTAX      Counter32
   MAX-ACCESS  read-only
   STATUS      current
   DESCRIPTION
      "Path: ethOam.performance.synthLoss.result.singleEnded.current.nbrOfBadDataFrames

       32 bit unsigned wrappable counter."
   ::= {pr1646v2EthOamSlmPerfEntry 117506307}

pr1646v2EthOamSlmPerfRsltSingleCurrentLate OBJECT-TYPE
   SYNTAX      Counter32
   MAX-ACCESS  read-only
   STATUS      current
   DESCRIPTION
      "Path: ethOam.performance.synthLoss.result.singleEnded.current.nbrOfLateFrames

       32 bit unsigned wrappable counter."
   ::= {pr1646v2EthOamSlmPerfEntry 117506308}

pr1646v2EthOamSlmPerfRsltSingleCurrentTxfcf OBJECT-TYPE
   SYNTAX      Counter32
   MAX-ACCESS  read-only
   STATUS      current
   DESCRIPTION
      "Path: ethOam.performance.synthLoss.result.singleEnded.current.nbrOfOutOfRangeFrames

       32 bit unsigned wrappable counter."
   ::= {pr1646v2EthOamSlmPerfEntry 117506312}

pr1646v2EthOamSlmPerfRsltSingleCurrentDupslm OBJECT-TYPE
   SYNTAX      Counter32
   MAX-ACCESS  read-only
   STATUS      current
   DESCRIPTION
      "Path: ethOam.performance.synthLoss.result.singleEnded.current.nbrOfDuplicateSlm

       32 bit unsigned wrappable counter."
   ::= {pr1646v2EthOamSlmPerfEntry 117506313}

pr1646v2EthOamSlmPerfRsltSingleCurrentDupslr OBJECT-TYPE
   SYNTAX      Counter32
   MAX-ACCESS  read-only
   STATUS      current
   DESCRIPTION
      "Path: ethOam.performance.synthLoss.result.singleEnded.current.nbrOfDuplicateSlr

       32 bit unsigned wrappable counter."
   ::= {pr1646v2EthOamSlmPerfEntry 117506314}

pr1646v2EthOamSlmPerfRsltSingleCurrentSeqslm OBJECT-TYPE
   SYNTAX      Counter32
   MAX-ACCESS  read-only
   STATUS      current
   DESCRIPTION
      "Path: ethOam.performance.synthLoss.result.singleEnded.current.nbrOfSlmSeqError

       32 bit unsigned wrappable counter."
   ::= {pr1646v2EthOamSlmPerfEntry 117506315}

pr1646v2EthOamSlmPerfRsltSingleCurrentSeqslr OBJECT-TYPE
   SYNTAX      Counter32
   MAX-ACCESS  read-only
   STATUS      current
   DESCRIPTION
      "Path: ethOam.performance.synthLoss.result.singleEnded.current.nbrOfSlrSeqError

       32 bit unsigned wrappable counter."
   ::= {pr1646v2EthOamSlmPerfEntry 117506316}

pr1646v2EthOamSlmPerfRsltSingleCurrentNeLoss OBJECT-TYPE
   SYNTAX      INTEGER
               {
               invalid (2147483647)
               }
   MAX-ACCESS  read-only
   STATUS      current
   DESCRIPTION
      "Path: ethOam.performance.synthLoss.result.singleEnded.current.nearEndLoss

       Possibilities:
               invalid   (2147483647)"
   ::= {pr1646v2EthOamSlmPerfEntry 117506310}

pr1646v2EthOamSlmPerfRsltSingleCurrentFeLoss OBJECT-TYPE
   SYNTAX      INTEGER
               {
               invalid (2147483647)
               }
   MAX-ACCESS  read-only
   STATUS      current
   DESCRIPTION
      "Path: ethOam.performance.synthLoss.result.singleEnded.current.farEndLoss

       Possibilities:
               invalid   (2147483647)"
   ::= {pr1646v2EthOamSlmPerfEntry 117506311}

pr1646v2EthOamSlmPerfRsltSingleOverallTx OBJECT-TYPE
   SYNTAX      Counter32
   MAX-ACCESS  read-only
   STATUS      current
   DESCRIPTION
      "Path: ethOam.performance.synthLoss.result.singleEnded.overall.nbrOfTxFrames

       32 bit unsigned wrappable counter."
   ::= {pr1646v2EthOamSlmPerfEntry 117506561}

pr1646v2EthOamSlmPerfRsltSingleOverallRx OBJECT-TYPE
   SYNTAX      Counter32
   MAX-ACCESS  read-only
   STATUS      current
   DESCRIPTION
      "Path: ethOam.performance.synthLoss.result.singleEnded.overall.nbrOfRxFrames

       32 bit unsigned wrappable counter."
   ::= {pr1646v2EthOamSlmPerfEntry 117506562}

pr1646v2EthOamSlmPerfRsltSingleOverallBad OBJECT-TYPE
   SYNTAX      Counter32
   MAX-ACCESS  read-only
   STATUS      current
   DESCRIPTION
      "Path: ethOam.performance.synthLoss.result.singleEnded.overall.nbrOfBadDataFrames

       32 bit unsigned wrappable counter."
   ::= {pr1646v2EthOamSlmPerfEntry 117506563}

pr1646v2EthOamSlmPerfRsltSingleOverallLate OBJECT-TYPE
   SYNTAX      Counter32
   MAX-ACCESS  read-only
   STATUS      current
   DESCRIPTION
      "Path: ethOam.performance.synthLoss.result.singleEnded.overall.nbrOfLateFrames

       32 bit unsigned wrappable counter."
   ::= {pr1646v2EthOamSlmPerfEntry 117506564}

pr1646v2EthOamSlmPerfRsltSingleOverallTxfcf OBJECT-TYPE
   SYNTAX      Counter32
   MAX-ACCESS  read-only
   STATUS      current
   DESCRIPTION
      "Path: ethOam.performance.synthLoss.result.singleEnded.overall.nbrOfOutOfRangeFrames

       32 bit unsigned wrappable counter."
   ::= {pr1646v2EthOamSlmPerfEntry 117506568}

pr1646v2EthOamSlmPerfRsltSingleOverallDupslm OBJECT-TYPE
   SYNTAX      Counter32
   MAX-ACCESS  read-only
   STATUS      current
   DESCRIPTION
      "Path: ethOam.performance.synthLoss.result.singleEnded.overall.nbrOfDuplicateSlm

       32 bit unsigned wrappable counter."
   ::= {pr1646v2EthOamSlmPerfEntry 117506569}

pr1646v2EthOamSlmPerfRsltSingleOverallDupslr OBJECT-TYPE
   SYNTAX      Counter32
   MAX-ACCESS  read-only
   STATUS      current
   DESCRIPTION
      "Path: ethOam.performance.synthLoss.result.singleEnded.overall.nbrOfDuplicateSlr

       32 bit unsigned wrappable counter."
   ::= {pr1646v2EthOamSlmPerfEntry 117506570}

pr1646v2EthOamSlmPerfRsltSingleOverallSeqslm OBJECT-TYPE
   SYNTAX      Counter32
   MAX-ACCESS  read-only
   STATUS      current
   DESCRIPTION
      "Path: ethOam.performance.synthLoss.result.singleEnded.overall.nbrOfSlmSeqError

       32 bit unsigned wrappable counter."
   ::= {pr1646v2EthOamSlmPerfEntry 117506571}

pr1646v2EthOamSlmPerfRsltSingleOverallSeqslr OBJECT-TYPE
   SYNTAX      Counter32
   MAX-ACCESS  read-only
   STATUS      current
   DESCRIPTION
      "Path: ethOam.performance.synthLoss.result.singleEnded.overall.nbrOfSlrSeqError

       32 bit unsigned wrappable counter."
   ::= {pr1646v2EthOamSlmPerfEntry 117506572}

pr1646v2EthOamSlmPerfRsltSingleOverallFail OBJECT-TYPE
   SYNTAX      Counter32
   MAX-ACCESS  read-only
   STATUS      current
   DESCRIPTION
      "Path: ethOam.performance.synthLoss.result.singleEnded.overall.nbrFailedTests

       32 bit unsigned wrappable counter."
   ::= {pr1646v2EthOamSlmPerfEntry 117506565}

pr1646v2EthOamSlmPerfRsltSingleOverallNeLoss OBJECT-TYPE
   SYNTAX      INTEGER
               {
               invalid (2147483647)
               }
   MAX-ACCESS  read-only
   STATUS      current
   DESCRIPTION
      "Path: ethOam.performance.synthLoss.result.singleEnded.overall.nearEndLoss

       Possibilities:
               invalid   (2147483647)"
   ::= {pr1646v2EthOamSlmPerfEntry 117506566}

pr1646v2EthOamSlmPerfRsltSingleOverallFeLoss OBJECT-TYPE
   SYNTAX      INTEGER
               {
               invalid (2147483647)
               }
   MAX-ACCESS  read-only
   STATUS      current
   DESCRIPTION
      "Path: ethOam.performance.synthLoss.result.singleEnded.overall.farEndLoss

       Possibilities:
               invalid   (2147483647)"
   ::= {pr1646v2EthOamSlmPerfEntry 117506567}

pr1646v2EthOamSlmPerfRsltDualNbrOfTxFrames OBJECT-TYPE
   SYNTAX      Counter32
   MAX-ACCESS  read-only
   STATUS      current
   DESCRIPTION
      "Path: ethOam.performance.synthLoss.result.dualEnded.nbrOfTxFrames

       32 bit unsigned wrappable counter."
   ::= {pr1646v2EthOamSlmPerfEntry 117571840}

pr1646v2EthOamSlmPerfRsltDualNbrOfTxFramesOverall OBJECT-TYPE
   SYNTAX      Counter32
   MAX-ACCESS  read-only
   STATUS      current
   DESCRIPTION
      "Path: ethOam.performance.synthLoss.result.dualEnded.nbrOfTxFramesOverall

       32 bit unsigned wrappable counter."
   ::= {pr1646v2EthOamSlmPerfEntry 117572096}

pr1646v2EthOamSlmPerfRsltSingleErrorLog OBJECT-TYPE
   SYNTAX      SEQUENCE OF Pr1646v2EthOamSlmPerfRsltSingleErrorLogEntry
   MAX-ACCESS  not-accessible
   STATUS      current
   DESCRIPTION
      ""
   ::= {pr1646v2EthOamSlmPerf 117506816}

pr1646v2EthOamSlmPerfRsltSingleErrorLogEntry OBJECT-TYPE
   SYNTAX      Pr1646v2EthOamSlmPerfRsltSingleErrorLogEntry
   MAX-ACCESS  not-accessible
   STATUS      current
   DESCRIPTION
      ""
   INDEX      { pr1646v2EthOamSlmPerfRsltSingleErrorLogGlobalIx,
                pr1646v2EthOamSlmPerfTableIx,
                pr1646v2EthOamSlmPerfRsltSingleErrorLogTableIx }
   ::= {pr1646v2EthOamSlmPerfRsltSingleErrorLog 1}

Pr1646v2EthOamSlmPerfRsltSingleErrorLogEntry ::=
   SEQUENCE
      {
      pr1646v2EthOamSlmPerfRsltSingleErrorLogGlobalIx
         GlobalIndex,
      pr1646v2EthOamSlmPerfRsltSingleErrorLogTableIx
         TableIndex,
      pr1646v2EthOamSlmPerfRsltSingleErrorLogTimeStamp
         DisplayString,
      pr1646v2EthOamSlmPerfRsltSingleErrorLogSysUpTime
         TimeTicks,
      pr1646v2EthOamSlmPerfRsltSingleErrorLogNbrOfTxFrames
         Counter32,
      pr1646v2EthOamSlmPerfRsltSingleErrorLogNbrOfRxFrames
         Counter32,
      pr1646v2EthOamSlmPerfRsltSingleErrorLogNbrOfBadDataFrames
         Counter32,
      pr1646v2EthOamSlmPerfRsltSingleErrorLogNbrOfLateFrames
         Counter32,
      pr1646v2EthOamSlmPerfRsltSingleErrorLogNbrOfDuplicateSlm
         Counter32,
      pr1646v2EthOamSlmPerfRsltSingleErrorLogNbrOfDuplicateSlr
         Counter32,
      pr1646v2EthOamSlmPerfRsltSingleErrorLogNbrOfSlmSeqError
         Counter32,
      pr1646v2EthOamSlmPerfRsltSingleErrorLogNbrOfSlrSeqError
         Counter32,
      pr1646v2EthOamSlmPerfRsltSingleErrorLogNearEndLoss
         INTEGER,
      pr1646v2EthOamSlmPerfRsltSingleErrorLogFarEndLoss
         INTEGER
      }

pr1646v2EthOamSlmPerfRsltSingleErrorLogGlobalIx OBJECT-TYPE
   SYNTAX      GlobalIndex
   MAX-ACCESS  not-accessible
   STATUS      current
   DESCRIPTION
      "The value of the tlsCntTreeGlobalIndex of the MANAGED OBJECT."
   ::= {pr1646v2EthOamSlmPerfRsltSingleErrorLogEntry 10}

pr1646v2EthOamSlmPerfRsltSingleErrorLogTableIx OBJECT-TYPE
   SYNTAX      TableIndex
   MAX-ACCESS  not-accessible
   STATUS      current
   DESCRIPTION
      ""
   ::= {pr1646v2EthOamSlmPerfRsltSingleErrorLogEntry 11}

pr1646v2EthOamSlmPerfRsltSingleErrorLogTimeStamp OBJECT-TYPE
   SYNTAX      DisplayString
   MAX-ACCESS  read-only
   STATUS      current
   DESCRIPTION
      "Path: ethOam.performance.synthLoss.result.singleEnded.errorLog.timeStamp"
   ::= {pr1646v2EthOamSlmPerfRsltSingleErrorLogEntry 134217728}

pr1646v2EthOamSlmPerfRsltSingleErrorLogSysUpTime OBJECT-TYPE
   SYNTAX      TimeTicks
   MAX-ACCESS  read-only
   STATUS      current
   DESCRIPTION
      "Path: ethOam.performance.synthLoss.result.singleEnded.errorLog.sysUpTime

       Time in centi-second."
   ::= {pr1646v2EthOamSlmPerfRsltSingleErrorLogEntry 16777216}

pr1646v2EthOamSlmPerfRsltSingleErrorLogNbrOfTxFrames OBJECT-TYPE
   SYNTAX      Counter32
   MAX-ACCESS  read-only
   STATUS      current
   DESCRIPTION
      "Path: ethOam.performance.synthLoss.result.singleEnded.errorLog.nbrOfTxFrames

       32 bit unsigned wrappable counter."
   ::= {pr1646v2EthOamSlmPerfRsltSingleErrorLogEntry 33554432}

pr1646v2EthOamSlmPerfRsltSingleErrorLogNbrOfRxFrames OBJECT-TYPE
   SYNTAX      Counter32
   MAX-ACCESS  read-only
   STATUS      current
   DESCRIPTION
      "Path: ethOam.performance.synthLoss.result.singleEnded.errorLog.nbrOfRxFrames

       32 bit unsigned wrappable counter."
   ::= {pr1646v2EthOamSlmPerfRsltSingleErrorLogEntry 50331648}

pr1646v2EthOamSlmPerfRsltSingleErrorLogNbrOfBadDataFrames OBJECT-TYPE
   SYNTAX      Counter32
   MAX-ACCESS  read-only
   STATUS      current
   DESCRIPTION
      "Path: ethOam.performance.synthLoss.result.singleEnded.errorLog.nbrOfBadDataFrames

       32 bit unsigned wrappable counter."
   ::= {pr1646v2EthOamSlmPerfRsltSingleErrorLogEntry 67108864}

pr1646v2EthOamSlmPerfRsltSingleErrorLogNbrOfLateFrames OBJECT-TYPE
   SYNTAX      Counter32
   MAX-ACCESS  read-only
   STATUS      current
   DESCRIPTION
      "Path: ethOam.performance.synthLoss.result.singleEnded.errorLog.nbrOfLateFrames

       32 bit unsigned wrappable counter."
   ::= {pr1646v2EthOamSlmPerfRsltSingleErrorLogEntry 83886080}

pr1646v2EthOamSlmPerfRsltSingleErrorLogNbrOfDuplicateSlm OBJECT-TYPE
   SYNTAX      Counter32
   MAX-ACCESS  read-only
   STATUS      current
   DESCRIPTION
      "Path: ethOam.performance.synthLoss.result.singleEnded.errorLog.nbrOfDuplicateSlm

       32 bit unsigned wrappable counter."
   ::= {pr1646v2EthOamSlmPerfRsltSingleErrorLogEntry 150994944}

pr1646v2EthOamSlmPerfRsltSingleErrorLogNbrOfDuplicateSlr OBJECT-TYPE
   SYNTAX      Counter32
   MAX-ACCESS  read-only
   STATUS      current
   DESCRIPTION
      "Path: ethOam.performance.synthLoss.result.singleEnded.errorLog.nbrOfDuplicateSlr

       32 bit unsigned wrappable counter."
   ::= {pr1646v2EthOamSlmPerfRsltSingleErrorLogEntry 167772160}

pr1646v2EthOamSlmPerfRsltSingleErrorLogNbrOfSlmSeqError OBJECT-TYPE
   SYNTAX      Counter32
   MAX-ACCESS  read-only
   STATUS      current
   DESCRIPTION
      "Path: ethOam.performance.synthLoss.result.singleEnded.errorLog.nbrOfSlmSeqError

       32 bit unsigned wrappable counter."
   ::= {pr1646v2EthOamSlmPerfRsltSingleErrorLogEntry 184549376}

pr1646v2EthOamSlmPerfRsltSingleErrorLogNbrOfSlrSeqError OBJECT-TYPE
   SYNTAX      Counter32
   MAX-ACCESS  read-only
   STATUS      current
   DESCRIPTION
      "Path: ethOam.performance.synthLoss.result.singleEnded.errorLog.nbrOfSlrSeqError

       32 bit unsigned wrappable counter."
   ::= {pr1646v2EthOamSlmPerfRsltSingleErrorLogEntry 201326592}

pr1646v2EthOamSlmPerfRsltSingleErrorLogNearEndLoss OBJECT-TYPE
   SYNTAX      INTEGER
               {
               invalid (2147483647)
               }
   MAX-ACCESS  read-only
   STATUS      current
   DESCRIPTION
      "Path: ethOam.performance.synthLoss.result.singleEnded.errorLog.nearEndLoss

       Possibilities:
               invalid   (2147483647)"
   ::= {pr1646v2EthOamSlmPerfRsltSingleErrorLogEntry 100663296}

pr1646v2EthOamSlmPerfRsltSingleErrorLogFarEndLoss OBJECT-TYPE
   SYNTAX      INTEGER
               {
               invalid (2147483647)
               }
   MAX-ACCESS  read-only
   STATUS      current
   DESCRIPTION
      "Path: ethOam.performance.synthLoss.result.singleEnded.errorLog.farEndLoss

       Possibilities:
               invalid   (2147483647)"
   ::= {pr1646v2EthOamSlmPerfRsltSingleErrorLogEntry 117440512}


pr1646v2EthOamMeps OBJECT IDENTIFIER ::= {pr1646v2EthOam 27}

pr1646v2EthOamMepsSSCTable OBJECT-TYPE
   SYNTAX      SEQUENCE OF Pr1646v2EthOamMepsEntry
   MAX-ACCESS  not-accessible
   STATUS      current
   DESCRIPTION
      "ETH OAM MEP statistics"
   ::= {pr1646v2EthOamMeps 1}

pr1646v2EthOamMepsEntry OBJECT-TYPE
   SYNTAX      Pr1646v2EthOamMepsEntry
   MAX-ACCESS  not-accessible
   STATUS      current
   DESCRIPTION
      ""
   INDEX      { pr1646v2EthOamMepsGlobalIx,
                pr1646v2EthOamMepsTableIx }
   ::= {pr1646v2EthOamMepsSSCTable 1}

Pr1646v2EthOamMepsEntry ::=
   SEQUENCE
      {
      pr1646v2EthOamMepsGlobalIx
         GlobalIndex,
      pr1646v2EthOamMepsTableIx
         TableIndex,
      pr1646v2EthOamMepsMepName
         DisplayString,
      pr1646v2EthOamMepsMegLevel
         Integer32,
      pr1646v2EthOamMepsMepId
         INTEGER,
      pr1646v2EthOamMepsTxOam
         Counter32,
      pr1646v2EthOamMepsRxOam
         Counter32,
      pr1646v2EthOamMepsCcmTxCcm
         Counter32,
      pr1646v2EthOamMepsCcmRxValidCcm
         Counter32,
      pr1646v2EthOamMepsCcmTxRdi
         Counter32,
      pr1646v2EthOamMepsCcmRxRdi
         Counter32,
      pr1646v2EthOamMepsCcmRxSeqError
         Counter32,
      pr1646v2EthOamMepsCcmRxBadMegLevel
         Counter32,
      pr1646v2EthOamMepsCcmRxMismerge
         Counter32,
      pr1646v2EthOamMepsCcmRxUnexpPeriod
         Counter32,
      pr1646v2EthOamMepsCcmRxUnexpMep
         Counter32,
      pr1646v2EthOamMepsLoopbackTxLbm
         Counter32,
      pr1646v2EthOamMepsLoopbackRxLbr
         Counter32,
      pr1646v2EthOamMepsLoopbackRxLbm
         Counter32,
      pr1646v2EthOamMepsLoopbackTxLbr
         Counter32,
      pr1646v2EthOamMepsLoopbackTxMcLbm
         Counter32,
      pr1646v2EthOamMepsLoopbackRxMcLbm
         Counter32,
      pr1646v2EthOamMepsLoopbackRxLbrOutOfSeq
         Counter32,
      pr1646v2EthOamMepsLoopbackRxLbrTooLate
         Counter32,
      pr1646v2EthOamMepsLoopbackRxLbrBadData
         Counter32,
      pr1646v2EthOamMepsLinkTraceTxLtm
         Counter32,
      pr1646v2EthOamMepsLinkTraceRxLtr
         Counter32,
      pr1646v2EthOamMepsLinkTraceRxLtm
         Counter32,
      pr1646v2EthOamMepsLinkTraceTxLtr
         Counter32,
      pr1646v2EthOamMepsLinkTraceRxLtrTooLate
         Counter32,
      pr1646v2EthOamMepsLinkTraceRxLtrUnexp
         Counter32,
      pr1646v2EthOamMepsDelayTxDmm
         Counter32,
      pr1646v2EthOamMepsDelayRxDmr
         Counter32,
      pr1646v2EthOamMepsDelayRxDmm
         Counter32,
      pr1646v2EthOamMepsDelayTxDmr
         Counter32,
      pr1646v2EthOamMepsLossTxLmm
         Counter32,
      pr1646v2EthOamMepsLossRxLmr
         Counter32,
      pr1646v2EthOamMepsLossRxLmm
         Counter32,
      pr1646v2EthOamMepsLossTxLmr
         Counter32,
      pr1646v2EthOamMepsSynthLossTxSlm
         Counter32,
      pr1646v2EthOamMepsSynthLossRxSlr
         Counter32,
      pr1646v2EthOamMepsSynthLossRxSlm
         Counter32,
      pr1646v2EthOamMepsSynthLossTxSlr
         Counter32,
      pr1646v2EthOamMepsSynthLossTx1Sl
         Counter32,
      pr1646v2EthOamMepsSynthLossRx1Sl
         Counter32,
      pr1646v2EthOamMepsSynthLossTxMc1Sl
         Counter32,
      pr1646v2EthOamMepsSynthLossRxMc1Sl
         Counter32,
      pr1646v2EthOamMepsAisTxAis
         Counter32,
      pr1646v2EthOamMepsAisRxAis
         Counter32,
      pr1646v2EthOamMepsApsTxAps
         Counter32,
      pr1646v2EthOamMepsApsRxAps
         Counter32,
      pr1646v2EthOamMepsApsRxApsMismatch
         Counter32,
      pr1646v2EthOamMepsPassiveDiscards
         Counter32,
      pr1646v2EthOamMepsDiscards
         Counter32
      }

pr1646v2EthOamMepsGlobalIx OBJECT-TYPE
   SYNTAX      GlobalIndex
   MAX-ACCESS  not-accessible
   STATUS      current
   DESCRIPTION
      "The value of the tlsCntTreeGlobalIndex of the MANAGED OBJECT."
   ::= {pr1646v2EthOamMepsEntry 10}

pr1646v2EthOamMepsTableIx OBJECT-TYPE
   SYNTAX      TableIndex
   MAX-ACCESS  not-accessible
   STATUS      current
   DESCRIPTION
      ""
   ::= {pr1646v2EthOamMepsEntry 11}

pr1646v2EthOamMepsMepName OBJECT-TYPE
   SYNTAX      DisplayString
   MAX-ACCESS  read-only
   STATUS      current
   DESCRIPTION
      "Path: ethOam.performance.meps.mepName"
   ::= {pr1646v2EthOamMepsEntry 16777216}

pr1646v2EthOamMepsMegLevel OBJECT-TYPE
   SYNTAX      Integer32
   MAX-ACCESS  read-only
   STATUS      current
   DESCRIPTION
      "Path: ethOam.performance.meps.megLevel"
   ::= {pr1646v2EthOamMepsEntry 33554432}

pr1646v2EthOamMepsMepId OBJECT-TYPE
   SYNTAX      INTEGER
               {
               unknown (8192)
               }
   MAX-ACCESS  read-only
   STATUS      current
   DESCRIPTION
      "Path: ethOam.performance.meps.mepId

       Possibilities:
               unknown   (8192)"
   ::= {pr1646v2EthOamMepsEntry 50331648}

pr1646v2EthOamMepsTxOam OBJECT-TYPE
   SYNTAX      Counter32
   MAX-ACCESS  read-only
   STATUS      current
   DESCRIPTION
      "Path: ethOam.performance.meps.txOam

       32 bit unsigned wrappable counter."
   ::= {pr1646v2EthOamMepsEntry 67108864}

pr1646v2EthOamMepsRxOam OBJECT-TYPE
   SYNTAX      Counter32
   MAX-ACCESS  read-only
   STATUS      current
   DESCRIPTION
      "Path: ethOam.performance.meps.rxOam

       32 bit unsigned wrappable counter."
   ::= {pr1646v2EthOamMepsEntry 83886080}

pr1646v2EthOamMepsCcmTxCcm OBJECT-TYPE
   SYNTAX      Counter32
   MAX-ACCESS  read-only
   STATUS      current
   DESCRIPTION
      "Path: ethOam.performance.meps.ccm.txCcm

       32 bit unsigned wrappable counter."
   ::= {pr1646v2EthOamMepsEntry 100728832}

pr1646v2EthOamMepsCcmRxValidCcm OBJECT-TYPE
   SYNTAX      Counter32
   MAX-ACCESS  read-only
   STATUS      current
   DESCRIPTION
      "Path: ethOam.performance.meps.ccm.rxValidCcm

       32 bit unsigned wrappable counter."
   ::= {pr1646v2EthOamMepsEntry 100794368}

pr1646v2EthOamMepsCcmTxRdi OBJECT-TYPE
   SYNTAX      Counter32
   MAX-ACCESS  read-only
   STATUS      current
   DESCRIPTION
      "Path: ethOam.performance.meps.ccm.txRdi

       32 bit unsigned wrappable counter."
   ::= {pr1646v2EthOamMepsEntry 101253120}

pr1646v2EthOamMepsCcmRxRdi OBJECT-TYPE
   SYNTAX      Counter32
   MAX-ACCESS  read-only
   STATUS      current
   DESCRIPTION
      "Path: ethOam.performance.meps.ccm.rxRdi

       32 bit unsigned wrappable counter."
   ::= {pr1646v2EthOamMepsEntry 100859904}

pr1646v2EthOamMepsCcmRxSeqError OBJECT-TYPE
   SYNTAX      Counter32
   MAX-ACCESS  read-only
   STATUS      current
   DESCRIPTION
      "Path: ethOam.performance.meps.ccm.rxSeqError

       32 bit unsigned wrappable counter."
   ::= {pr1646v2EthOamMepsEntry 100925440}

pr1646v2EthOamMepsCcmRxBadMegLevel OBJECT-TYPE
   SYNTAX      Counter32
   MAX-ACCESS  read-only
   STATUS      current
   DESCRIPTION
      "Path: ethOam.performance.meps.ccm.rxBadMegLevel

       32 bit unsigned wrappable counter."
   ::= {pr1646v2EthOamMepsEntry 100990976}

pr1646v2EthOamMepsCcmRxMismerge OBJECT-TYPE
   SYNTAX      Counter32
   MAX-ACCESS  read-only
   STATUS      current
   DESCRIPTION
      "Path: ethOam.performance.meps.ccm.rxMismerge

       32 bit unsigned wrappable counter."
   ::= {pr1646v2EthOamMepsEntry 101056512}

pr1646v2EthOamMepsCcmRxUnexpPeriod OBJECT-TYPE
   SYNTAX      Counter32
   MAX-ACCESS  read-only
   STATUS      current
   DESCRIPTION
      "Path: ethOam.performance.meps.ccm.rxUnexpPeriod

       32 bit unsigned wrappable counter."
   ::= {pr1646v2EthOamMepsEntry 101122048}

pr1646v2EthOamMepsCcmRxUnexpMep OBJECT-TYPE
   SYNTAX      Counter32
   MAX-ACCESS  read-only
   STATUS      current
   DESCRIPTION
      "Path: ethOam.performance.meps.ccm.rxUnexpMep

       32 bit unsigned wrappable counter."
   ::= {pr1646v2EthOamMepsEntry 101187584}

pr1646v2EthOamMepsLoopbackTxLbm OBJECT-TYPE
   SYNTAX      Counter32
   MAX-ACCESS  read-only
   STATUS      current
   DESCRIPTION
      "Path: ethOam.performance.meps.loopback.txLbm

       32 bit unsigned wrappable counter."
   ::= {pr1646v2EthOamMepsEntry 117506048}

pr1646v2EthOamMepsLoopbackRxLbr OBJECT-TYPE
   SYNTAX      Counter32
   MAX-ACCESS  read-only
   STATUS      current
   DESCRIPTION
      "Path: ethOam.performance.meps.loopback.rxLbr

       32 bit unsigned wrappable counter."
   ::= {pr1646v2EthOamMepsEntry 117702656}

pr1646v2EthOamMepsLoopbackRxLbm OBJECT-TYPE
   SYNTAX      Counter32
   MAX-ACCESS  read-only
   STATUS      current
   DESCRIPTION
      "Path: ethOam.performance.meps.loopback.rxLbm

       32 bit unsigned wrappable counter."
   ::= {pr1646v2EthOamMepsEntry 117571584}

pr1646v2EthOamMepsLoopbackTxLbr OBJECT-TYPE
   SYNTAX      Counter32
   MAX-ACCESS  read-only
   STATUS      current
   DESCRIPTION
      "Path: ethOam.performance.meps.loopback.txLbr

       32 bit unsigned wrappable counter."
   ::= {pr1646v2EthOamMepsEntry 117637120}

pr1646v2EthOamMepsLoopbackTxMcLbm OBJECT-TYPE
   SYNTAX      Counter32
   MAX-ACCESS  read-only
   STATUS      current
   DESCRIPTION
      "Path: ethOam.performance.meps.loopback.txMcLbm

       32 bit unsigned wrappable counter."
   ::= {pr1646v2EthOamMepsEntry 118030336}

pr1646v2EthOamMepsLoopbackRxMcLbm OBJECT-TYPE
   SYNTAX      Counter32
   MAX-ACCESS  read-only
   STATUS      current
   DESCRIPTION
      "Path: ethOam.performance.meps.loopback.rxMcLbm

       32 bit unsigned wrappable counter."
   ::= {pr1646v2EthOamMepsEntry 117964800}

pr1646v2EthOamMepsLoopbackRxLbrOutOfSeq OBJECT-TYPE
   SYNTAX      Counter32
   MAX-ACCESS  read-only
   STATUS      current
   DESCRIPTION
      "Path: ethOam.performance.meps.loopback.rxLbrOutOfSeq

       32 bit unsigned wrappable counter."
   ::= {pr1646v2EthOamMepsEntry 117768192}

pr1646v2EthOamMepsLoopbackRxLbrTooLate OBJECT-TYPE
   SYNTAX      Counter32
   MAX-ACCESS  read-only
   STATUS      current
   DESCRIPTION
      "Path: ethOam.performance.meps.loopback.rxLbrTooLate

       32 bit unsigned wrappable counter."
   ::= {pr1646v2EthOamMepsEntry 117833728}

pr1646v2EthOamMepsLoopbackRxLbrBadData OBJECT-TYPE
   SYNTAX      Counter32
   MAX-ACCESS  read-only
   STATUS      current
   DESCRIPTION
      "Path: ethOam.performance.meps.loopback.rxLbrBadData

       32 bit unsigned wrappable counter."
   ::= {pr1646v2EthOamMepsEntry 117899264}

pr1646v2EthOamMepsLinkTraceTxLtm OBJECT-TYPE
   SYNTAX      Counter32
   MAX-ACCESS  read-only
   STATUS      current
   DESCRIPTION
      "Path: ethOam.performance.meps.linkTrace.txLtm

       32 bit unsigned wrappable counter."
   ::= {pr1646v2EthOamMepsEntry 134283264}

pr1646v2EthOamMepsLinkTraceRxLtr OBJECT-TYPE
   SYNTAX      Counter32
   MAX-ACCESS  read-only
   STATUS      current
   DESCRIPTION
      "Path: ethOam.performance.meps.linkTrace.rxLtr

       32 bit unsigned wrappable counter."
   ::= {pr1646v2EthOamMepsEntry 134479872}

pr1646v2EthOamMepsLinkTraceRxLtm OBJECT-TYPE
   SYNTAX      Counter32
   MAX-ACCESS  read-only
   STATUS      current
   DESCRIPTION
      "Path: ethOam.performance.meps.linkTrace.rxLtm

       32 bit unsigned wrappable counter."
   ::= {pr1646v2EthOamMepsEntry 134348800}

pr1646v2EthOamMepsLinkTraceTxLtr OBJECT-TYPE
   SYNTAX      Counter32
   MAX-ACCESS  read-only
   STATUS      current
   DESCRIPTION
      "Path: ethOam.performance.meps.linkTrace.txLtr

       32 bit unsigned wrappable counter."
   ::= {pr1646v2EthOamMepsEntry 134414336}

pr1646v2EthOamMepsLinkTraceRxLtrTooLate OBJECT-TYPE
   SYNTAX      Counter32
   MAX-ACCESS  read-only
   STATUS      current
   DESCRIPTION
      "Path: ethOam.performance.meps.linkTrace.rxLtrTooLate

       32 bit unsigned wrappable counter."
   ::= {pr1646v2EthOamMepsEntry 134545408}

pr1646v2EthOamMepsLinkTraceRxLtrUnexp OBJECT-TYPE
   SYNTAX      Counter32
   MAX-ACCESS  read-only
   STATUS      current
   DESCRIPTION
      "Path: ethOam.performance.meps.linkTrace.rxLtrUnexp

       32 bit unsigned wrappable counter."
   ::= {pr1646v2EthOamMepsEntry 134610944}

pr1646v2EthOamMepsDelayTxDmm OBJECT-TYPE
   SYNTAX      Counter32
   MAX-ACCESS  read-only
   STATUS      current
   DESCRIPTION
      "Path: ethOam.performance.meps.delay.txDmm

       32 bit unsigned wrappable counter."
   ::= {pr1646v2EthOamMepsEntry 151060480}

pr1646v2EthOamMepsDelayRxDmr OBJECT-TYPE
   SYNTAX      Counter32
   MAX-ACCESS  read-only
   STATUS      current
   DESCRIPTION
      "Path: ethOam.performance.meps.delay.rxDmr

       32 bit unsigned wrappable counter."
   ::= {pr1646v2EthOamMepsEntry 151257088}

pr1646v2EthOamMepsDelayRxDmm OBJECT-TYPE
   SYNTAX      Counter32
   MAX-ACCESS  read-only
   STATUS      current
   DESCRIPTION
      "Path: ethOam.performance.meps.delay.rxDmm

       32 bit unsigned wrappable counter."
   ::= {pr1646v2EthOamMepsEntry 151126016}

pr1646v2EthOamMepsDelayTxDmr OBJECT-TYPE
   SYNTAX      Counter32
   MAX-ACCESS  read-only
   STATUS      current
   DESCRIPTION
      "Path: ethOam.performance.meps.delay.txDmr

       32 bit unsigned wrappable counter."
   ::= {pr1646v2EthOamMepsEntry 151191552}

pr1646v2EthOamMepsLossTxLmm OBJECT-TYPE
   SYNTAX      Counter32
   MAX-ACCESS  read-only
   STATUS      current
   DESCRIPTION
      "Path: ethOam.performance.meps.loss.txLmm

       32 bit unsigned wrappable counter."
   ::= {pr1646v2EthOamMepsEntry 167837696}

pr1646v2EthOamMepsLossRxLmr OBJECT-TYPE
   SYNTAX      Counter32
   MAX-ACCESS  read-only
   STATUS      current
   DESCRIPTION
      "Path: ethOam.performance.meps.loss.rxLmr

       32 bit unsigned wrappable counter."
   ::= {pr1646v2EthOamMepsEntry 168034304}

pr1646v2EthOamMepsLossRxLmm OBJECT-TYPE
   SYNTAX      Counter32
   MAX-ACCESS  read-only
   STATUS      current
   DESCRIPTION
      "Path: ethOam.performance.meps.loss.rxLmm

       32 bit unsigned wrappable counter."
   ::= {pr1646v2EthOamMepsEntry 167903232}

pr1646v2EthOamMepsLossTxLmr OBJECT-TYPE
   SYNTAX      Counter32
   MAX-ACCESS  read-only
   STATUS      current
   DESCRIPTION
      "Path: ethOam.performance.meps.loss.txLmr

       32 bit unsigned wrappable counter."
   ::= {pr1646v2EthOamMepsEntry 167968768}

pr1646v2EthOamMepsSynthLossTxSlm OBJECT-TYPE
   SYNTAX      Counter32
   MAX-ACCESS  read-only
   STATUS      current
   DESCRIPTION
      "Path: ethOam.performance.meps.synthLoss.txSlm

       32 bit unsigned wrappable counter."
   ::= {pr1646v2EthOamMepsEntry 251723776}

pr1646v2EthOamMepsSynthLossRxSlr OBJECT-TYPE
   SYNTAX      Counter32
   MAX-ACCESS  read-only
   STATUS      current
   DESCRIPTION
      "Path: ethOam.performance.meps.synthLoss.rxSlr

       32 bit unsigned wrappable counter."
   ::= {pr1646v2EthOamMepsEntry 251920384}

pr1646v2EthOamMepsSynthLossRxSlm OBJECT-TYPE
   SYNTAX      Counter32
   MAX-ACCESS  read-only
   STATUS      current
   DESCRIPTION
      "Path: ethOam.performance.meps.synthLoss.rxSlm

       32 bit unsigned wrappable counter."
   ::= {pr1646v2EthOamMepsEntry 251789312}

pr1646v2EthOamMepsSynthLossTxSlr OBJECT-TYPE
   SYNTAX      Counter32
   MAX-ACCESS  read-only
   STATUS      current
   DESCRIPTION
      "Path: ethOam.performance.meps.synthLoss.txSlr

       32 bit unsigned wrappable counter."
   ::= {pr1646v2EthOamMepsEntry 251854848}

pr1646v2EthOamMepsSynthLossTx1Sl OBJECT-TYPE
   SYNTAX      Counter32
   MAX-ACCESS  read-only
   STATUS      current
   DESCRIPTION
      "Path: ethOam.performance.meps.synthLoss.tx1Sl

       32 bit unsigned wrappable counter."
   ::= {pr1646v2EthOamMepsEntry 251985920}

pr1646v2EthOamMepsSynthLossRx1Sl OBJECT-TYPE
   SYNTAX      Counter32
   MAX-ACCESS  read-only
   STATUS      current
   DESCRIPTION
      "Path: ethOam.performance.meps.synthLoss.rx1Sl

       32 bit unsigned wrappable counter."
   ::= {pr1646v2EthOamMepsEntry 252051456}

pr1646v2EthOamMepsSynthLossTxMc1Sl OBJECT-TYPE
   SYNTAX      Counter32
   MAX-ACCESS  read-only
   STATUS      current
   DESCRIPTION
      "Path: ethOam.performance.meps.synthLoss.txMc1Sl

       32 bit unsigned wrappable counter."
   ::= {pr1646v2EthOamMepsEntry 252116992}

pr1646v2EthOamMepsSynthLossRxMc1Sl OBJECT-TYPE
   SYNTAX      Counter32
   MAX-ACCESS  read-only
   STATUS      current
   DESCRIPTION
      "Path: ethOam.performance.meps.synthLoss.rxMc1Sl

       32 bit unsigned wrappable counter."
   ::= {pr1646v2EthOamMepsEntry 252182528}

pr1646v2EthOamMepsAisTxAis OBJECT-TYPE
   SYNTAX      Counter32
   MAX-ACCESS  read-only
   STATUS      current
   DESCRIPTION
      "Path: ethOam.performance.meps.ais.txAis

       32 bit unsigned wrappable counter."
   ::= {pr1646v2EthOamMepsEntry 201392128}

pr1646v2EthOamMepsAisRxAis OBJECT-TYPE
   SYNTAX      Counter32
   MAX-ACCESS  read-only
   STATUS      current
   DESCRIPTION
      "Path: ethOam.performance.meps.ais.rxAis

       32 bit unsigned wrappable counter."
   ::= {pr1646v2EthOamMepsEntry 201457664}

pr1646v2EthOamMepsApsTxAps OBJECT-TYPE
   SYNTAX      Counter32
   MAX-ACCESS  read-only
   STATUS      current
   DESCRIPTION
      "Path: ethOam.performance.meps.aps.txAps

       32 bit unsigned wrappable counter."
   ::= {pr1646v2EthOamMepsEntry 234946560}

pr1646v2EthOamMepsApsRxAps OBJECT-TYPE
   SYNTAX      Counter32
   MAX-ACCESS  read-only
   STATUS      current
   DESCRIPTION
      "Path: ethOam.performance.meps.aps.rxAps

       32 bit unsigned wrappable counter."
   ::= {pr1646v2EthOamMepsEntry 235012096}

pr1646v2EthOamMepsApsRxApsMismatch OBJECT-TYPE
   SYNTAX      Counter32
   MAX-ACCESS  read-only
   STATUS      current
   DESCRIPTION
      "Path: ethOam.performance.meps.aps.rxApsMismatch

       32 bit unsigned wrappable counter."
   ::= {pr1646v2EthOamMepsEntry 235077632}

pr1646v2EthOamMepsPassiveDiscards OBJECT-TYPE
   SYNTAX      Counter32
   MAX-ACCESS  read-only
   STATUS      current
   DESCRIPTION
      "Path: ethOam.performance.meps.passiveDiscards

       32 bit unsigned wrappable counter."
   ::= {pr1646v2EthOamMepsEntry 218103808}

pr1646v2EthOamMepsDiscards OBJECT-TYPE
   SYNTAX      Counter32
   MAX-ACCESS  read-only
   STATUS      current
   DESCRIPTION
      "Path: ethOam.performance.meps.discards

       32 bit unsigned wrappable counter."
   ::= {pr1646v2EthOamMepsEntry 184549376}


pr1646v2EthOamMips OBJECT IDENTIFIER ::= {pr1646v2EthOam 30}

pr1646v2EthOamMipsSSCTable OBJECT-TYPE
   SYNTAX      SEQUENCE OF Pr1646v2EthOamMipsEntry
   MAX-ACCESS  not-accessible
   STATUS      current
   DESCRIPTION
      "ETH OAM MIP statistics"
   ::= {pr1646v2EthOamMips 1}

pr1646v2EthOamMipsEntry OBJECT-TYPE
   SYNTAX      Pr1646v2EthOamMipsEntry
   MAX-ACCESS  not-accessible
   STATUS      current
   DESCRIPTION
      ""
   INDEX      { pr1646v2EthOamMipsGlobalIx,
                pr1646v2EthOamMipsTableIx }
   ::= {pr1646v2EthOamMipsSSCTable 1}

Pr1646v2EthOamMipsEntry ::=
   SEQUENCE
      {
      pr1646v2EthOamMipsGlobalIx
         GlobalIndex,
      pr1646v2EthOamMipsTableIx
         TableIndex,
      pr1646v2EthOamMipsMipName
         DisplayString,
      pr1646v2EthOamMipsMegLevel
         Integer32,
      pr1646v2EthOamMipsRxLbm
         Counter32,
      pr1646v2EthOamMipsTxLbr
         Counter32,
      pr1646v2EthOamMipsRxLtm
         Counter32,
      pr1646v2EthOamMipsTxLtm
         Counter32,
      pr1646v2EthOamMipsTxLtr
         Counter32,
      pr1646v2EthOamMipsDiscards
         Counter32
      }

pr1646v2EthOamMipsGlobalIx OBJECT-TYPE
   SYNTAX      GlobalIndex
   MAX-ACCESS  not-accessible
   STATUS      current
   DESCRIPTION
      "The value of the tlsCntTreeGlobalIndex of the MANAGED OBJECT."
   ::= {pr1646v2EthOamMipsEntry 10}

pr1646v2EthOamMipsTableIx OBJECT-TYPE
   SYNTAX      TableIndex
   MAX-ACCESS  not-accessible
   STATUS      current
   DESCRIPTION
      ""
   ::= {pr1646v2EthOamMipsEntry 11}

pr1646v2EthOamMipsMipName OBJECT-TYPE
   SYNTAX      DisplayString
   MAX-ACCESS  read-only
   STATUS      current
   DESCRIPTION
      "Path: ethOam.performance.mips.mipName"
   ::= {pr1646v2EthOamMipsEntry 16777216}

pr1646v2EthOamMipsMegLevel OBJECT-TYPE
   SYNTAX      Integer32
   MAX-ACCESS  read-only
   STATUS      current
   DESCRIPTION
      "Path: ethOam.performance.mips.megLevel"
   ::= {pr1646v2EthOamMipsEntry 33554432}

pr1646v2EthOamMipsRxLbm OBJECT-TYPE
   SYNTAX      Counter32
   MAX-ACCESS  read-only
   STATUS      current
   DESCRIPTION
      "Path: ethOam.performance.mips.rxLbm

       32 bit unsigned wrappable counter."
   ::= {pr1646v2EthOamMipsEntry 50331648}

pr1646v2EthOamMipsTxLbr OBJECT-TYPE
   SYNTAX      Counter32
   MAX-ACCESS  read-only
   STATUS      current
   DESCRIPTION
      "Path: ethOam.performance.mips.txLbr

       32 bit unsigned wrappable counter."
   ::= {pr1646v2EthOamMipsEntry 67108864}

pr1646v2EthOamMipsRxLtm OBJECT-TYPE
   SYNTAX      Counter32
   MAX-ACCESS  read-only
   STATUS      current
   DESCRIPTION
      "Path: ethOam.performance.mips.rxLtm

       32 bit unsigned wrappable counter."
   ::= {pr1646v2EthOamMipsEntry 83886080}

pr1646v2EthOamMipsTxLtm OBJECT-TYPE
   SYNTAX      Counter32
   MAX-ACCESS  read-only
   STATUS      current
   DESCRIPTION
      "Path: ethOam.performance.mips.txLtm

       32 bit unsigned wrappable counter."
   ::= {pr1646v2EthOamMipsEntry 100663296}

pr1646v2EthOamMipsTxLtr OBJECT-TYPE
   SYNTAX      Counter32
   MAX-ACCESS  read-only
   STATUS      current
   DESCRIPTION
      "Path: ethOam.performance.mips.txLtr

       32 bit unsigned wrappable counter."
   ::= {pr1646v2EthOamMipsEntry 117440512}

pr1646v2EthOamMipsDiscards OBJECT-TYPE
   SYNTAX      Counter32
   MAX-ACCESS  read-only
   STATUS      current
   DESCRIPTION
      "Path: ethOam.performance.mips.discards

       32 bit unsigned wrappable counter."
   ::= {pr1646v2EthOamMipsEntry 134217728}


pr1646v2EthOamManagedMeps OBJECT IDENTIFIER ::= {pr1646v2EthOam 40}

pr1646v2EthOamManagedMepsSSCTable OBJECT-TYPE
   SYNTAX      SEQUENCE OF Pr1646v2EthOamManagedMepsEntry
   MAX-ACCESS  not-accessible
   STATUS      current
   DESCRIPTION
      "list of managed MEPs"
   ::= {pr1646v2EthOamManagedMeps 1}

pr1646v2EthOamManagedMepsEntry OBJECT-TYPE
   SYNTAX      Pr1646v2EthOamManagedMepsEntry
   MAX-ACCESS  not-accessible
   STATUS      current
   DESCRIPTION
      ""
   INDEX      { pr1646v2EthOamManagedMepsGlobalIx,
                pr1646v2EthOamManagedMepsTableIx }
   ::= {pr1646v2EthOamManagedMepsSSCTable 1}

Pr1646v2EthOamManagedMepsEntry ::=
   SEQUENCE
      {
      pr1646v2EthOamManagedMepsGlobalIx
         GlobalIndex,
      pr1646v2EthOamManagedMepsTableIx
         TableIndex,
      pr1646v2EthOamManagedMepsManagedMepName
         DisplayString,
      pr1646v2EthOamManagedMepsMegLevel
         Integer32,
      pr1646v2EthOamManagedMepsMegIdMaintDomainName
         DisplayString,
      pr1646v2EthOamManagedMepsMegIdShortMaName
         DisplayString,
      pr1646v2EthOamManagedMepsMepId
         Integer32,
      pr1646v2EthOamManagedMepsRxCcm
         Counter32,
      pr1646v2EthOamManagedMepsTxLbm
         Counter32,
      pr1646v2EthOamManagedMepsRxLbr
         Counter32,
      pr1646v2EthOamManagedMepsRxLbm
         Counter32,
      pr1646v2EthOamManagedMepsTxLmm
         Counter32,
      pr1646v2EthOamManagedMepsRxLmr
         Counter32,
      pr1646v2EthOamManagedMepsRxLmm
         Counter32,
      pr1646v2EthOamManagedMepsTxDmm
         Counter32,
      pr1646v2EthOamManagedMepsRxDmr
         Counter32,
      pr1646v2EthOamManagedMepsRxDmm
         Counter32,
      pr1646v2EthOamManagedMepsSlTxSlm
         Counter32,
      pr1646v2EthOamManagedMepsSlRxSlr
         Counter32,
      pr1646v2EthOamManagedMepsSlRxSlm
         Counter32,
      pr1646v2EthOamManagedMepsSlRx1SlCurrentNbrOfRxFrames
         Counter32,
      pr1646v2EthOamManagedMepsSlRx1SlCurrentNearEndLoss
         INTEGER,
      pr1646v2EthOamManagedMepsSlRx1SlOverallNbrOfRxFrames
         Counter32,
      pr1646v2EthOamManagedMepsSlRx1SlOverallNearEndLoss
         INTEGER,
      pr1646v2EthOamManagedMepsSlRxMc1SlCurrentNbrOfRxFrames
         Counter32,
      pr1646v2EthOamManagedMepsSlRxMc1SlCurrentNearEndLoss
         INTEGER,
      pr1646v2EthOamManagedMepsSlRxMc1SlOverallNbrOfRxFrames
         Counter32,
      pr1646v2EthOamManagedMepsSlRxMc1SlOverallNearEndLoss
         INTEGER
      }

pr1646v2EthOamManagedMepsGlobalIx OBJECT-TYPE
   SYNTAX      GlobalIndex
   MAX-ACCESS  not-accessible
   STATUS      current
   DESCRIPTION
      "The value of the tlsCntTreeGlobalIndex of the MANAGED OBJECT."
   ::= {pr1646v2EthOamManagedMepsEntry 10}

pr1646v2EthOamManagedMepsTableIx OBJECT-TYPE
   SYNTAX      TableIndex
   MAX-ACCESS  not-accessible
   STATUS      current
   DESCRIPTION
      ""
   ::= {pr1646v2EthOamManagedMepsEntry 11}

pr1646v2EthOamManagedMepsManagedMepName OBJECT-TYPE
   SYNTAX      DisplayString
   MAX-ACCESS  read-only
   STATUS      current
   DESCRIPTION
      "Path: ethOam.performance.managedMeps.managedMepName"
   ::= {pr1646v2EthOamManagedMepsEntry 201326592}

pr1646v2EthOamManagedMepsMegLevel OBJECT-TYPE
   SYNTAX      Integer32
   MAX-ACCESS  read-only
   STATUS      current
   DESCRIPTION
      "Path: ethOam.performance.managedMeps.megLevel"
   ::= {pr1646v2EthOamManagedMepsEntry 83886080}

pr1646v2EthOamManagedMepsMegIdMaintDomainName OBJECT-TYPE
   SYNTAX      DisplayString
   MAX-ACCESS  read-only
   STATUS      current
   DESCRIPTION
      "Path: ethOam.performance.managedMeps.megId.maintDomainName"
   ::= {pr1646v2EthOamManagedMepsEntry 100728832}

pr1646v2EthOamManagedMepsMegIdShortMaName OBJECT-TYPE
   SYNTAX      DisplayString
   MAX-ACCESS  read-only
   STATUS      current
   DESCRIPTION
      "Path: ethOam.performance.managedMeps.megId.shortMaName"
   ::= {pr1646v2EthOamManagedMepsEntry 100794368}

pr1646v2EthOamManagedMepsMepId OBJECT-TYPE
   SYNTAX      Integer32
   MAX-ACCESS  read-only
   STATUS      current
   DESCRIPTION
      "Path: ethOam.performance.managedMeps.mepId"
   ::= {pr1646v2EthOamManagedMepsEntry 117440512}

pr1646v2EthOamManagedMepsRxCcm OBJECT-TYPE
   SYNTAX      Counter32
   MAX-ACCESS  read-only
   STATUS      current
   DESCRIPTION
      "Path: ethOam.performance.managedMeps.rxCcm

       32 bit unsigned wrappable counter."
   ::= {pr1646v2EthOamManagedMepsEntry 335544320}

pr1646v2EthOamManagedMepsTxLbm OBJECT-TYPE
   SYNTAX      Counter32
   MAX-ACCESS  read-only
   STATUS      current
   DESCRIPTION
      "Path: ethOam.performance.managedMeps.txLbm

       32 bit unsigned wrappable counter."
   ::= {pr1646v2EthOamManagedMepsEntry 553648128}

pr1646v2EthOamManagedMepsRxLbr OBJECT-TYPE
   SYNTAX      Counter32
   MAX-ACCESS  read-only
   STATUS      current
   DESCRIPTION
      "Path: ethOam.performance.managedMeps.rxLbr

       32 bit unsigned wrappable counter."
   ::= {pr1646v2EthOamManagedMepsEntry 721420288}

pr1646v2EthOamManagedMepsRxLbm OBJECT-TYPE
   SYNTAX      Counter32
   MAX-ACCESS  read-only
   STATUS      current
   DESCRIPTION
      "Path: ethOam.performance.managedMeps.rxLbm

       32 bit unsigned wrappable counter."
   ::= {pr1646v2EthOamManagedMepsEntry 385875968}

pr1646v2EthOamManagedMepsTxLmm OBJECT-TYPE
   SYNTAX      Counter32
   MAX-ACCESS  read-only
   STATUS      current
   DESCRIPTION
      "Path: ethOam.performance.managedMeps.txLmm

       32 bit unsigned wrappable counter."
   ::= {pr1646v2EthOamManagedMepsEntry 520093696}

pr1646v2EthOamManagedMepsRxLmr OBJECT-TYPE
   SYNTAX      Counter32
   MAX-ACCESS  read-only
   STATUS      current
   DESCRIPTION
      "Path: ethOam.performance.managedMeps.rxLmr

       32 bit unsigned wrappable counter."
   ::= {pr1646v2EthOamManagedMepsEntry 687865856}

pr1646v2EthOamManagedMepsRxLmm OBJECT-TYPE
   SYNTAX      Counter32
   MAX-ACCESS  read-only
   STATUS      current
   DESCRIPTION
      "Path: ethOam.performance.managedMeps.rxLmm

       32 bit unsigned wrappable counter."
   ::= {pr1646v2EthOamManagedMepsEntry 352321536}

pr1646v2EthOamManagedMepsTxDmm OBJECT-TYPE
   SYNTAX      Counter32
   MAX-ACCESS  read-only
   STATUS      current
   DESCRIPTION
      "Path: ethOam.performance.managedMeps.txDmm

       32 bit unsigned wrappable counter."
   ::= {pr1646v2EthOamManagedMepsEntry 536870912}

pr1646v2EthOamManagedMepsRxDmr OBJECT-TYPE
   SYNTAX      Counter32
   MAX-ACCESS  read-only
   STATUS      current
   DESCRIPTION
      "Path: ethOam.performance.managedMeps.rxDmr

       32 bit unsigned wrappable counter."
   ::= {pr1646v2EthOamManagedMepsEntry 704643072}

pr1646v2EthOamManagedMepsRxDmm OBJECT-TYPE
   SYNTAX      Counter32
   MAX-ACCESS  read-only
   STATUS      current
   DESCRIPTION
      "Path: ethOam.performance.managedMeps.rxDmm

       32 bit unsigned wrappable counter."
   ::= {pr1646v2EthOamManagedMepsEntry 369098752}

pr1646v2EthOamManagedMepsSlTxSlm OBJECT-TYPE
   SYNTAX      Counter32
   MAX-ACCESS  read-only
   STATUS      current
   DESCRIPTION
      "Path: ethOam.performance.managedMeps.synthLoss.txSlm

       32 bit unsigned wrappable counter."
   ::= {pr1646v2EthOamManagedMepsEntry 855900160}

pr1646v2EthOamManagedMepsSlRxSlr OBJECT-TYPE
   SYNTAX      Counter32
   MAX-ACCESS  read-only
   STATUS      current
   DESCRIPTION
      "Path: ethOam.performance.managedMeps.synthLoss.rxSlr

       32 bit unsigned wrappable counter."
   ::= {pr1646v2EthOamManagedMepsEntry 855965696}

pr1646v2EthOamManagedMepsSlRxSlm OBJECT-TYPE
   SYNTAX      Counter32
   MAX-ACCESS  read-only
   STATUS      current
   DESCRIPTION
      "Path: ethOam.performance.managedMeps.synthLoss.rxSlm

       32 bit unsigned wrappable counter."
   ::= {pr1646v2EthOamManagedMepsEntry 855703552}

pr1646v2EthOamManagedMepsSlRx1SlCurrentNbrOfRxFrames OBJECT-TYPE
   SYNTAX      Counter32
   MAX-ACCESS  read-only
   STATUS      current
   DESCRIPTION
      "Path: ethOam.performance.managedMeps.synthLoss.rx1Sl.current.nbrOfRxFrames

       32 bit unsigned wrappable counter."
   ::= {pr1646v2EthOamManagedMepsEntry 855769345}

pr1646v2EthOamManagedMepsSlRx1SlCurrentNearEndLoss OBJECT-TYPE
   SYNTAX      INTEGER
               {
               invalid (2147483647)
               }
   MAX-ACCESS  read-only
   STATUS      current
   DESCRIPTION
      "Path: ethOam.performance.managedMeps.synthLoss.rx1Sl.current.nearEndLoss

       Possibilities:
               invalid   (2147483647)"
   ::= {pr1646v2EthOamManagedMepsEntry 855769346}

pr1646v2EthOamManagedMepsSlRx1SlOverallNbrOfRxFrames OBJECT-TYPE
   SYNTAX      Counter32
   MAX-ACCESS  read-only
   STATUS      current
   DESCRIPTION
      "Path: ethOam.performance.managedMeps.synthLoss.rx1Sl.overall.nbrOfRxFrames

       32 bit unsigned wrappable counter."
   ::= {pr1646v2EthOamManagedMepsEntry 855769601}

pr1646v2EthOamManagedMepsSlRx1SlOverallNearEndLoss OBJECT-TYPE
   SYNTAX      INTEGER
               {
               invalid (2147483647)
               }
   MAX-ACCESS  read-only
   STATUS      current
   DESCRIPTION
      "Path: ethOam.performance.managedMeps.synthLoss.rx1Sl.overall.nearEndLoss

       Possibilities:
               invalid   (2147483647)"
   ::= {pr1646v2EthOamManagedMepsEntry 855769602}

pr1646v2EthOamManagedMepsSlRxMc1SlCurrentNbrOfRxFrames OBJECT-TYPE
   SYNTAX      Counter32
   MAX-ACCESS  read-only
   STATUS      current
   DESCRIPTION
      "Path: ethOam.performance.managedMeps.synthLoss.rxMc1Sl.current.nbrOfRxFrames

       32 bit unsigned wrappable counter."
   ::= {pr1646v2EthOamManagedMepsEntry 855834881}

pr1646v2EthOamManagedMepsSlRxMc1SlCurrentNearEndLoss OBJECT-TYPE
   SYNTAX      INTEGER
               {
               invalid (2147483647)
               }
   MAX-ACCESS  read-only
   STATUS      current
   DESCRIPTION
      "Path: ethOam.performance.managedMeps.synthLoss.rxMc1Sl.current.nearEndLoss

       Possibilities:
               invalid   (2147483647)"
   ::= {pr1646v2EthOamManagedMepsEntry 855834882}

pr1646v2EthOamManagedMepsSlRxMc1SlOverallNbrOfRxFrames OBJECT-TYPE
   SYNTAX      Counter32
   MAX-ACCESS  read-only
   STATUS      current
   DESCRIPTION
      "Path: ethOam.performance.managedMeps.synthLoss.rxMc1Sl.overall.nbrOfRxFrames

       32 bit unsigned wrappable counter."
   ::= {pr1646v2EthOamManagedMepsEntry 855835137}

pr1646v2EthOamManagedMepsSlRxMc1SlOverallNearEndLoss OBJECT-TYPE
   SYNTAX      INTEGER
               {
               invalid (2147483647)
               }
   MAX-ACCESS  read-only
   STATUS      current
   DESCRIPTION
      "Path: ethOam.performance.managedMeps.synthLoss.rxMc1Sl.overall.nearEndLoss

       Possibilities:
               invalid   (2147483647)"
   ::= {pr1646v2EthOamManagedMepsEntry 855835138}

pr1646v2EthOamManagedMepsSlRx1SlErrorLog OBJECT-TYPE
   SYNTAX      SEQUENCE OF Pr1646v2EthOamManagedMepsSlRx1SlErrorLogEntry
   MAX-ACCESS  not-accessible
   STATUS      current
   DESCRIPTION
      ""
   ::= {pr1646v2EthOamManagedMeps 855769856}

pr1646v2EthOamManagedMepsSlRx1SlErrorLogEntry OBJECT-TYPE
   SYNTAX      Pr1646v2EthOamManagedMepsSlRx1SlErrorLogEntry
   MAX-ACCESS  not-accessible
   STATUS      current
   DESCRIPTION
      ""
   INDEX      { pr1646v2EthOamManagedMepsSlRx1SlErrorLogGlobalIx,
                pr1646v2EthOamManagedMepsTableIx,
                pr1646v2EthOamManagedMepsSlRx1SlErrorLogTableIx }
   ::= {pr1646v2EthOamManagedMepsSlRx1SlErrorLog 1}

Pr1646v2EthOamManagedMepsSlRx1SlErrorLogEntry ::=
   SEQUENCE
      {
      pr1646v2EthOamManagedMepsSlRx1SlErrorLogGlobalIx
         GlobalIndex,
      pr1646v2EthOamManagedMepsSlRx1SlErrorLogTableIx
         TableIndex,
      pr1646v2EthOamManagedMepsSlRx1SlErrorLogTimeStamp
         DisplayString,
      pr1646v2EthOamManagedMepsSlRx1SlErrorLogSysUpTime
         TimeTicks,
      pr1646v2EthOamManagedMepsSlRx1SlErrorLogNbrOfRxFrames
         Counter32,
      pr1646v2EthOamManagedMepsSlRx1SlErrorLogNearEndLoss
         INTEGER
      }

pr1646v2EthOamManagedMepsSlRx1SlErrorLogGlobalIx OBJECT-TYPE
   SYNTAX      GlobalIndex
   MAX-ACCESS  not-accessible
   STATUS      current
   DESCRIPTION
      "The value of the tlsCntTreeGlobalIndex of the MANAGED OBJECT."
   ::= {pr1646v2EthOamManagedMepsSlRx1SlErrorLogEntry 10}

pr1646v2EthOamManagedMepsSlRx1SlErrorLogTableIx OBJECT-TYPE
   SYNTAX      TableIndex
   MAX-ACCESS  not-accessible
   STATUS      current
   DESCRIPTION
      ""
   ::= {pr1646v2EthOamManagedMepsSlRx1SlErrorLogEntry 11}

pr1646v2EthOamManagedMepsSlRx1SlErrorLogTimeStamp OBJECT-TYPE
   SYNTAX      DisplayString
   MAX-ACCESS  read-only
   STATUS      current
   DESCRIPTION
      "Path: ethOam.performance.managedMeps.synthLoss.rx1Sl.errorLog.timeStamp"
   ::= {pr1646v2EthOamManagedMepsSlRx1SlErrorLogEntry 134217728}

pr1646v2EthOamManagedMepsSlRx1SlErrorLogSysUpTime OBJECT-TYPE
   SYNTAX      TimeTicks
   MAX-ACCESS  read-only
   STATUS      current
   DESCRIPTION
      "Path: ethOam.performance.managedMeps.synthLoss.rx1Sl.errorLog.sysUpTime

       Time in centi-second."
   ::= {pr1646v2EthOamManagedMepsSlRx1SlErrorLogEntry 16777216}

pr1646v2EthOamManagedMepsSlRx1SlErrorLogNbrOfRxFrames OBJECT-TYPE
   SYNTAX      Counter32
   MAX-ACCESS  read-only
   STATUS      current
   DESCRIPTION
      "Path: ethOam.performance.managedMeps.synthLoss.rx1Sl.errorLog.nbrOfRxFrames

       32 bit unsigned wrappable counter."
   ::= {pr1646v2EthOamManagedMepsSlRx1SlErrorLogEntry 50331648}

pr1646v2EthOamManagedMepsSlRx1SlErrorLogNearEndLoss OBJECT-TYPE
   SYNTAX      INTEGER
               {
               invalid (2147483647)
               }
   MAX-ACCESS  read-only
   STATUS      current
   DESCRIPTION
      "Path: ethOam.performance.managedMeps.synthLoss.rx1Sl.errorLog.nearEndLoss

       Possibilities:
               invalid   (2147483647)"
   ::= {pr1646v2EthOamManagedMepsSlRx1SlErrorLogEntry 100663296}

pr1646v2EthOamManagedMepsSlRxMc1SlErrorLog OBJECT-TYPE
   SYNTAX      SEQUENCE OF Pr1646v2EthOamManagedMepsSlRxMc1SlErrorLogEntry
   MAX-ACCESS  not-accessible
   STATUS      current
   DESCRIPTION
      ""
   ::= {pr1646v2EthOamManagedMeps 855835392}

pr1646v2EthOamManagedMepsSlRxMc1SlErrorLogEntry OBJECT-TYPE
   SYNTAX      Pr1646v2EthOamManagedMepsSlRxMc1SlErrorLogEntry
   MAX-ACCESS  not-accessible
   STATUS      current
   DESCRIPTION
      ""
   INDEX      { pr1646v2EthOamManagedMepsSlRxMc1SlErrorLogGlobalIx,
                pr1646v2EthOamManagedMepsTableIx,
                pr1646v2EthOamManagedMepsSlRxMc1SlErrorLogTableIx }
   ::= {pr1646v2EthOamManagedMepsSlRxMc1SlErrorLog 1}

Pr1646v2EthOamManagedMepsSlRxMc1SlErrorLogEntry ::=
   SEQUENCE
      {
      pr1646v2EthOamManagedMepsSlRxMc1SlErrorLogGlobalIx
         GlobalIndex,
      pr1646v2EthOamManagedMepsSlRxMc1SlErrorLogTableIx
         TableIndex,
      pr1646v2EthOamManagedMepsSlRxMc1SlErrorLogTimeStamp
         DisplayString,
      pr1646v2EthOamManagedMepsSlRxMc1SlErrorLogSysUpTime
         TimeTicks,
      pr1646v2EthOamManagedMepsSlRxMc1SlErrorLogNbrOfRxFrames
         Counter32,
      pr1646v2EthOamManagedMepsSlRxMc1SlErrorLogNearEndLoss
         INTEGER
      }

pr1646v2EthOamManagedMepsSlRxMc1SlErrorLogGlobalIx OBJECT-TYPE
   SYNTAX      GlobalIndex
   MAX-ACCESS  not-accessible
   STATUS      current
   DESCRIPTION
      "The value of the tlsCntTreeGlobalIndex of the MANAGED OBJECT."
   ::= {pr1646v2EthOamManagedMepsSlRxMc1SlErrorLogEntry 10}

pr1646v2EthOamManagedMepsSlRxMc1SlErrorLogTableIx OBJECT-TYPE
   SYNTAX      TableIndex
   MAX-ACCESS  not-accessible
   STATUS      current
   DESCRIPTION
      ""
   ::= {pr1646v2EthOamManagedMepsSlRxMc1SlErrorLogEntry 11}

pr1646v2EthOamManagedMepsSlRxMc1SlErrorLogTimeStamp OBJECT-TYPE
   SYNTAX      DisplayString
   MAX-ACCESS  read-only
   STATUS      current
   DESCRIPTION
      "Path: ethOam.performance.managedMeps.synthLoss.rxMc1Sl.errorLog.timeStamp"
   ::= {pr1646v2EthOamManagedMepsSlRxMc1SlErrorLogEntry 134217728}

pr1646v2EthOamManagedMepsSlRxMc1SlErrorLogSysUpTime OBJECT-TYPE
   SYNTAX      TimeTicks
   MAX-ACCESS  read-only
   STATUS      current
   DESCRIPTION
      "Path: ethOam.performance.managedMeps.synthLoss.rxMc1Sl.errorLog.sysUpTime

       Time in centi-second."
   ::= {pr1646v2EthOamManagedMepsSlRxMc1SlErrorLogEntry 16777216}

pr1646v2EthOamManagedMepsSlRxMc1SlErrorLogNbrOfRxFrames OBJECT-TYPE
   SYNTAX      Counter32
   MAX-ACCESS  read-only
   STATUS      current
   DESCRIPTION
      "Path: ethOam.performance.managedMeps.synthLoss.rxMc1Sl.errorLog.nbrOfRxFrames

       32 bit unsigned wrappable counter."
   ::= {pr1646v2EthOamManagedMepsSlRxMc1SlErrorLogEntry 50331648}

pr1646v2EthOamManagedMepsSlRxMc1SlErrorLogNearEndLoss OBJECT-TYPE
   SYNTAX      INTEGER
               {
               invalid (2147483647)
               }
   MAX-ACCESS  read-only
   STATUS      current
   DESCRIPTION
      "Path: ethOam.performance.managedMeps.synthLoss.rxMc1Sl.errorLog.nearEndLoss

       Possibilities:
               invalid   (2147483647)"
   ::= {pr1646v2EthOamManagedMepsSlRxMc1SlErrorLogEntry 100663296}



fr1646v2EthOam OBJECT IDENTIFIER ::= {r1646v2EthOam 13}


fr1646v2EthOamAlarm OBJECT IDENTIFIER ::= {fr1646v2EthOam 202}

fr1646v2EthOamAlarmSSCTable OBJECT-TYPE
   SYNTAX      SEQUENCE OF Fr1646v2EthOamAlarmEntry
   MAX-ACCESS  not-accessible
   STATUS      current
   DESCRIPTION
      "ETH OAM AlarmInfo"
   ::= {fr1646v2EthOamAlarm 1}

fr1646v2EthOamAlarmEntry OBJECT-TYPE
   SYNTAX      Fr1646v2EthOamAlarmEntry
   MAX-ACCESS  not-accessible
   STATUS      current
   DESCRIPTION
      ""
   INDEX      { fr1646v2EthOamAlarmGlobalIx }
   ::= {fr1646v2EthOamAlarmSSCTable 1}

Fr1646v2EthOamAlarmEntry ::=
   SEQUENCE
      {
      fr1646v2EthOamAlarmGlobalIx
         GlobalIndex,
      fr1646v2EthOamAlarmDiscriminator
         Integer32,
      fr1646v2EthOamAlarmCurrent
         Integer32,
      fr1646v2EthOamAlarmPrevious
         Integer32,
      fr1646v2EthOamAlarmMask
         Integer32,
      fr1646v2EthOamAlarmLevDelay
         Integer32,
      fr1646v2EthOamAlarmLevJitter
         Integer32,
      fr1646v2EthOamAlarmLevLossOfContinuity
         Integer32,
      fr1646v2EthOamAlarmLevMismerge
         Integer32,
      fr1646v2EthOamAlarmLevUnexpectedMep
         Integer32,
      fr1646v2EthOamAlarmLevUnexpectedMegLevel
         Integer32,
      fr1646v2EthOamAlarmLevUnexpectedPeriod
         Integer32,
      fr1646v2EthOamAlarmLevRdi
         Integer32,
      fr1646v2EthOamAlarmLevAis
         Integer32,
      fr1646v2EthOamAlarmLevMacStatus
         Integer32,
      fr1646v2EthOamAlarmLevQualityMonitor
         Integer32
      }

fr1646v2EthOamAlarmGlobalIx OBJECT-TYPE
   SYNTAX      GlobalIndex
   MAX-ACCESS  not-accessible
   STATUS      current
   DESCRIPTION
      "The value of the tlsCntTreeGlobalIndex of the MANAGED OBJECT."
   ::= {fr1646v2EthOamAlarmEntry 10}

fr1646v2EthOamAlarmDiscriminator OBJECT-TYPE
   SYNTAX      Integer32
   MAX-ACCESS  read-only
   STATUS      current
   DESCRIPTION
      "Path: ethOam.alarms.alarmInfo.discriminator"
   ::= {fr1646v2EthOamAlarmEntry 16777216}

fr1646v2EthOamAlarmCurrent OBJECT-TYPE
   SYNTAX      Integer32
   MAX-ACCESS  read-only
   STATUS      current
   DESCRIPTION
      "Path: ethOam.alarms.alarmInfo.currentAlarms

       Bit meanings:
               bit 1 = delay,
               bit 2 = jitter,
               bit 3 = lossOfContinuity,
               bit 4 = mismerge,
               bit 5 = unexpectedMep,
               bit 6 = unexpectedMegLevel,
               bit 7 = unexpectedPeriod,
               bit 8 = rdi,
               bit 9 = ais,
               bit 10 = macStatus,
               bit 11 = qualityMonitor"
   ::= {fr1646v2EthOamAlarmEntry 33554432}

fr1646v2EthOamAlarmPrevious OBJECT-TYPE
   SYNTAX      Integer32
   MAX-ACCESS  read-only
   STATUS      current
   DESCRIPTION
      "Path: ethOam.alarms.alarmInfo.previousAlarms

       Bit meanings:
               bit 1 = delay,
               bit 2 = jitter,
               bit 3 = lossOfContinuity,
               bit 4 = mismerge,
               bit 5 = unexpectedMep,
               bit 6 = unexpectedMegLevel,
               bit 7 = unexpectedPeriod,
               bit 8 = rdi,
               bit 9 = ais,
               bit 10 = macStatus,
               bit 11 = qualityMonitor"
   ::= {fr1646v2EthOamAlarmEntry 50331648}

fr1646v2EthOamAlarmMask OBJECT-TYPE
   SYNTAX      Integer32
   MAX-ACCESS  read-only
   STATUS      current
   DESCRIPTION
      "Path: ethOam.alarms.alarmInfo.alarmMask

       Bit meanings:
               bit 1 = delay,
               bit 2 = jitter,
               bit 3 = lossOfContinuity,
               bit 4 = mismerge,
               bit 5 = unexpectedMep,
               bit 6 = unexpectedMegLevel,
               bit 7 = unexpectedPeriod,
               bit 8 = rdi,
               bit 9 = ais,
               bit 10 = macStatus,
               bit 11 = qualityMonitor"
   ::= {fr1646v2EthOamAlarmEntry 67108864}

fr1646v2EthOamAlarmLevDelay OBJECT-TYPE
   SYNTAX      Integer32
   MAX-ACCESS  read-only
   STATUS      current
   DESCRIPTION
      "Path: ethOam.alarms.alarmInfo.alarmLevel.delay"
   ::= {fr1646v2EthOamAlarmEntry 84017152}

fr1646v2EthOamAlarmLevJitter OBJECT-TYPE
   SYNTAX      Integer32
   MAX-ACCESS  read-only
   STATUS      current
   DESCRIPTION
      "Path: ethOam.alarms.alarmInfo.alarmLevel.jitter"
   ::= {fr1646v2EthOamAlarmEntry 84082688}

fr1646v2EthOamAlarmLevLossOfContinuity OBJECT-TYPE
   SYNTAX      Integer32
   MAX-ACCESS  read-only
   STATUS      current
   DESCRIPTION
      "Path: ethOam.alarms.alarmInfo.alarmLevel.lossOfContinuity"
   ::= {fr1646v2EthOamAlarmEntry 84148224}

fr1646v2EthOamAlarmLevMismerge OBJECT-TYPE
   SYNTAX      Integer32
   MAX-ACCESS  read-only
   STATUS      current
   DESCRIPTION
      "Path: ethOam.alarms.alarmInfo.alarmLevel.mismerge"
   ::= {fr1646v2EthOamAlarmEntry 84213760}

fr1646v2EthOamAlarmLevUnexpectedMep OBJECT-TYPE
   SYNTAX      Integer32
   MAX-ACCESS  read-only
   STATUS      current
   DESCRIPTION
      "Path: ethOam.alarms.alarmInfo.alarmLevel.unexpectedMep"
   ::= {fr1646v2EthOamAlarmEntry 84279296}

fr1646v2EthOamAlarmLevUnexpectedMegLevel OBJECT-TYPE
   SYNTAX      Integer32
   MAX-ACCESS  read-only
   STATUS      current
   DESCRIPTION
      "Path: ethOam.alarms.alarmInfo.alarmLevel.unexpectedMegLevel"
   ::= {fr1646v2EthOamAlarmEntry 84344832}

fr1646v2EthOamAlarmLevUnexpectedPeriod OBJECT-TYPE
   SYNTAX      Integer32
   MAX-ACCESS  read-only
   STATUS      current
   DESCRIPTION
      "Path: ethOam.alarms.alarmInfo.alarmLevel.unexpectedPeriod"
   ::= {fr1646v2EthOamAlarmEntry 84410368}

fr1646v2EthOamAlarmLevRdi OBJECT-TYPE
   SYNTAX      Integer32
   MAX-ACCESS  read-only
   STATUS      current
   DESCRIPTION
      "Path: ethOam.alarms.alarmInfo.alarmLevel.rdi"
   ::= {fr1646v2EthOamAlarmEntry 84475904}

fr1646v2EthOamAlarmLevAis OBJECT-TYPE
   SYNTAX      Integer32
   MAX-ACCESS  read-only
   STATUS      current
   DESCRIPTION
      "Path: ethOam.alarms.alarmInfo.alarmLevel.ais"
   ::= {fr1646v2EthOamAlarmEntry 84541440}

fr1646v2EthOamAlarmLevMacStatus OBJECT-TYPE
   SYNTAX      Integer32
   MAX-ACCESS  read-only
   STATUS      current
   DESCRIPTION
      "Path: ethOam.alarms.alarmInfo.alarmLevel.macStatus"
   ::= {fr1646v2EthOamAlarmEntry 84606976}

fr1646v2EthOamAlarmLevQualityMonitor OBJECT-TYPE
   SYNTAX      Integer32
   MAX-ACCESS  read-only
   STATUS      current
   DESCRIPTION
      "Path: ethOam.alarms.alarmInfo.alarmLevel.qualityMonitor"
   ::= {fr1646v2EthOamAlarmEntry 84672512}


fr1646v2EthOamAlarmE2 OBJECT IDENTIFIER ::= {fr1646v2EthOamAlarm 2}

fr1646v2EthOamAlarmE2Entry OBJECT IDENTIFIER ::= {fr1646v2EthOamAlarmE2 1}

fr1646v2EthOamAlarmE2Delay OBJECT IDENTIFIER ::= {fr1646v2EthOamAlarmE2Entry 11}

fr1646v2EthOamAlarmE2DelayPfx OBJECT IDENTIFIER ::= {fr1646v2EthOamAlarmE2Delay 0}

fr1646v2EthOamAlarmE2DelayOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'delay'
                representing an alarm condition in the alarm word
                of attribute 'alarmInfo' of managed object 'ethOam'
                (root='router1646') has changed from the ON to the OFF state."
   ::= {fr1646v2EthOamAlarmE2DelayPfx 1}

fr1646v2EthOamAlarmE2DelayOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'delay'
                representing an alarm condition in the alarm word
                of attribute 'alarmInfo' of managed object 'ethOam'
                (root='router1646') has changed from the OFF to the ON state."
   ::= {fr1646v2EthOamAlarmE2DelayPfx 2}

fr1646v2EthOamAlarmE2Jitter OBJECT IDENTIFIER ::= {fr1646v2EthOamAlarmE2Entry 12}

fr1646v2EthOamAlarmE2JitterPfx OBJECT IDENTIFIER ::= {fr1646v2EthOamAlarmE2Jitter 0}

fr1646v2EthOamAlarmE2JitterOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'jitter'
                representing an alarm condition in the alarm word
                of attribute 'alarmInfo' of managed object 'ethOam'
                (root='router1646') has changed from the ON to the OFF state."
   ::= {fr1646v2EthOamAlarmE2JitterPfx 1}

fr1646v2EthOamAlarmE2JitterOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'jitter'
                representing an alarm condition in the alarm word
                of attribute 'alarmInfo' of managed object 'ethOam'
                (root='router1646') has changed from the OFF to the ON state."
   ::= {fr1646v2EthOamAlarmE2JitterPfx 2}

fr1646v2EthOamAlarmE2LossOfContinuity OBJECT IDENTIFIER ::= {fr1646v2EthOamAlarmE2Entry 13}

fr1646v2EthOamAlarmE2LossOfContinuityPfx OBJECT IDENTIFIER ::= {fr1646v2EthOamAlarmE2LossOfContinuity 0}

fr1646v2EthOamAlarmE2LossOfContinuityOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'lossOfContinuity'
                representing an alarm condition in the alarm word
                of attribute 'alarmInfo' of managed object 'ethOam'
                (root='router1646') has changed from the ON to the OFF state."
   ::= {fr1646v2EthOamAlarmE2LossOfContinuityPfx 1}

fr1646v2EthOamAlarmE2LossOfContinuityOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'lossOfContinuity'
                representing an alarm condition in the alarm word
                of attribute 'alarmInfo' of managed object 'ethOam'
                (root='router1646') has changed from the OFF to the ON state."
   ::= {fr1646v2EthOamAlarmE2LossOfContinuityPfx 2}

fr1646v2EthOamAlarmE2Mismerge OBJECT IDENTIFIER ::= {fr1646v2EthOamAlarmE2Entry 14}

fr1646v2EthOamAlarmE2MismergePfx OBJECT IDENTIFIER ::= {fr1646v2EthOamAlarmE2Mismerge 0}

fr1646v2EthOamAlarmE2MismergeOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'mismerge'
                representing an alarm condition in the alarm word
                of attribute 'alarmInfo' of managed object 'ethOam'
                (root='router1646') has changed from the ON to the OFF state."
   ::= {fr1646v2EthOamAlarmE2MismergePfx 1}

fr1646v2EthOamAlarmE2MismergeOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'mismerge'
                representing an alarm condition in the alarm word
                of attribute 'alarmInfo' of managed object 'ethOam'
                (root='router1646') has changed from the OFF to the ON state."
   ::= {fr1646v2EthOamAlarmE2MismergePfx 2}

fr1646v2EthOamAlarmE2UnexpectedMep OBJECT IDENTIFIER ::= {fr1646v2EthOamAlarmE2Entry 15}

fr1646v2EthOamAlarmE2UnexpectedMepPfx OBJECT IDENTIFIER ::= {fr1646v2EthOamAlarmE2UnexpectedMep 0}

fr1646v2EthOamAlarmE2UnexpectedMepOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedMep'
                representing an alarm condition in the alarm word
                of attribute 'alarmInfo' of managed object 'ethOam'
                (root='router1646') has changed from the ON to the OFF state."
   ::= {fr1646v2EthOamAlarmE2UnexpectedMepPfx 1}

fr1646v2EthOamAlarmE2UnexpectedMepOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedMep'
                representing an alarm condition in the alarm word
                of attribute 'alarmInfo' of managed object 'ethOam'
                (root='router1646') has changed from the OFF to the ON state."
   ::= {fr1646v2EthOamAlarmE2UnexpectedMepPfx 2}

fr1646v2EthOamAlarmE2UnexpectedMegLevel OBJECT IDENTIFIER ::= {fr1646v2EthOamAlarmE2Entry 16}

fr1646v2EthOamAlarmE2UnexpectedMegLevelPfx OBJECT IDENTIFIER ::= {fr1646v2EthOamAlarmE2UnexpectedMegLevel 0}

fr1646v2EthOamAlarmE2UnexpectedMegLevelOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedMegLevel'
                representing an alarm condition in the alarm word
                of attribute 'alarmInfo' of managed object 'ethOam'
                (root='router1646') has changed from the ON to the OFF state."
   ::= {fr1646v2EthOamAlarmE2UnexpectedMegLevelPfx 1}

fr1646v2EthOamAlarmE2UnexpectedMegLevelOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedMegLevel'
                representing an alarm condition in the alarm word
                of attribute 'alarmInfo' of managed object 'ethOam'
                (root='router1646') has changed from the OFF to the ON state."
   ::= {fr1646v2EthOamAlarmE2UnexpectedMegLevelPfx 2}

fr1646v2EthOamAlarmE2UnexpectedPeriod OBJECT IDENTIFIER ::= {fr1646v2EthOamAlarmE2Entry 17}

fr1646v2EthOamAlarmE2UnexpectedPeriodPfx OBJECT IDENTIFIER ::= {fr1646v2EthOamAlarmE2UnexpectedPeriod 0}

fr1646v2EthOamAlarmE2UnexpectedPeriodOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedPeriod'
                representing an alarm condition in the alarm word
                of attribute 'alarmInfo' of managed object 'ethOam'
                (root='router1646') has changed from the ON to the OFF state."
   ::= {fr1646v2EthOamAlarmE2UnexpectedPeriodPfx 1}

fr1646v2EthOamAlarmE2UnexpectedPeriodOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unexpectedPeriod'
                representing an alarm condition in the alarm word
                of attribute 'alarmInfo' of managed object 'ethOam'
                (root='router1646') has changed from the OFF to the ON state."
   ::= {fr1646v2EthOamAlarmE2UnexpectedPeriodPfx 2}

fr1646v2EthOamAlarmE2Rdi OBJECT IDENTIFIER ::= {fr1646v2EthOamAlarmE2Entry 18}

fr1646v2EthOamAlarmE2RdiPfx OBJECT IDENTIFIER ::= {fr1646v2EthOamAlarmE2Rdi 0}

fr1646v2EthOamAlarmE2RdiOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'rdi'
                representing an alarm condition in the alarm word
                of attribute 'alarmInfo' of managed object 'ethOam'
                (root='router1646') has changed from the ON to the OFF state."
   ::= {fr1646v2EthOamAlarmE2RdiPfx 1}

fr1646v2EthOamAlarmE2RdiOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'rdi'
                representing an alarm condition in the alarm word
                of attribute 'alarmInfo' of managed object 'ethOam'
                (root='router1646') has changed from the OFF to the ON state."
   ::= {fr1646v2EthOamAlarmE2RdiPfx 2}

fr1646v2EthOamAlarmE2Ais OBJECT IDENTIFIER ::= {fr1646v2EthOamAlarmE2Entry 19}

fr1646v2EthOamAlarmE2AisPfx OBJECT IDENTIFIER ::= {fr1646v2EthOamAlarmE2Ais 0}

fr1646v2EthOamAlarmE2AisOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ais'
                representing an alarm condition in the alarm word
                of attribute 'alarmInfo' of managed object 'ethOam'
                (root='router1646') has changed from the ON to the OFF state."
   ::= {fr1646v2EthOamAlarmE2AisPfx 1}

fr1646v2EthOamAlarmE2AisOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ais'
                representing an alarm condition in the alarm word
                of attribute 'alarmInfo' of managed object 'ethOam'
                (root='router1646') has changed from the OFF to the ON state."
   ::= {fr1646v2EthOamAlarmE2AisPfx 2}

fr1646v2EthOamAlarmE2MacStatus OBJECT IDENTIFIER ::= {fr1646v2EthOamAlarmE2Entry 20}

fr1646v2EthOamAlarmE2MacStatusPfx OBJECT IDENTIFIER ::= {fr1646v2EthOamAlarmE2MacStatus 0}

fr1646v2EthOamAlarmE2MacStatusOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'macStatus'
                representing an alarm condition in the alarm word
                of attribute 'alarmInfo' of managed object 'ethOam'
                (root='router1646') has changed from the ON to the OFF state."
   ::= {fr1646v2EthOamAlarmE2MacStatusPfx 1}

fr1646v2EthOamAlarmE2MacStatusOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'macStatus'
                representing an alarm condition in the alarm word
                of attribute 'alarmInfo' of managed object 'ethOam'
                (root='router1646') has changed from the OFF to the ON state."
   ::= {fr1646v2EthOamAlarmE2MacStatusPfx 2}

fr1646v2EthOamAlarmE2QualityMonitor OBJECT IDENTIFIER ::= {fr1646v2EthOamAlarmE2Entry 21}

fr1646v2EthOamAlarmE2QualityMonitorPfx OBJECT IDENTIFIER ::= {fr1646v2EthOamAlarmE2QualityMonitor 0}

fr1646v2EthOamAlarmE2QualityMonitorOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qualityMonitor'
                representing an alarm condition in the alarm word
                of attribute 'alarmInfo' of managed object 'ethOam'
                (root='router1646') has changed from the ON to the OFF state."
   ::= {fr1646v2EthOamAlarmE2QualityMonitorPfx 1}

fr1646v2EthOamAlarmE2QualityMonitorOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qualityMonitor'
                representing an alarm condition in the alarm word
                of attribute 'alarmInfo' of managed object 'ethOam'
                (root='router1646') has changed from the OFF to the ON state."
   ::= {fr1646v2EthOamAlarmE2QualityMonitorPfx 2}



ar1646v2EthOam OBJECT IDENTIFIER ::= {r1646v2EthOam 16}


ar1646v2EthOamStopPacketDebug OBJECT IDENTIFIER ::= {ar1646v2EthOam 32}

ar1646v2EthOamStopPacketDebugTable OBJECT-TYPE
   SYNTAX      SEQUENCE OF Ar1646v2EthOamStopPacketDebugEntry
   MAX-ACCESS  not-accessible
   STATUS      current
   DESCRIPTION
      "action in the debug group"
   ::= {ar1646v2EthOamStopPacketDebug 1}

ar1646v2EthOamStopPacketDebugEntry OBJECT-TYPE
   SYNTAX      Ar1646v2EthOamStopPacketDebugEntry
   MAX-ACCESS  not-accessible
   STATUS      current
   DESCRIPTION
      ""
   INDEX      { ar1646v2EthOamStopPacketDebugGlobalIx }
   ::= {ar1646v2EthOamStopPacketDebugTable 1}

Ar1646v2EthOamStopPacketDebugEntry ::=
   SEQUENCE
      {
      ar1646v2EthOamStopPacketDebugGlobalIx
         GlobalIndex,
      ar1646v2EthOamStopPacketDebugValue
         Integer32
      }

ar1646v2EthOamStopPacketDebugGlobalIx OBJECT-TYPE
   SYNTAX      GlobalIndex
   MAX-ACCESS  not-accessible
   STATUS      current
   DESCRIPTION
      "The value of the tlsCntTreeGlobalIndex of the MANAGED OBJECT."
   ::= {ar1646v2EthOamStopPacketDebugEntry 10}

ar1646v2EthOamStopPacketDebugValue OBJECT-TYPE
   SYNTAX      Integer32
   MAX-ACCESS  read-write
   STATUS      current
   DESCRIPTION
      "Path: ethOam.actions.stopPacketDebug"
   ::= {ar1646v2EthOamStopPacketDebugEntry 2147483648}


ar1646v2EthOamStartPacketDebug OBJECT IDENTIFIER ::= {ar1646v2EthOam 31}

ar1646v2EthOamStartPacketDebugTable OBJECT-TYPE
   SYNTAX      SEQUENCE OF Ar1646v2EthOamStartPacketDebugEntry
   MAX-ACCESS  not-accessible
   STATUS      current
   DESCRIPTION
      "action in the debug group"
   ::= {ar1646v2EthOamStartPacketDebug 1}

ar1646v2EthOamStartPacketDebugEntry OBJECT-TYPE
   SYNTAX      Ar1646v2EthOamStartPacketDebugEntry
   MAX-ACCESS  not-accessible
   STATUS      current
   DESCRIPTION
      ""
   INDEX      { ar1646v2EthOamStartPacketDebugGlobalIx }
   ::= {ar1646v2EthOamStartPacketDebugTable 1}

Ar1646v2EthOamStartPacketDebugEntry ::=
   SEQUENCE
      {
      ar1646v2EthOamStartPacketDebugGlobalIx
         GlobalIndex,
      ar1646v2EthOamStartPacketDebugValue
         Integer32
      }

ar1646v2EthOamStartPacketDebugGlobalIx OBJECT-TYPE
   SYNTAX      GlobalIndex
   MAX-ACCESS  not-accessible
   STATUS      current
   DESCRIPTION
      "The value of the tlsCntTreeGlobalIndex of the MANAGED OBJECT."
   ::= {ar1646v2EthOamStartPacketDebugEntry 10}

ar1646v2EthOamStartPacketDebugValue OBJECT-TYPE
   SYNTAX      Integer32
   MAX-ACCESS  read-write
   STATUS      current
   DESCRIPTION
      "Path: ethOam.actions.startPacketDebug"
   ::= {ar1646v2EthOamStartPacketDebugEntry 2147483648}


ar1646v2EthOamClearCounters OBJECT IDENTIFIER ::= {ar1646v2EthOam 263}

ar1646v2EthOamClearCountersTable OBJECT-TYPE
   SYNTAX      SEQUENCE OF Ar1646v2EthOamClearCountersEntry
   MAX-ACCESS  not-accessible
   STATUS      current
   DESCRIPTION
      "reset counters"
   ::= {ar1646v2EthOamClearCounters 1}

ar1646v2EthOamClearCountersEntry OBJECT-TYPE
   SYNTAX      Ar1646v2EthOamClearCountersEntry
   MAX-ACCESS  not-accessible
   STATUS      current
   DESCRIPTION
      ""
   INDEX      { ar1646v2EthOamClearCountersGlobalIx }
   ::= {ar1646v2EthOamClearCountersTable 1}

Ar1646v2EthOamClearCountersEntry ::=
   SEQUENCE
      {
      ar1646v2EthOamClearCountersGlobalIx
         GlobalIndex,
      ar1646v2EthOamClearCountersValue
         Integer32
      }

ar1646v2EthOamClearCountersGlobalIx OBJECT-TYPE
   SYNTAX      GlobalIndex
   MAX-ACCESS  not-accessible
   STATUS      current
   DESCRIPTION
      "The value of the tlsCntTreeGlobalIndex of the MANAGED OBJECT."
   ::= {ar1646v2EthOamClearCountersEntry 10}

ar1646v2EthOamClearCountersValue OBJECT-TYPE
   SYNTAX      Integer32
   MAX-ACCESS  read-write
   STATUS      current
   DESCRIPTION
      "Path: ethOam.actions.clearCounters"
   ::= {ar1646v2EthOamClearCountersEntry 2147483648}


ar1646v2EthOamClearMpStats OBJECT IDENTIFIER ::= {ar1646v2EthOam 28}

ar1646v2EthOamClearMpStatsTable OBJECT-TYPE
   SYNTAX      SEQUENCE OF Ar1646v2EthOamClearMpStatsEntry
   MAX-ACCESS  not-accessible
   STATUS      current
   DESCRIPTION
      "clear Maintenance Point statistics"
   ::= {ar1646v2EthOamClearMpStats 1}

ar1646v2EthOamClearMpStatsEntry OBJECT-TYPE
   SYNTAX      Ar1646v2EthOamClearMpStatsEntry
   MAX-ACCESS  not-accessible
   STATUS      current
   DESCRIPTION
      ""
   INDEX      { ar1646v2EthOamClearMpStatsGlobalIx }
   ::= {ar1646v2EthOamClearMpStatsTable 1}

Ar1646v2EthOamClearMpStatsEntry ::=
   SEQUENCE
      {
      ar1646v2EthOamClearMpStatsGlobalIx
         GlobalIndex,
      ar1646v2EthOamClearMpStatsValue
         Integer32
      }

ar1646v2EthOamClearMpStatsGlobalIx OBJECT-TYPE
   SYNTAX      GlobalIndex
   MAX-ACCESS  not-accessible
   STATUS      current
   DESCRIPTION
      "The value of the tlsCntTreeGlobalIndex of the MANAGED OBJECT."
   ::= {ar1646v2EthOamClearMpStatsEntry 10}

ar1646v2EthOamClearMpStatsValue OBJECT-TYPE
   SYNTAX      Integer32
   MAX-ACCESS  read-write
   STATUS      current
   DESCRIPTION
      "Path: ethOam.actions.clearMpStats"
   ::= {ar1646v2EthOamClearMpStatsEntry 2147483648}


ar1646v2EthOamMaintenancePointName OBJECT IDENTIFIER ::= {ar1646v2EthOam 29}

ar1646v2EthOamMaintenancePointNameTable OBJECT-TYPE
   SYNTAX      SEQUENCE OF Ar1646v2EthOamMaintenancePointNameEntry
   MAX-ACCESS  not-accessible
   STATUS      current
   DESCRIPTION
      "data needed for clearStats action"
   ::= {ar1646v2EthOamMaintenancePointName 1}

ar1646v2EthOamMaintenancePointNameEntry OBJECT-TYPE
   SYNTAX      Ar1646v2EthOamMaintenancePointNameEntry
   MAX-ACCESS  not-accessible
   STATUS      current
   DESCRIPTION
      ""
   INDEX      { ar1646v2EthOamMaintenancePointNameGlobalIx }
   ::= {ar1646v2EthOamMaintenancePointNameTable 1}

Ar1646v2EthOamMaintenancePointNameEntry ::=
   SEQUENCE
      {
      ar1646v2EthOamMaintenancePointNameGlobalIx
         GlobalIndex,
      ar1646v2EthOamMaintenancePointNameValue
         DisplayString
      }

ar1646v2EthOamMaintenancePointNameGlobalIx OBJECT-TYPE
   SYNTAX      GlobalIndex
   MAX-ACCESS  not-accessible
   STATUS      current
   DESCRIPTION
      "The value of the tlsCntTreeGlobalIndex of the MANAGED OBJECT."
   ::= {ar1646v2EthOamMaintenancePointNameEntry 10}

ar1646v2EthOamMaintenancePointNameValue OBJECT-TYPE
   SYNTAX      DisplayString
   MAX-ACCESS  read-write
   STATUS      current
   DESCRIPTION
      "Path: ethOam.actions.maintenancePointName"
   ::= {ar1646v2EthOamMaintenancePointNameEntry 2147483648}


ar1646v2EthOamSlmOnDemand OBJECT IDENTIFIER ::= {ar1646v2EthOam 45}

ar1646v2EthOamSlmOnDemandTable OBJECT-TYPE
   SYNTAX      SEQUENCE OF Ar1646v2EthOamSlmOnDemandEntry
   MAX-ACCESS  not-accessible
   STATUS      current
   DESCRIPTION
      "start synthetic loss measurement"
   ::= {ar1646v2EthOamSlmOnDemand 1}

ar1646v2EthOamSlmOnDemandEntry OBJECT-TYPE
   SYNTAX      Ar1646v2EthOamSlmOnDemandEntry
   MAX-ACCESS  not-accessible
   STATUS      current
   DESCRIPTION
      ""
   INDEX      { ar1646v2EthOamSlmOnDemandGlobalIx }
   ::= {ar1646v2EthOamSlmOnDemandTable 1}

Ar1646v2EthOamSlmOnDemandEntry ::=
   SEQUENCE
      {
      ar1646v2EthOamSlmOnDemandGlobalIx
         GlobalIndex,
      ar1646v2EthOamSlmOnDemandValue
         Integer32
      }

ar1646v2EthOamSlmOnDemandGlobalIx OBJECT-TYPE
   SYNTAX      GlobalIndex
   MAX-ACCESS  not-accessible
   STATUS      current
   DESCRIPTION
      "The value of the tlsCntTreeGlobalIndex of the MANAGED OBJECT."
   ::= {ar1646v2EthOamSlmOnDemandEntry 10}

ar1646v2EthOamSlmOnDemandValue OBJECT-TYPE
   SYNTAX      Integer32
   MAX-ACCESS  read-write
   STATUS      current
   DESCRIPTION
      "Path: ethOam.actions.slmOnDemand"
   ::= {ar1646v2EthOamSlmOnDemandEntry 2147483648}


ar1646v2EthOamAction OBJECT IDENTIFIER ::= {ar1646v2EthOam 46}

ar1646v2EthOamActionSSCTable OBJECT-TYPE
   SYNTAX      SEQUENCE OF Ar1646v2EthOamActionEntry
   MAX-ACCESS  not-accessible
   STATUS      current
   DESCRIPTION
      "data needed for synthetic loss measurement"
   ::= {ar1646v2EthOamAction 1}

ar1646v2EthOamActionEntry OBJECT-TYPE
   SYNTAX      Ar1646v2EthOamActionEntry
   MAX-ACCESS  not-accessible
   STATUS      current
   DESCRIPTION
      ""
   INDEX      { ar1646v2EthOamActionGlobalIx }
   ::= {ar1646v2EthOamActionSSCTable 1}

Ar1646v2EthOamActionEntry ::=
   SEQUENCE
      {
      ar1646v2EthOamActionGlobalIx
         GlobalIndex,
      ar1646v2EthOamActionAction
         INTEGER,
      ar1646v2EthOamActionName
         DisplayString
      }

ar1646v2EthOamActionGlobalIx OBJECT-TYPE
   SYNTAX      GlobalIndex
   MAX-ACCESS  not-accessible
   STATUS      current
   DESCRIPTION
      "The value of the tlsCntTreeGlobalIndex of the MANAGED OBJECT."
   ::= {ar1646v2EthOamActionEntry 10}

ar1646v2EthOamActionAction OBJECT-TYPE
   SYNTAX      INTEGER
               {
               start (1),
               stop (2)
               }
   MAX-ACCESS  read-write
   STATUS      current
   DESCRIPTION
      "Path: ethOam.actions.action.action

       Possibilities:
               start   (1)
               stop   (2)"
   ::= {ar1646v2EthOamActionEntry 16777216}

ar1646v2EthOamActionName OBJECT-TYPE
   SYNTAX      DisplayString
   MAX-ACCESS  read-write
   STATUS      current
   DESCRIPTION
      "Path: ethOam.actions.action.name"
   ::= {ar1646v2EthOamActionEntry 33554432}


ar1646v2EthOamStartMcLoopback OBJECT IDENTIFIER ::= {ar1646v2EthOam 33}

ar1646v2EthOamStartMcLoopbackTable OBJECT-TYPE
   SYNTAX      SEQUENCE OF Ar1646v2EthOamStartMcLoopbackEntry
   MAX-ACCESS  not-accessible
   STATUS      current
   DESCRIPTION
      "start multicast loopback"
   ::= {ar1646v2EthOamStartMcLoopback 1}

ar1646v2EthOamStartMcLoopbackEntry OBJECT-TYPE
   SYNTAX      Ar1646v2EthOamStartMcLoopbackEntry
   MAX-ACCESS  not-accessible
   STATUS      current
   DESCRIPTION
      ""
   INDEX      { ar1646v2EthOamStartMcLoopbackGlobalIx }
   ::= {ar1646v2EthOamStartMcLoopbackTable 1}

Ar1646v2EthOamStartMcLoopbackEntry ::=
   SEQUENCE
      {
      ar1646v2EthOamStartMcLoopbackGlobalIx
         GlobalIndex,
      ar1646v2EthOamStartMcLoopbackValue
         Integer32
      }

ar1646v2EthOamStartMcLoopbackGlobalIx OBJECT-TYPE
   SYNTAX      GlobalIndex
   MAX-ACCESS  not-accessible
   STATUS      current
   DESCRIPTION
      "The value of the tlsCntTreeGlobalIndex of the MANAGED OBJECT."
   ::= {ar1646v2EthOamStartMcLoopbackEntry 10}

ar1646v2EthOamStartMcLoopbackValue OBJECT-TYPE
   SYNTAX      Integer32
   MAX-ACCESS  read-write
   STATUS      current
   DESCRIPTION
      "Path: ethOam.actions.startMcLoopback"
   ::= {ar1646v2EthOamStartMcLoopbackEntry 2147483648}


ar1646v2EthOamMcLoopbackData OBJECT IDENTIFIER ::= {ar1646v2EthOam 34}

ar1646v2EthOamMcLoopbackDataSSCTable OBJECT-TYPE
   SYNTAX      SEQUENCE OF Ar1646v2EthOamMcLoopbackDataEntry
   MAX-ACCESS  not-accessible
   STATUS      current
   DESCRIPTION
      "data needed for multicast loopback action"
   ::= {ar1646v2EthOamMcLoopbackData 1}

ar1646v2EthOamMcLoopbackDataEntry OBJECT-TYPE
   SYNTAX      Ar1646v2EthOamMcLoopbackDataEntry
   MAX-ACCESS  not-accessible
   STATUS      current
   DESCRIPTION
      ""
   INDEX      { ar1646v2EthOamMcLoopbackDataGlobalIx }
   ::= {ar1646v2EthOamMcLoopbackDataSSCTable 1}

Ar1646v2EthOamMcLoopbackDataEntry ::=
   SEQUENCE
      {
      ar1646v2EthOamMcLoopbackDataGlobalIx
         GlobalIndex,
      ar1646v2EthOamMcLoopbackDataSourceMepName
         DisplayString,
      ar1646v2EthOamMcLoopbackDataPriority
         Integer32
      }

ar1646v2EthOamMcLoopbackDataGlobalIx OBJECT-TYPE
   SYNTAX      GlobalIndex
   MAX-ACCESS  not-accessible
   STATUS      current
   DESCRIPTION
      "The value of the tlsCntTreeGlobalIndex of the MANAGED OBJECT."
   ::= {ar1646v2EthOamMcLoopbackDataEntry 10}

ar1646v2EthOamMcLoopbackDataSourceMepName OBJECT-TYPE
   SYNTAX      DisplayString
   MAX-ACCESS  read-write
   STATUS      current
   DESCRIPTION
      "Path: ethOam.actions.mcLoopbackData.sourceMepName"
   ::= {ar1646v2EthOamMcLoopbackDataEntry 16777216}

ar1646v2EthOamMcLoopbackDataPriority OBJECT-TYPE
   SYNTAX      Integer32
   MAX-ACCESS  read-write
   STATUS      current
   DESCRIPTION
      "Path: ethOam.actions.mcLoopbackData.priority"
   ::= {ar1646v2EthOamMcLoopbackDataEntry 33554432}


ar1646v2EthOamStartLinkTrace OBJECT IDENTIFIER ::= {ar1646v2EthOam 25}

ar1646v2EthOamStartLinkTraceTable OBJECT-TYPE
   SYNTAX      SEQUENCE OF Ar1646v2EthOamStartLinkTraceEntry
   MAX-ACCESS  not-accessible
   STATUS      current
   DESCRIPTION
      "start link trace"
   ::= {ar1646v2EthOamStartLinkTrace 1}

ar1646v2EthOamStartLinkTraceEntry OBJECT-TYPE
   SYNTAX      Ar1646v2EthOamStartLinkTraceEntry
   MAX-ACCESS  not-accessible
   STATUS      current
   DESCRIPTION
      ""
   INDEX      { ar1646v2EthOamStartLinkTraceGlobalIx }
   ::= {ar1646v2EthOamStartLinkTraceTable 1}

Ar1646v2EthOamStartLinkTraceEntry ::=
   SEQUENCE
      {
      ar1646v2EthOamStartLinkTraceGlobalIx
         GlobalIndex,
      ar1646v2EthOamStartLinkTraceValue
         Integer32
      }

ar1646v2EthOamStartLinkTraceGlobalIx OBJECT-TYPE
   SYNTAX      GlobalIndex
   MAX-ACCESS  not-accessible
   STATUS      current
   DESCRIPTION
      "The value of the tlsCntTreeGlobalIndex of the MANAGED OBJECT."
   ::= {ar1646v2EthOamStartLinkTraceEntry 10}

ar1646v2EthOamStartLinkTraceValue OBJECT-TYPE
   SYNTAX      Integer32
   MAX-ACCESS  read-write
   STATUS      current
   DESCRIPTION
      "Path: ethOam.actions.startLinkTrace"
   ::= {ar1646v2EthOamStartLinkTraceEntry 2147483648}


ar1646v2EthOamLinkTraceData OBJECT IDENTIFIER ::= {ar1646v2EthOam 26}

ar1646v2EthOamLinkTraceDataSSCTable OBJECT-TYPE
   SYNTAX      SEQUENCE OF Ar1646v2EthOamLinkTraceDataEntry
   MAX-ACCESS  not-accessible
   STATUS      current
   DESCRIPTION
      "data needed for link trace action"
   ::= {ar1646v2EthOamLinkTraceData 1}

ar1646v2EthOamLinkTraceDataEntry OBJECT-TYPE
   SYNTAX      Ar1646v2EthOamLinkTraceDataEntry
   MAX-ACCESS  not-accessible
   STATUS      current
   DESCRIPTION
      ""
   INDEX      { ar1646v2EthOamLinkTraceDataGlobalIx }
   ::= {ar1646v2EthOamLinkTraceDataSSCTable 1}

Ar1646v2EthOamLinkTraceDataEntry ::=
   SEQUENCE
      {
      ar1646v2EthOamLinkTraceDataGlobalIx
         GlobalIndex,
      ar1646v2EthOamLinkTraceDataSourceMepName
         DisplayString,
      ar1646v2EthOamLinkTraceDataDestinationMepId
         Integer32,
      ar1646v2EthOamLinkTraceDataDestinationMacAddress
         OCTET STRING,
      ar1646v2EthOamLinkTraceDataTtl
         Integer32
      }

ar1646v2EthOamLinkTraceDataGlobalIx OBJECT-TYPE
   SYNTAX      GlobalIndex
   MAX-ACCESS  not-accessible
   STATUS      current
   DESCRIPTION
      "The value of the tlsCntTreeGlobalIndex of the MANAGED OBJECT."
   ::= {ar1646v2EthOamLinkTraceDataEntry 10}

ar1646v2EthOamLinkTraceDataSourceMepName OBJECT-TYPE
   SYNTAX      DisplayString
   MAX-ACCESS  read-write
   STATUS      current
   DESCRIPTION
      "Path: ethOam.actions.linkTraceData.sourceMepName"
   ::= {ar1646v2EthOamLinkTraceDataEntry 16777216}

ar1646v2EthOamLinkTraceDataDestinationMepId OBJECT-TYPE
   SYNTAX      Integer32
   MAX-ACCESS  read-write
   STATUS      current
   DESCRIPTION
      "Path: ethOam.actions.linkTraceData.destination.mepId"
   ::= {ar1646v2EthOamLinkTraceDataEntry 33619968}

ar1646v2EthOamLinkTraceDataDestinationMacAddress OBJECT-TYPE
   SYNTAX      OCTET STRING
   MAX-ACCESS  read-write
   STATUS      current
   DESCRIPTION
      "Path: ethOam.actions.linkTraceData.destination.macAddress

       MAC address."
   ::= {ar1646v2EthOamLinkTraceDataEntry 33685504}

ar1646v2EthOamLinkTraceDataTtl OBJECT-TYPE
   SYNTAX      Integer32
   MAX-ACCESS  read-write
   STATUS      current
   DESCRIPTION
      "Path: ethOam.actions.linkTraceData.ttl"
   ::= {ar1646v2EthOamLinkTraceDataEntry 50331648}


ar1646v2EthOamClearDefectLog OBJECT IDENTIFIER ::= {ar1646v2EthOam 24}

ar1646v2EthOamClearDefectLogTable OBJECT-TYPE
   SYNTAX      SEQUENCE OF Ar1646v2EthOamClearDefectLogEntry
   MAX-ACCESS  not-accessible
   STATUS      current
   DESCRIPTION
      "clear defectLog table"
   ::= {ar1646v2EthOamClearDefectLog 1}

ar1646v2EthOamClearDefectLogEntry OBJECT-TYPE
   SYNTAX      Ar1646v2EthOamClearDefectLogEntry
   MAX-ACCESS  not-accessible
   STATUS      current
   DESCRIPTION
      ""
   INDEX      { ar1646v2EthOamClearDefectLogGlobalIx }
   ::= {ar1646v2EthOamClearDefectLogTable 1}

Ar1646v2EthOamClearDefectLogEntry ::=
   SEQUENCE
      {
      ar1646v2EthOamClearDefectLogGlobalIx
         GlobalIndex,
      ar1646v2EthOamClearDefectLogValue
         Integer32
      }

ar1646v2EthOamClearDefectLogGlobalIx OBJECT-TYPE
   SYNTAX      GlobalIndex
   MAX-ACCESS  not-accessible
   STATUS      current
   DESCRIPTION
      "The value of the tlsCntTreeGlobalIndex of the MANAGED OBJECT."
   ::= {ar1646v2EthOamClearDefectLogEntry 10}

ar1646v2EthOamClearDefectLogValue OBJECT-TYPE
   SYNTAX      Integer32
   MAX-ACCESS  read-write
   STATUS      current
   DESCRIPTION
      "Path: ethOam.actions.clearDefectLog"
   ::= {ar1646v2EthOamClearDefectLogEntry 2147483648}



END
